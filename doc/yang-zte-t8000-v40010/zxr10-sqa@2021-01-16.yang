module zxr10-sqa {
  namespace 'http://www.zte.com.cn/zxr10/netconf/schema/rosng/sqa'
            ;
  prefix sqa ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe SQA'
              ;
  revision 2021-01-16 {
    description '1.Remove container feature of configuration/sqa/tests/test/lig'
              + 'ht-twamp/light-twamp/interval-unit.'
                ;
  }
  revision 2020-12-24 {
    description '1.Add  configuration/sqa/tests/test/light-twamp/light-twamp/de'
              + 'lay-mode.'
                ;
  }
  revision 2020-12-07 {
    description '1.Add  configuration/sqa/tests/test/light-twamp/light-twamp/sr'
              + '-policy.'
                ;
  }
  revision 2020-09-07 {
    description '1.Add choice type at configuration/sqa/tests/test/policy.'+"\n"
              + '2.Add case branches of loop-time and frequency at configuratio'
              + 'n/sqa/tests/test/policy/type.'+"\n"
              + '3.Move leaf node loop-time to case branch of configuration/sqa'
              + '/tests/test/policy/type/loop-time.'+"\n"
              + '4.Add leaf node frequency to case branch of configuration/sqa/'
              + 'tests/test/policy/type/frequency.'+"\n"
              + '5.Add feature policy-frequency support products of T8000 and 1'
              + '5K.'
                ;
  }
  revision 2020-08-11 {
    description '1.Add choice ip-addr-family at configuration/sqa/tests/test/ic'
              + 'mpjitter.'+"\n"
              + '2.Add case branches of ipv4 and ipv6 at configuration/sqa/test'
              + 's/test/icmpjitter/ip-addr-family.'+"\n"
              + '3.Modify description of destination-ip and source-ip at config'
              + 'uration/sqa/tests/test/icmpjitter.'+"\n"
              + '4.Move leaf nodes destination-ip and source-ip to case branch '
              + 'of configuration/sqa/tests/test/icmpjitter/ip-addr-family/ipv4'
              + '.'+"\n"
              + '5.Add leaf nodes destination-ipv6 and source-ipv6 to case bran'
              + 'ch of configuration/sqa/tests/test/icmpjitter/ip-addr-family/i'
              + 'pv6.'+"\n"
              + '6.Add leaf nodes min-rtt,max-rtt,avg-rtt,sum-rtt,cur-rtt,min-d'
              + 'elay-jitter,max-delay-jitter,avg-delay-jitter,sum-delay-jitter'
              + ',cur-delay-jitter,cur-delay-jitter-sd,cur-delay-jitter-ds,pkt-'
              + 'loss-num,pkt-loss-rate and destination-ipv6 at state/sqa/icmpj'
              + 'itter-results/icmpjitter-result.'+"\n"
              + '7.Add leaf nodes min-rtt,max-rtt,avg-rtt,sum-rtt,cur-rtt,min-d'
              + 'elay-jitter,max-delay-jitter,avg-delay-jitter,sum-delay-jitter'
              + ',cur-delay-jitter,cur-delay-jitter-sd,cur-delay-jitter-ds,pkt-'
              + 'loss-num,pkt-loss-rate and destination-ipv6 at icmpjitter-even'
              + 't/icmpjitter-result.'+"\n"
              + '8.Modify description of state/sqa/icmpjitter-results/icmpjitte'
              + 'r-result/destination-ip.'+"\n"
              + '9.Modify description of icmpjitter-event/icmpjitter-result/des'
              + 'tination-ip.'+"\n"
              + '10.Move size node at configuration/sqa/tests/test/icmp to conf'
              + 'iguration/sqa/tests/test/icmp/ip-addr-family/ipv4.'+"\n"
              + '11.Add leaf node size-ipv6 at configuration/sqa/tests/test/icm'
              + 'p/ip-addr-family/ipv6.'+"\n"
              + '12.Move size node at configuration/sqa/tests/test/icmpjitter t'
              + 'o configuration/sqa/tests/test/icmpjitter/ip-addr-family/ipv4.'
              + ''+"\n"
              + '13.Add leaf node size-ipv6 at configuration/sqa/tests/test/icm'
              + 'pjitter/ip-addr-family/ipv6.'
                ;
  }
  revision 2020-07-16 {
    description '1.Obsolete sqa:state/sqa/light-twamp-result.'+"\n"
              + '2.Add sqa:state/sqa/light-twamp-results/light-twamp-result.'
                ;
  }
  revision 2020-06-16 {
    description '1.Modify range and description for configuration/sqa/tests/tes'
              + 't/ftp/encrypted-password.'+"\n"
              + '2.Modify range and description for configuration/sqa/tests/tes'
              + 't/snmp/encrypted-community.'
                ;
  }
  revision 2020-04-08 {
    description '1.Add choice ip-addr-family at configuration/sqa/tests/test/pr'
              + 'oactive-ping.'+"\n"
              + '2.Add leaf node destination-ipv6 at configuration/sqa/tests/te'
              + 'st/proactive-ping.'+"\n"
              + '3.Add leaf node source-ipv6 at configuration/sqa/tests/test/pr'
              + 'oactive-ping.'+"\n"
              + '4.Add leaf node nexthop-address-ipv6 at configuration/sqa/test'
              + 's/test/proactive-ping.'+"\n"
              + '5.Add case ipv4 that contains leaves of source-ip,destination-'
              + 'ip and nexthop-address at the choice of configuration/sqa/test'
              + 's/test/proactive-ping/ip-addr-family. '+"\n"
              + '6.Add case ipv6 that contains leaves of source-ipv6,destinatio'
              + 'n-ipv6 and nexthop-address-ipv6 at the choice of configuration'
              + '/sqa/tests/test/proactive-ping/ip-addr-family.'
                ;
  }
  revision 2020-03-18 {
    description '1.Add leaf node destination-ipv6 at state/sqa/icmp-results/icm'
              + 'p-result.'+"\n"
              + '2.Modify the description of state/sqa/icmp-results/icmp-result'
              + '/destination-ip.'+"\n"
              + '3.Add leaf node destination-ipv6 at state/sqa/udp-results/udp-'
              + 'result.'+"\n"
              + '4.Modify the description of state/sqa/udp-results/udp-result/d'
              + 'estination-ip.'+"\n"
              + '5.Add leaf node destination-ipv6 at state/sqa/tcp-results/tcp-'
              + 'result.'+"\n"
              + '6.Modify the description of state/sqa/tcp-results/tcp-result/d'
              + 'estination-ip.'+"\n"
              + '7.Add leaf node destination-ipv6 at state/sqa/udpjitter-result'
              + 's/udpjitter-result.'+"\n"
              + '8.Modify the description of state/sqa/udpjitter-results/udpjit'
              + 'ter-result/destination-ip.'+"\n"
              + '9.Add leaf node destination-ipv6 at icmp-event/icmp-result.'+"\n"
              + '10.Modify the description of icmp-event/icmp-result/destinatio'
              + 'n-ip.'+"\n"
              + '11.Add leaf node destination-ipv6 at udp-event/udp-result.'+"\n"
              + '12.Modify the description of udp-event/udp-result/destination-'
              + 'ip.'+"\n"
              + '13.Add leaf node destination-ipv6 at tcp-event/tcp-result.'+"\n"
              + '14.Modify the description of tcp-event/tcp-result/destination-'
              + 'ip.'+"\n"
              + '15.Add leaf node destination-ipv6 at udpjitter-event/udpjitter'
              + '-result.'+"\n"
              + '16.Modify the description of udpjitter-event/udpjitter-result/'
              + 'destination-ip.'
                ;
  }
  revision 2020-02-18 {
    description '1.Add project label switch99 in the feature of policy-loop.'+"\n"
              + '2.Add choice ip-addr-family at configuration/sqa/tests/test/ic'
              + 'mp.'+"\n"
              + '3.Add leaf node destination-ipv6 at configuration/sqa/tests/te'
              + 'st/icmp.'+"\n"
              + '4.Add leaf node source-ipv6 at configuration/sqa/tests/test/ic'
              + 'mp.'+"\n"
              + '5.Add case ipv4 that contains leaves of destination-ip and sou'
              + 'rce-ip at the choice of configuration/sqa/tests/test/icmp/ip-a'
              + 'ddr-family. '+"\n"
              + '6.Add case ipv6 that contains leaves of destination-ipv6 and s'
              + 'ource-ipv6 at the choice of configuration/sqa/tests/test/icmp/'
              + 'ip-addr-family.'+"\n"
              + '7.Add choice ip-addr-family at configuration/sqa/tests/test/ud'
              + 'p.'+"\n"
              + '8.Add leaf node destination-ipv6 at configuration/sqa/tests/te'
              + 'st/udp.'+"\n"
              + '9.Add case ipv4 that contains leaves of destination-ip at the '
              + 'choice of configuration/sqa/tests/test/udp/ip-addr-family. '+"\n"
              + '10.Add case ipv6 that contains leaves of destination-ipv6 at t'
              + 'he choice of configuration/sqa/tests/test/udp/ip-addr-family.'+"\n"
              + '11.Add choice ip-addr-family at configuration/sqa/tests/test/t'
              + 'cp.'+"\n"
              + '12.Add leaf node destination-ipv6 at configuration/sqa/tests/t'
              + 'est/tcp.'+"\n"
              + '13.Add case ipv4 that contains leaves of destination-ip at the'
              + ' choice of configuration/sqa/tests/test/tcp/ip-addr-family. '+"\n"
              + '14.Add case ipv6 that contains leaves of destination-ipv6 at t'
              + 'he choice of configuration/sqa/tests/test/tcp/ip-addr-family.'+"\n"
              + '15.Add choice ip-addr-family at configuration/sqa/tests/test/u'
              + 'dpjitter.'+"\n"
              + '16.Add leaf node destination-ipv6 at configuration/sqa/tests/t'
              + 'est/udpjitter.'+"\n"
              + '17.Add case ipv4 that contains leaves of destination-ip at the'
              + ' choice of configuration/sqa/tests/test/udpjitter/ip-addr-fami'
              + 'ly. '+"\n"
              + '18.Add case ipv6 that contains leaves of destination-ipv6 at t'
              + 'he choice of configuration/sqa/tests/test/udpjitter/ip-addr-fa'
              + 'mily.'
                ;
  }
  revision 2019-11-27 {
    description '1 Add leaf node of configuration/sqa/tests/test/test-type/proa'
              + 'ctive-ping/proactive-ping/pattern.'
                ;
  }
  revision 2019-08-23 {
    description '1.Add a enumeration value of state/sqa/twamp-reflector-informa'
              + 'tions/twamp-reflector-information/test-mode.'
                ;
  }
  revision 2019-07-22 {
    description '1.Add configuration/sqa/tests/test/light-twamp/light-twamp/vrf'
              + '-name.'
                ;
  }
  revision 2019-06-24 {
    description '1.Add state/sqa/light-twamp-result.'
                ;
  }
  revision 2019-06-17 {
    description '1.Modify length and description for configuration/sqa/tests/te'
              + 'st/ftp/password/password.'+"\n"
              + '2.Modify length and description for configuration/sqa/tests/te'
              + 'st/ftp/encrypted-password/encrypted-password.'
                ;
  }
  revision 2019-05-17 {
    description '1.Add feature delay-statistics-mode.'+"\n"
              + '2.Add configuration/sqa/tests/test/light-twamp/light-twamp/del'
              + 'ay-statistics-mode.'
                ;
  }
  revision 2019-04-30 {
    description '1.Add feature ipv6-address, nd-na-status and nd-na-interval.'+"\n"
              + '2.Add choice configuration/sqa/tests/test/generalflow/generalf'
              + 'low/ipv4-or-ipv6.'+"\n"
              + '3.Add case configuration/sqa/tests/test/generalflow/generalflo'
              + 'w/ipv4-or-ipv6/ipv4 that contains leaves of source-ip and dest'
              + 'ination-ip. '+"\n"
              + '4.Add case configuration/sqa/tests/test/generalflow/generalflo'
              + 'w/ipv4-or-ipv6/ipv6 that contains leaves of source-ipv6 and de'
              + 'stination-ipv6.'+"\n"
              + '5.Add configuration/sqa/tests/test/generalflow/generalflow/nd-'
              + 'na-status.'+"\n"
              + '6.Add configuration/sqa/tests/test/generalflow/generalflow/nd-'
              + 'na-interval.'+"\n"
              + '7.Add choice configuration/sqa/tests/test/light-twamp/light-tw'
              + 'amp/ipv4-or-ipv6.'+"\n"
              + '8.Add case configuration/sqa/tests/test/light-twamp/light-twam'
              + 'p/ipv4-or-ipv6/ipv4 that contains leaves of source-ip and dest'
              + 'ination-ip.'+"\n"
              + '9.Add case configuration/sqa/tests/test/light-twamp/light-twam'
              + 'p/ipv4-or-ipv6/ipv6 that contains leaves of source-ipv6 and de'
              + 'stination-ipv6.'+"\n"
              + '10.Add configuration/sqa/tests/test/light-twamp/light-twamp/nd'
              + '-na-status.'+"\n"
              + '11.Add configuration/sqa/tests/test/light-twamp/light-twamp/nd'
              + '-na-interval.'+"\n"
              + '12.Add choice configuration/sqa/reflectors/reflector/ipv4-or-i'
              + 'pv6.'+"\n"
              + '13.Add case configuration/sqa/reflectors/reflector/ipv4-or-ipv'
              + '6/ipv4 that contains leaves of source-ip and destination-ip.'+"\n"
              + '14.Add case configuration/sqa/reflectors/reflector/ipv4-or-ipv'
              + '6/ipv6 that contains leaves of source-ipv6 and destination-ipv'
              + '6.'+"\n"
              + '15.Add configuration/sqa/reflector-nd-nas/reflector-nd-na and '
              + 'the leaves.'+"\n"
              + '16.Add choice configuration/sqa/twamp-reflectors/twamp-reflect'
              + 'or/ipv4-or-ipv6.'+"\n"
              + '17.Add case configuration/sqa/twamp-reflectors/twamp-reflector'
              + '/ipv4-or-ipv6/ipv4 that contains leaves of source-ip and desti'
              + 'nation-ip.'+"\n"
              + '18.Add case configuration/sqa/twamp-reflectors/twamp-reflector'
              + '/ipv4-or-ipv6/ipv6 that contains leaves of source-ipv6 and des'
              + 'tination-ipv6.'
                ;
  }
  revision 2019-04-02 {
    description '1 Modify the upper limit for configuration/sqa/tests/test/test'
              + '-type/light-twamp/light-twamp/padding-length which depends on '
              + 'the device.'
                ;
  }
  revision 2019-01-05 {
    description '1.Add feature vrf-name.'+"\n"
              + '2.Add configuration/sqa/twamp-reflectors/twamp-reflector/vrf-n'
              + 'ame.'+"\n"
              + '3.Change the configuration/sqa/twamp-reflectors/twamp-reflecto'
              + 'r/inbound-interface from mandatory to optional.'+"\n"
              + '4.Modify range and description for configuration/sqa/tests/tes'
              + 't/light-twamp/source-port.'+"\n"
              + '5.Modify range and description for configuration/sqa/tests/tes'
              + 't/light-twamp/destination-port.'+"\n"
              + '6.Modify range and description for configuration/sqa/twamp-ref'
              + 'lectors/twamp-reflector/source-port. '+"\n"
              + '7.Modify range and description for configuration/sqa/twamp-ref'
              + 'lectors/twamp-reflector/destination-port.'+"\n"
              + '8.Change the configuration/sqa/tests/test/generalflow/y1564/ci'
              + 'r from mandatory to optional.'+"\n"
              + '9.Change the configuration/sqa/tests/test/generalflow/y1564/ei'
              + 'r from mandatory to optional.'+"\n"
              + '10.Change the configuration/sqa/tests/test/generalflow/y1564/o'
              + 'verload from mandatory to optional.'+"\n"
              + '11.Remove the presence feature of configuration/sqa/tests/test'
              + '/generalflow/y1564.'
                ;
  }
  revision 2018-10-17 {
    description '1.Add configuration/sqa/tests/test/generalflow/generalflow/y15'
              + '64.'+"\n"
              + '2.Add y1564-event notification.'
                ;
  }
  revision 2018-05-03 {
    description '1.Modify range for configuration/sqa/tests/test/test-type/gene'
              + 'ralflow/generalflow/packet-size/size.'+"\n"
              + '2.Modify range for configuration/sqa/tests/test/test-type/gene'
              + 'ralflow/generalflow/throughput/one-rate/rate.'+"\n"
              + '3.Modify range for configuration/sqa/tests/test/test-type/gene'
              + 'ralflow/generalflow/throughput/two-rate/low-rate/rate.'+"\n"
              + '4.Modify range for configuration/sqa/tests/test/test-type/gene'
              + 'ralflow/generalflow/throughput/two-rate/high-rate/rate.'+"\n"
              + '5.Modify range for configuration/sqa/tests/test/test-type/gene'
              + 'ralflow/generalflow/loss/rate.'+"\n"
              + '6.Modify range for configuration/sqa/tests/test/test-type/gene'
              + 'ralflow/generalflow/delay/rate.'+"\n"
              + '7.Add configuration/sqa/tests/test/test-type/light-twamp/packe'
              + 't-matching-mode.'+"\n"
              + '8.Add configuration/sqa/tests/test/test-type/light-twamp/perfo'
              + 'rmance-statistics.'+"\n"
              + '9.Add configuration/sqa/tests/test/test-type/proactive-ping/bi'
              + 'nd-oma-interface.'+"\n"
              + '10.Add configuration/sqa/tests/test/test-type/proactive-ping/s'
              + 'pecify-interface.'+"\n"
              + '11.Modify description for state/sqa/twamp-reflector-informatio'
              + 'ns/twamp-reflector-information/source-port.'
                ;
  }
  revision 2018-03-29 {
    description 'Change the configuration/sqa/twamp-reflectors/reflector/source'
              + '-port from mandatory to optional'
                ;
  }
  revision 2017-10-18 {
    description 'Modify default for configuration/sqa/twamp-reflectors/reflecto'
              + 'r/ageing-time'
                ;
  }
  revision 2017-09-05 {
    description 'Add configuration/sqa/tests/test/test-type/light-twamp/interva'
              + 'l-unit.'+"\n"
              + 'Add configuration/sqa/tests/test/test-type/light-twamp/statist'
              + 'ics-interval.'+"\n"
              + 'Add configuration/sqa/tests/test/test-type/light-twamp/timeout'
              + '.'+"\n"
              + 'Add feature interval-unit.'+"\n"
              + 'Add feature statistics-interval.'+"\n"
              + 'Add feature timeout.'
                ;
  }
  revision 2017-08-15 {
    description 'Add configuration/sqa/tests/test/test-type/proactive-ping.'+"\n"
              + 'Add configuration/sqa/tests/test/test-type/generalflow/member-'
              + 'port.'+"\n"
              + 'Add configuration/sqa/tests/test/test-type/light-twamp/reflect'
              + 'or-mode.'+"\n"
              + 'Add configuration/sqa/tests/test/test-type/light-twamp/timesta'
              + 'mp-format.'+"\n"
              + 'Add configuration/sqa/twamp-reflectors/twamp-reflector/timesta'
              + 'mp-format.'+"\n"
              + 'Add state/sqa/twamp-reflector-informations/twamp-reflector-inf'
              + 'ormation/timestamp-format.'+"\n"
              + 'Add feature timestamp-format.'+"\n"
              + 'Add feature reflector-mode.'
                ;
  }
  revision 2017-08-02 {
    description 'Add 59,89,5960,59-GM,89-GM,5960-GM label for policy-loop featu'
              + 're.'
                ;
  }
  revision 2017-07-07 {
    description '1 Obsolete detect-path node of general flow test.'+"\n"
              + '2 Obsolete vrf-name node of general flow test.'
                ;
  }
  revision 2017-06-14 {
    description '1 Feature policy-loop is available for 15K product.'+"\n"
              + '2 Feature thredelay-threshold is available for 15K product.'+"\n"
              + '3 Add container of configuration/sqa/tests/test/delay-threshol'
              + 'd, and add delay-threshold-value, delay-threshold-type to this'
              + ' container.'+"\n"
              + '4 Add container of configuration/sqa/tests/test/policy, and ad'
              + 'd loop-time node to this container.'
                ;
  }
  revision 2017-05-10 {
    description '1 Feature detect-path is available for 15K product'+"\n"
              + '2 Feature vrf-sqa is available for 15K product'
                ;
  }
  revision 2017-03-03 {
    description '1.Add configuration/sqa/tests/test/generalflow/generalflow/det'
              + 'ect-path.'+"\n"
              + '2.Add configuration/sqa/tests/test/generalflow/generalflow/vrf'
              + '-name.'
                ;
  }
  revision 2016-08-19 {
    description '1.Modify range for configuration/sqa/tests/test/test-type/gene'
              + 'ralflow/generalflow/delay/rate'+"\n"
              + '2.Modify range for configuration/sqa/tests/test/test-type/gene'
              + 'ralflow/generalflow/loss/duration'
                ;
  }
  revision 2016-07-04 {
    description '1.Add configuration/sqa/tests/test/generalflow/generalflow/sou'
              + 'rce-port.'+"\n"
              + '2.Add configuration/sqa/tests/test/generalflow/generalflow/des'
              + 'tination-port.'
                ;
  }
  revision 2016-02-27 {
    description '1.Add configuration/sqa/tests/test/light-twamp.'+"\n"
              + '2.Add configuration/sqa/twamp-reflectors.'+"\n"
              + '3.Add state/sqa/twamp-reflector-informations.'+"\n"
              + '4.Add lighttwamp-event notification.'
                ;
  }
  revision 2016-02-26 {
    description '1.Modify range for configuration/sqa/tests/test/test-type/gene'
              + 'ralflow/generalflow/throughput/one-or-two-rate/one-rate/one-ra'
              + 'te/rate.'
                ;
  }
  revision 2016-02-15 {
    description '1.Add Presence and OperationChangeType for configuration/sqa/t'
              + 'ests/test/test-type/generalflow/throughput.'+"\n"
              + '2.Add Presence and OperationChangeType for configuration/sqa/t'
              + 'ests/test/test-type/generalflow/loss.'+"\n"
              + '3.Add Presence and OperationChangeType for configuration/sqa/t'
              + 'ests/test/test-type/generalflow/delay.'
                ;
  }
  revision 2015-11-24 {
    description '1.Add throughput-event,loss-event,delay-event.'+"\n"
              + '2.Add configuration/sqa/tests/test/generalflow.'+"\n"
              + '3.Add state/sqa/reflector-information.'+"\n"
              + '4.Add configuration/sqa/reflector and configuration/sqa/reflec'
              + 'tor-free-arp.'+"\n"
              + '5.Modify import.'
                ;
  }
  revision 2015-08-20 {
    description 'Add icmp-event,udp-event,tcp-event,ftp-event,dns-event,udpjitt'
              + 'er-event,snmp-event,http-event,icmpjitter-event notification.'
                ;
  }
  revision 2015-08-03 {
    description '1.Add tos node for configuration/sqa/tests/test/test-type/udp.'
              + ''+"\n"
              + '2.Add tos node for configuration/sqa/tests/test/test-type/udpj'
              + 'itter.'
                ;
  }
  revision 2015-05-21 {
    description '1.Modify length for configuration/sqa/tests/test/test-number.'+"\n"
              + '2.Modify length for state/sqa/icmp-results/icmp-result/test-nu'
              + 'mber.'+"\n"
              + '3.Modify length for state/sqa/udp-results/udp-result/test-numb'
              + 'er.'+"\n"
              + '4.Modify length for state/sqa/tcp-results/tcp-result/test-numb'
              + 'er.'+"\n"
              + '5.Modify length for state/sqa/ftp-results/ftp-result/number.'+"\n"
              + '6.Modify length for state/sqa/dns-results/dns-result/test-numb'
              + 'er.'+"\n"
              + '7.Modify length for state/sqa/udpjitter-results/udpjitter-resu'
              + 'lt/test-number.'+"\n"
              + '8.Modify length for state/sqa/snmp-results/snmp-result/test-nu'
              + 'mber.'+"\n"
              + '9.Modify length for state/sqa/http-results/http-result/test-nu'
              + 'mber.'+"\n"
              + '10.Modify length for state/sqa/icmpjitter-results/icmpjitter-r'
              + 'esult/test-number.'+"\n"
              + '11.Modify length for operation/sqa/test-operations/test-operat'
              + 'ion/test-number.'+"\n"
              + '12.Delete Max-elements for configuration/sqa/tests/test.'
                ;
  }
  revision 2015-02-26 {
    description '1.Add destination-url node for state/sqa/dns-results/dns-resul'
              + 't.'+"\n"
              + '2.Add length and modify basetype for configuration/sqa/tests/t'
              + 'est/udp/size.'+"\n"
              + '3.Add length for modify basetype for configuration/sqa/tests/t'
              + 'est/dns/repeat.'
                ;
  }
  revision 2014-12-16 {
    description 'Move vrf-name node and source-ip node from vrf container and s'
              + 'ource-ip container to another container:'+"\n"
              + '1.Move vrf-name node and source-ip node from vrf container and'
              + ' source-ip container to ICMP container.'+"\n"
              + '2.Move vrf-name node from vrf container to UDP container.'+"\n"
              + '3.Move vrf-name node from vrf container to TCP container.'+"\n"
              + '4.Move vrf-name node from vrf container to FTP container.'+"\n"
              + '5.Move vrf-name node from vrf container to DNS container.'+"\n"
              + '6.Move vrf-name node from vrf container to UDPjitter container'
              + '.'+"\n"
              + '7.Move vrf-name node from vrf container to SNMP container.'+"\n"
              + '8.Move vrf-name node from vrf container to HTTP container.'+"\n"
              + '9.Move vrf-name node and source-ip node from vrf container and'
              + ' source-ip container to ICMPjitter container.'
                ;
  }
  revision 2014-07-14 {
    description 'Add length for some nodes.'+"\n"
              + '1.Add length for state/sqa/icmp-results/icmp-result/repeat-cou'
              + 'nt and response-count and pkt-loss-rate and probe-time.'+"\n"
              + '2.Add length for state/sqa/udp-results/udp-result/repeat-count'
              + ' and response-count and pkt-loss-rate and probe-time.'+"\n"
              + '3.Add length for state/sqa/tcp-results/tcp-result/repeat-count'
              + ' and response-count and probe-time.'+"\n"
              + '4.Add length for state/sqa/ftp-results/ftp-result/probe-time.'+"\n"
              + '5.Add length for state/sqa/dns-results/dns-result/repeat-count'
              + ' and response-count and probe-time.'+"\n"
              + '6.Add length for state/sqa/udpjitter-results/udpjitter-result/'
              + 'repeat-count and response-count and probe-time.'+"\n"
              + '7.Add length for state/sqa/snmp-results/snmp-result/probe-time'
              + '.'+"\n"
              + '8.Add length for state/sqa/http-results/http-result/repeat-cou'
              + 'nt and response-count and probe-time.'+"\n"
              + '9.Add length for state/sqa/icmpjitter-results/icmpjitter-resul'
              + 't/repeat-count and response-count and probe-time.'
                ;
  }
  revision 2014-04-23 {
    description "Delete the patterns of icmp's source-ip node."
                ;
  }
  revision 2013-11-23 {
    description 'Initial version.'
                ;
  }
  feature generalflow-port {
    description 'Generalflow test source or destination port config.'
                ;
  }
  feature detect-path {
    description 'Detect path type,including down and up(default:up).'
                ;
  }
  feature vrf-sqa {
    description 'Support the SQA for the VPN of layer3.'
                ;
  }
  feature policy-loop {
    description 'Support the cycle testing policy.'
                ;
  }
  feature delay-threshold {
    description 'Delay-threshold config.'
                ;
  }
  feature timestamp-format {
    description 'Timestamp format,including PTP and NTP(default:PTP).'
                ;
  }
  feature reflector-mode {
    description 'Reflector mode,including standard mode and loopback mode(defau'
              + 'lt:standard mode).'
                ;
  }
  feature interval-unit-us {
    description 'Interval unit,including 100millisecond and 100microsecond(defa'
              + 'ult:100millisecond).'
                ;
  }
  feature statistics-interval {
    description 'The value of statistics interval,ranges from 5s to 60s(default'
              + ':15s).'
                ;
  }
  feature timeout {
    description 'The value of timeout,ranges from 1s to 10s(default:5s).'
                ;
  }
  feature interval-unit {
    description 'Interval unit.'
                ;
  }
  feature packet-matching-mode {
    description 'Packet matching mode.'
                ;
  }
  feature specify-interface {
    description 'Specify interface.'
                ;
  }
  feature bind-oma-interface {
    description 'Bind OMA interface.'
                ;
  }
  feature performance-statistics {
    description 'performance statistics.'
                ;
  }
  feature vrf-name {
    description 'The VRF name.'
                ;
  }
  feature ipv6-address {
    description 'The ipv6 address.'
                ;
  }
  feature nd-na-status {
    description 'The status of ND NA,including enable and disable(default:disab'
              + 'le).'
                ;
  }
  feature nd-na-interval {
    description 'The interval of ND NA,ranges from 1s to 14400s(default:30s).'
                ;
  }
  feature delay-statistics-mode {
    description 'The delay statistics mode,including bidirection,unidirection a'
              + 'nd both(default:both).'
                ;
  }
  feature pattern {
    description 'The TLV value of proactive-ping function,from <0-9>,<a-f>or<A-'
              + 'F>.'
                ;
  }
  feature policy-frequency {
    description 'Support the cycle frequency testing policy.'
                ;
  }
  feature sr-policy {
    description 'SR policy support.'
                ;
  }
  feature delay-mode {
    description 'delay mode'
                ;
  }
  container configuration {
    description 'Configuration model info.'
                ;
    container sqa {
      description 'SQA instances configuration.'
                  ;
      container tests {
        description 'Configure SQA test info.'
                    ;
        list test {
          description 'Configure SQA test info.'
                      ;
          key test-number ;
          leaf test-number {
            description 'The configration of test number,the upper limit of thi'
                      + 's parameter depend on the device.'
                        ;
            type uint32 {
              range 1..1024 {
                description 'The test number ranges from 1 to 1024.'
                            ;
              }
            }
          }
          choice test-type {
            description 'Configure SQA test type.'
                        ;
            mandatory true ;
            case icmp {
              description 'Configure ICMP test parameters.'
                          ;
              container icmp {
                description 'Configure ICMP test parameters.'
                            ;
                leaf vrf-name {
                  description 'The name of VRF,this string length ranges from 1'
                            + ' to 32.'
                              ;
                  type string {
                    length 1..32 {
                      description 'This string length ranges from 1 to 32.'
                                  ;
                    }
                  }
                }
                choice ip-addr-family {
                  description 'Choose one from IPv4 and IPv6.'
                              ;
                  mandatory true ;
                  case ipv4 {
                    description 'Type is IPv4.'
                                ;
                    leaf destination-ip {
                      description 'The destination IPv4 address.'
                                  ;
                      type ncd:ipv4-address ;
                      mandatory true ;
                    }
                    leaf source-ip {
                      description 'The source IPv4 address.'
                                  ;
                      type ncd:ipv4-address ;
                    }
                    leaf size {
                      description 'The size of ICMP packet,ranges from 36bytes '
                                + 'to 8192bytes(default:36bytes).'
                                  ;
                      type uint16 {
                        range 36..8192 {
                          description 'This parameter ranges from 36 to 8192(de'
                                    + 'fault:36).'
                                      ;
                        }
                      }
                      units byte ;
                      default 36 ;
                    }
                  }
                  case ipv6 {
                    description 'Type is IPv6.'
                                ;
                    leaf destination-ipv6 {
                      description 'The destination IPv6 address.'
                                  ;
                      type ncd:ipv6-address ;
                      mandatory true ;
                    }
                    leaf source-ipv6 {
                      description 'The source IPv6 address.'
                                  ;
                      type ncd:ipv6-address ;
                    }
                    leaf size-ipv6 {
                      description 'The size of ICMPv6 packet,ranges from 64byte'
                                + 's to 8192bytes(default:64bytes).'
                                  ;
                      type uint16 {
                        range 64..8192 {
                          description 'This parameter ranges from 64 to 8192(de'
                                    + 'fault:64).'
                                      ;
                        }
                      }
                      units byte ;
                      default 64 ;
                      ncd:revise-date 2020-08-11 ;
                    }
                    ncd:revise-date 2020-02-18 ;
                  }
                }
                leaf repeat {
                  description 'The number of repeat,ranges from 1 to 65535(defa'
                            + 'ult:1).'
                              ;
                  type uint16 {
                    range 1..65535 {
                      description 'This parameter ranges from 1 to 65535(defaul'
                                + 't:1).'
                                  ;
                    }
                  }
                  default 1 ;
                }
                leaf interval {
                  description 'The sending period of icmp packets,ranges from 5'
                            + '0ms to 65535ms(default:100ms).'
                              ;
                  type uint16 {
                    range 50..65535 {
                      description 'This parameter ranges from 50 to 65535(defau'
                                + 'lt:100).'
                                  ;
                    }
                  }
                  units ms ;
                  default 100 ;
                }
                leaf ttl {
                  description 'The TTL value in ICMP packets,ranges from 1 to 2'
                            + '55(default:255).'
                              ;
                  type uint8 {
                    range 1..255 {
                      description 'This parameter ranges from 1 to 255(default:'
                                + '255).'
                                  ;
                    }
                  }
                  default 255 ;
                }
                choice tos-or-dscp {
                  description 'Choose one from TOS and DSCP.'
                              ;
                  default tos ;
                  case tos {
                    description 'TOS configuration.'
                                ;
                    container tos {
                      description 'TOS configuration.'
                                  ;
                      leaf tos {
                        description 'The TOS value in ICMP packets,ranges from '
                                  + '0 to 255(default:0).'
                                    ;
                        type uint16 {
                          range 0..255 {
                            description 'This parameter ranges from 0 to 255(default:0).'
                                        ;
                          }
                        }
                        default 0 ;
                      }
                    }
                  }
                  case dscp {
                    description 'DSCP configuration.'
                                ;
                    container dscp {
                      description 'DSCP configuration.'
                                  ;
                      leaf dscp {
                        description 'The DSCP value,ranges from 0 to 63.'
                                    ;
                        type uint8 {
                          range 0..63 {
                            description 'This parameter ranges from 0 to 63.'
                                        ;
                          }
                        }
                        default 0 ;
                      }
                    }
                  }
                }
              }
            }
            case udp {
              description 'Configure UDP test parameters.'
                          ;
              container udp {
                description 'Configure UDP test parameters.'
                            ;
                leaf vrf-name {
                  description 'The name of VRF,this string length ranges from 1'
                            + ' to 32.'
                              ;
                  type string {
                    length 1..32 {
                      description 'This string length ranges from 1 to 32.'
                                  ;
                    }
                  }
                }
                choice ip-addr-family {
                  description 'Choose one from IPv4 and IPv6.'
                              ;
                  mandatory true ;
                  case ipv4 {
                    description 'Type is IPv4.'
                                ;
                    leaf destination-ip {
                      description 'The destination IPv4 address.'
                                  ;
                      type ncd:ipv4-address ;
                      mandatory true ;
                    }
                  }
                  case ipv6 {
                    description 'Type is IPv6.'
                                ;
                    leaf destination-ipv6 {
                      description 'The destination IPv6 address.'
                                  ;
                      type ncd:ipv6-address ;
                      mandatory true ;
                    }
                    ncd:revise-date 2020-02-18 ;
                  }
                }
                leaf destination-port {
                  description 'The destination port number,ranges from 1025 to '
                            + '65535.'
                              ;
                  type uint16 {
                    range 1025..65535 {
                      description 'This parameter ranges from 1025 to 65535.'
                                  ;
                    }
                  }
                  mandatory true ;
                }
                leaf interval {
                  description 'The sending period of udp packets,ranges from 50'
                            + 'ms to 2000ms(default:100ms).'
                              ;
                  type uint16 {
                    range 50..2000 {
                      description 'This parameter ranges from 50 to 2000(defaul'
                                + 't:100).'
                                  ;
                    }
                  }
                  units ms ;
                  default 100 ;
                }
                leaf repeat {
                  description 'The number of repeat,ranges from 1 to 1000(defau'
                            + 'lt:1).'
                              ;
                  type uint16 {
                    range 1..1000 {
                      description 'This parameter ranges from 1 to 1000(default'
                                + ':1).'
                                  ;
                    }
                  }
                  default 1 ;
                }
                leaf size {
                  description 'The size of UDP packet,ranges from 50bytes to 15'
                            + '00bytes(default:50bytes).'
                              ;
                  type uint16 {
                    range 50..1500 {
                      description 'This parameter ranges from 50 to 1500(defaul'
                                + 't:50).'
                                  ;
                    }
                  }
                  units byte ;
                  default 50 ;
                }
                leaf tos {
                  description 'The TOS value in UDP packets,ranges from 0 to 25'
                            + '5(default:0).'
                              ;
                  type uint16 {
                    range 0..255 {
                      description 'This parameter ranges from 0 to 255(default:'
                                + '0).'
                                  ;
                    }
                  }
                  default 0 ;
                  ncd:revise-date 2015-08-03 ;
                }
              }
            }
            case tcp {
              description 'Configure TCP test parameters.'
                          ;
              container tcp {
                description 'Configure TCP test parameters.'
                            ;
                leaf vrf-name {
                  description 'The name of VRF,this string length ranges from 1'
                            + ' to 32.'
                              ;
                  type string {
                    length 1..32 {
                      description 'This string length ranges from 1 to 32.'
                                  ;
                    }
                  }
                }
                choice ip-addr-family {
                  description 'Choose one from IPv4 and IPv6.'
                              ;
                  mandatory true ;
                  case ipv4 {
                    description 'Type is IPv4.'
                                ;
                    leaf destination-ip {
                      description 'The destination IPv4 address.'
                                  ;
                      type ncd:ipv4-address ;
                      mandatory true ;
                    }
                  }
                  case ipv6 {
                    description 'Type is IPv6.'
                                ;
                    leaf destination-ipv6 {
                      description 'The destination IPv6 address.'
                                  ;
                      type ncd:ipv6-address ;
                      mandatory true ;
                    }
                    ncd:revise-date 2020-02-18 ;
                  }
                }
                leaf destination-port {
                  description 'The destination port number,ranges from 1025 to '
                            + '65535.'
                              ;
                  type uint16 {
                    range 1025..65535 {
                      description 'This parameter ranges from 1025 to 65535.'
                                  ;
                    }
                  }
                  mandatory true ;
                }
                leaf interval {
                  description 'The sending period of establishing TCP link,rang'
                            + 'es from 1000ms to 4000ms(default:1000ms).'
                              ;
                  type uint16 {
                    range 1000..4000 {
                      description 'This parameter ranges from 1000 to 4000(defa'
                                + 'ult:1000).'
                                  ;
                    }
                  }
                  units ms ;
                  default 1000 ;
                }
                leaf repeat {
                  description 'The number of repeat,ranges from 1 to 200(defaul'
                            + 't:1).'
                              ;
                  type uint16 {
                    range 1..200 {
                      description 'This parameter ranges from 1 to 200(default:'
                                + '1).'
                                  ;
                    }
                  }
                  default 1 ;
                }
              }
            }
            case ftp {
              description 'Configure FTP test parameters.'
                          ;
              container ftp {
                description 'Configure FTP test parameters.'
                            ;
                leaf vrf-name {
                  description 'The name of VRF,this string length ranges from 1'
                            + ' to 32.'
                              ;
                  type string {
                    length 1..32 {
                      description 'This string length ranges from 1 to 32.'
                                  ;
                    }
                  }
                }
                leaf destination-ip {
                  description 'The IP address of FTP server.'
                              ;
                  type ncd:ipv4-address ;
                  mandatory true ;
                }
                leaf filename {
                  description 'The source file name,this string length ranges f'
                            + 'rom 1 to 79.'
                              ;
                  type string {
                    length 1..79 {
                      description 'This string length ranges from 1 to 79.'
                                  ;
                    }
                  }
                  mandatory true ;
                }
                leaf root {
                  description 'The target path and file name,this string length'
                            + ' ranges from 1 to 151.'
                              ;
                  type string {
                    length 1..151 {
                      description 'This string length ranges from 1 to 151.'
                                  ;
                    }
                  }
                  mandatory true ;
                }
                leaf destination-port {
                  description 'The destination port number,ranges from 1 to 655'
                            + '35(default:21).'
                              ;
                  type uint16 {
                    range 1..65535 {
                      description 'This parameter ranges from 1 to 65535(defaul'
                                + 't:21).'
                                  ;
                    }
                  }
                  default 21 ;
                }
                leaf username {
                  description 'Configure the username of connecting to FTP serv'
                            + 'er,this string length ranges from 1 to 31.'
                              ;
                  type string {
                    length 1..31 {
                      description 'This string length ranges from 1 to 31.'
                                  ;
                    }
                  }
                  mandatory true ;
                }
                choice encrypted-or-not-encrypted {
                  description 'Choose one from password and encrypted password.'
                              ;
                  mandatory true ;
                  case password {
                    description 'Configure the password of connecting to FTP se'
                              + 'rver.'
                                ;
                    container password {
                      description 'Configure the password of connecting to FTP '
                                + 'server.'
                                  ;
                      leaf password {
                        description 'Configure the password of connecting to FT'
                                  + 'P server,this string length ranges from 1 '
                                  + 'to 63.'
                                    ;
                        type string {
                          length 1..63 {
                            description 'This string length ranges from 1 to 63.'
                                        ;
                          }
                        }
                        mandatory true ;
                      }
                    }
                  }
                  case encrypted-password {
                    description 'Configure the encrypted password of connecting'
                              + ' to FTP server.'
                                ;
                    container encrypted-password {
                      description 'Configure the encrypted password of connecti'
                                + 'ng to FTP server.'
                                  ;
                      leaf encrypted-password {
                        description 'Configure the encrypted password of connec'
                                  + 'ting to FTP server,this string length rang'
                                  + 'es from 1 to 128.'
                                    ;
                        type string {
                          length 1..128 {
                            description 'This string length ranges from 1 to 128.'
                                        ;
                          }
                        }
                        mandatory true ;
                      }
                    }
                  }
                }
              }
            }
            case dns {
              description 'Configure DNS test parameters.'
                          ;
              container dns {
                description 'Configure DNS test parameters.'
                            ;
                leaf vrf-name {
                  description 'The name of VRF,this string length ranges from 1'
                            + ' to 32.'
                              ;
                  type string {
                    length 1..32 {
                      description 'This string length ranges from 1 to 32.'
                                  ;
                    }
                  }
                }
                leaf destination-url {
                  description 'Configure the domain name to be resolved,this st'
                            + 'ring length ranges from 1 to 128.'
                              ;
                  type string {
                    length 1..128 {
                      description 'This string length ranges from 1 to 128.'
                                  ;
                    }
                  }
                  mandatory true ;
                }
                leaf server-ip {
                  description 'The IP address of domain name server.'
                              ;
                  type ncd:ipv4-address ;
                  mandatory true ;
                }
                leaf repeat {
                  description 'The number of repeat,ranges from 1 to 10(default'
                            + ':1).'
                              ;
                  type uint16 {
                    range 1..10 {
                      description 'This parameter ranges from 1 to 10(default:1'
                                + ').'
                                  ;
                    }
                  }
                  default 1 ;
                }
              }
            }
            case udpjitter {
              description 'Configure udpjitter test parameters.'
                          ;
              container udpjitter {
                description 'Configure udpjitter test parameters.'
                            ;
                leaf vrf-name {
                  description 'The name of VRF,this string length ranges from 1'
                            + ' to 32.'
                              ;
                  type string {
                    length 1..32 {
                      description 'This string length ranges from 1 to 32.'
                                  ;
                    }
                  }
                }
                choice ip-addr-family {
                  description 'Choose one from IPv4 and IPv6.'
                              ;
                  mandatory true ;
                  case ipv4 {
                    description 'Type is IPv4.'
                                ;
                    leaf destination-ip {
                      description 'The destination IPv4 address.'
                                  ;
                      type ncd:ipv4-address ;
                      mandatory true ;
                    }
                  }
                  case ipv6 {
                    description 'Type is IPv6.'
                                ;
                    leaf destination-ipv6 {
                      description 'The destination IPv6 address.'
                                  ;
                      type ncd:ipv6-address ;
                      mandatory true ;
                    }
                    ncd:revise-date 2020-02-18 ;
                  }
                }
                leaf destination-port {
                  description 'The destination port number,ranges from 1025 to '
                            + '65535.'
                              ;
                  type uint16 {
                    range 1025..65535 {
                      description 'This parameter ranges from 1025 to 65535.'
                                  ;
                    }
                  }
                  mandatory true ;
                }
                leaf interval {
                  description 'The sending period of UDP packets,ranges from 50'
                            + 'ms to 2000ms(default:100ms).'
                              ;
                  type uint16 {
                    range 50..2000 {
                      description 'This parameter ranges from 50 to 2000(defaul'
                                + 't:100).'
                                  ;
                    }
                  }
                  units ms ;
                  default 100 ;
                }
                leaf repeat {
                  description 'The number of repeat,ranges from 1 to 1000(defau'
                            + 'lt:1).'
                              ;
                  type uint16 {
                    range 1..1000 {
                      description 'This parameter ranges from 1 to 1000(default'
                                + ':1).'
                                  ;
                    }
                  }
                  default 1 ;
                }
                leaf size {
                  description 'The size of UDP packet,ranges from 50bytes to 15'
                            + '00bytes(default:50bytes).'
                              ;
                  type uint16 {
                    range 50..1500 {
                      description 'This parameter ranges from 50 to 1500(defaul'
                                + 't:50).'
                                  ;
                    }
                  }
                  units byte ;
                  default 50 ;
                }
                leaf tos {
                  description 'The TOS value in UDP packets,ranges from 0 to 25'
                            + '5(default:0).'
                              ;
                  type uint16 {
                    range 0..255 {
                      description 'This parameter ranges from 0 to 255(default:'
                                + '0).'
                                  ;
                    }
                  }
                  default 0 ;
                  ncd:revise-date 2015-08-03 ;
                }
              }
            }
            case snmp {
              description 'Configure SNMP test parameters.'
                          ;
              container snmp {
                description 'Configure SNMP test parameters.'
                            ;
                leaf vrf-name {
                  description 'The name of VRF,this string length ranges from 1'
                            + ' to 32.'
                              ;
                  type string {
                    length 1..32 {
                      description 'This string length ranges from 1 to 32.'
                                  ;
                    }
                  }
                }
                leaf destination-ip {
                  description 'The destination IP address.'
                              ;
                  type ncd:ipv4-address ;
                  mandatory true ;
                }
                leaf destination-port {
                  description 'The destination port number,ranges from 1024 to '
                            + '20000,or 161(default:161).'
                              ;
                  type uint16 {
                    range '161 | 1024..20000'
                          {
                      description 'This parameter ranges from 1024 to 20000,or '
                                + '161(default:161).'
                                  ;
                    }
                  }
                  default 161 ;
                }
                choice encrypted-or-not-encrypted {
                  description 'Choose one from community and encrypted communit'
                            + 'y.'
                              ;
                  case community {
                    description 'The community in SNMP packet.'
                                ;
                    container community {
                      description 'The community in SNMP packet.'
                                  ;
                      leaf community {
                        description 'The community in SNMP packet,this string l'
                                  + 'ength ranges from 1 to 32.'
                                    ;
                        type string {
                          length 1..32 {
                            description 'This string length ranges from 1 to 32.'
                                        ;
                          }
                        }
                        mandatory true ;
                      }
                    }
                  }
                  case encrypted-community {
                    description 'The encrypted community in SNMP packet.'
                                ;
                    container encrypted-community {
                      description 'The encrypted community in SNMP packet.'
                                  ;
                      leaf encrypted-community {
                        description 'The encrypted community in SNMP packett,th'
                                  + 'is string length ranges from 1 to 108.'
                                    ;
                        type string {
                          length 1..108 {
                            description 'This string length ranges from 1 to 108.'
                                        ;
                          }
                        }
                        mandatory true ;
                      }
                    }
                  }
                }
              }
            }
            case http {
              description 'Configure HTTP test parameters.'
                          ;
              container http {
                description 'Configure HTTP test parameters.'
                            ;
                leaf vrf-name {
                  description 'The name of VRF,this string length ranges from 1'
                            + ' to 32.'
                              ;
                  type string {
                    length 1..32 {
                      description 'This string length ranges from 1 to 32.'
                                  ;
                    }
                  }
                }
                choice url-or-ip {
                  description 'Choose one from destination url and destination '
                            + 'IP address.'
                              ;
                  mandatory true ;
                  case destination-url {
                    description 'Configure the destination url and the IP addre'
                              + 'ss of DNS.'
                                ;
                    container url {
                      description 'Configure the destination url and the IP add'
                                + 'ress of DNS.'
                                  ;
                      leaf url {
                        description 'The destination domain name,this string le'
                                  + 'ngth ranges from 1 to 128.'
                                    ;
                        type string {
                          length 1..128 {
                            description 'This string length ranges from 1 to 128.'
                                        ;
                          }
                        }
                        mandatory true ;
                      }
                      leaf dns-ip {
                        description 'The IP address of domain name server.'
                                    ;
                        type ncd:ipv4-address ;
                        mandatory true ;
                      }
                    }
                  }
                  case destination-ip {
                    description 'Configure the destination IP address.'
                                ;
                    container ip {
                      description 'Configure the destination IP address.'
                                  ;
                      leaf ip {
                        description 'The destination IP address.'
                                    ;
                        type ncd:ipv4-address ;
                        mandatory true ;
                      }
                    }
                  }
                }
                leaf repeat {
                  description 'The number of repeat,ranges from 1 to 10(default'
                            + ':1).'
                              ;
                  type uint16 {
                    range 1..10 {
                      description 'This parameter ranges from 1 to 10(default:1'
                                + ').'
                                  ;
                    }
                  }
                  default 1 ;
                }
              }
            }
            case icmpjitter {
              description 'Configure icmpjitter test parameters.'
                          ;
              container icmpjitter {
                description 'Configure icmpjitter test parameters.'
                            ;
                leaf vrf-name {
                  description 'The name of VRF,this string length ranges from 1'
                            + ' to 32.'
                              ;
                  type string {
                    length 1..32 {
                      description 'This string length ranges from 1 to 32.'
                                  ;
                    }
                  }
                }
                choice ip-addr-family {
                  description 'Choose one from IPv4 and IPv6.'
                              ;
                  case ipv4 {
                    description 'Type is IPv4.'
                                ;
                    leaf destination-ip {
                      description 'The destination IPv4 address.'
                                  ;
                      type ncd:ipv4-address ;
                      mandatory true ;
                    }
                    leaf source-ip {
                      description 'The Source IPv4 address.'
                                  ;
                      type ncd:ipv4-address ;
                    }
                    leaf size {
                      description 'The size of ICMP packet,ranges from 40bytes '
                                + 'to 8192bytes(default:40bytes).'
                                  ;
                      type uint16 {
                        range 40..8192 {
                          description 'This parameter ranges from 40 to 8192(de'
                                    + 'fault:40).'
                                      ;
                        }
                      }
                      units byte ;
                      default 40 ;
                    }
                  }
                  case ipv6 {
                    description 'Type is IPv6.'
                                ;
                    leaf destination-ipv6 {
                      description 'The destination IPv6 address.'
                                  ;
                      type ncd:ipv6-address-none-zero ;
                      mandatory true ;
                    }
                    leaf source-ipv6 {
                      description 'The source IPv6 address.'
                                  ;
                      type ncd:ipv6-address-none-zero ;
                    }
                    leaf size-ipv6 {
                      description 'The size of ICMPv6 packet,ranges from 64byte'
                                + 's to 8192bytes(default:64bytes).'
                                  ;
                      type uint16 {
                        range 64..8192 {
                          description 'This parameter ranges from 64 to 8192(de'
                                    + 'fault:64).'
                                      ;
                        }
                      }
                      units byte ;
                      default 64 ;
                    }
                    ncd:revise-date 2020-08-11 ;
                  }
                }
                leaf repeat {
                  description 'The number of repeat,ranges from 1 to 65535(defa'
                            + 'ult:1).'
                              ;
                  type uint16 {
                    range 1..65535 {
                      description 'This parameter ranges from 1 to 65535(defaul'
                                + 't:1).'
                                  ;
                    }
                  }
                  default 1 ;
                }
                leaf interval {
                  description 'The sending period of icmp packets,ranges from 5'
                            + '0ms to 65535ms(default:100ms).'
                              ;
                  type uint16 {
                    range 50..65535 {
                      description 'This parameter ranges from 50 to 65535(defau'
                                + 'lt:100).'
                                  ;
                    }
                  }
                  units ms ;
                  default 100 ;
                }
                leaf ttl {
                  description 'The TTL value in ICMP packets,ranges from 1 to 2'
                            + '55(default:255).'
                              ;
                  type uint8 {
                    range 1..255 {
                      description 'This parameter ranges from 1 to 255(default:'
                                + '255).'
                                  ;
                    }
                  }
                  default 255 ;
                }
                choice tos-or-dscp {
                  description 'Choose one from TOS and DSCP.'
                              ;
                  default tos ;
                  case tos {
                    description 'TOS configuration.'
                                ;
                    container tos {
                      description 'TOS configuration.'
                                  ;
                      leaf tos {
                        description 'The TOS value in ICMP packets,ranges from '
                                  + '0 to 255(default:0).'
                                    ;
                        type uint16 {
                          range 0..255 {
                            description 'This parameter ranges from 0 to 255(default:0).'
                                        ;
                          }
                        }
                        default 0 ;
                      }
                    }
                  }
                  case dscp {
                    description 'DSCP configuration.'
                                ;
                    container dscp {
                      description 'DSCP configuration.'
                                  ;
                      leaf dscp {
                        description 'The DSCP value,choose one from TOS and DSC'
                                  + 'P,ranges from 0 to 63.'
                                    ;
                        type uint8 {
                          range 0..63 {
                            description 'This parameter ranges from 0 to 63.'
                                        ;
                          }
                        }
                        default 0 ;
                      }
                    }
                  }
                }
              }
            }
            case generalflow {
              description 'Configure generalflow test parameters.'
                          ;
              container generalflow {
                description 'Configure generalflow test parameters.'
                            ;
                leaf reflector-mode {
                  description 'Reflector mode,including L2 mode,L3 mode and def'
                            + 'ault mode(default:default mode).'
                              ;
                  type enumeration {
                    enum l2 {
                      value 2 ;
                      description 'The reflector mode is L2.'
                                  ;
                    }
                    enum l3 {
                      value 3 ;
                      description 'The reflector mode is L3.'
                                  ;
                    }
                    enum default {
                      value 5 ;
                      description 'The reflector mode is default.'
                                  ;
                    }
                  }
                  default default ;
                }
                leaf client-mode {
                  description 'Client mode, including L2 UNI mode,L3 UNI mode a'
                            + 'nd L2 bridge UNI mode.'
                              ;
                  type enumeration {
                    enum l2-uni {
                      value 1 ;
                      description 'The client mode is L2 UNI.'
                                  ;
                    }
                    enum l3-uni {
                      value 2 ;
                      description 'The client mode is L3 UNI.'
                                  ;
                    }
                    enum l2-bridge-uni {
                      value 3 ;
                      description 'The client mode is L2 bridge UNI.'
                                  ;
                    }
                  }
                }
                leaf test-mode {
                  description 'Test mode,including online and offline.'
                              ;
                  type enumeration {
                    enum online {
                      value 1 ;
                      description 'The mode is online.'
                                  ;
                    }
                    enum offline {
                      value 2 ;
                      description 'The mode is offline.'
                                  ;
                    }
                  }
                }
                leaf detect-path {
                  if-feature detect-path ;
                  status obsolete {
                    ncd:revise-date 2017-07-07 ;
                  }
                  description 'Detect path type,including down and up(default:u'
                            + 'p).'
                              ;
                  type enumeration {
                    enum down {
                      value 1 ;
                      description 'Down detect.'
                                  ;
                    }
                    enum up {
                      value 2 ;
                      description 'Up detect.'
                                  ;
                    }
                  }
                  default up ;
                  ncd:revise-date 2017-03-03 ;
                }
                leaf inbound-interface {
                  description 'Interface name.'
                              ;
                  type ncd:ifname {
                    length 1..31 {
                      description 'The range of interface name length.'
                                  ;
                    }
                  }
                }
                leaf member-port {
                  description 'Member port name.'
                              ;
                  type ncd:ifname ;
                  ncd:revise-date 2017-08-15 ;
                }
                leaf interface-mode {
                  description 'Interface mode,including share mode,exclusive mo'
                            + 'de(default:share mode).'
                              ;
                  type enumeration {
                    enum share {
                      value 1 ;
                      description 'The interface mode is share mode.'
                                  ;
                    }
                    enum exclusive {
                      value 2 ;
                      description 'The interface mode is exclusive mode.'
                                  ;
                    }
                  }
                  default share ;
                }
                choice ipv4-or-ipv6 {
                  description 'Choose one from ipv4 and ipv6.'
                              ;
                  case ipv4 {
                    description 'Type is ipv4.'
                                ;
                    leaf source-ip {
                      description 'The source IPv4 address.'
                                  ;
                      type ncd:ipv4-address-none-zero ;
                    }
                    leaf destination-ip {
                      description 'The destination IPv4 address.'
                                  ;
                      type ncd:ipv4-address-none-zero ;
                    }
                  }
                  case ipv6 {
                    description 'Type is ipv6.'
                                ;
                    leaf source-ipv6 {
                      if-feature ipv6-address ;
                      description 'The source ipv6 address.'
                                  ;
                      type ncd:ipv6-address ;
                    }
                    leaf destination-ipv6 {
                      if-feature ipv6-address ;
                      description 'The destination ipv6 address.'
                                  ;
                      type ncd:ipv6-address ;
                    }
                    ncd:revise-date 2019-04-30 ;
                  }
                }
                leaf source-mac {
                  description 'The source MAC address.'
                              ;
                  type ncd:mac-address-none-zero ;
                }
                leaf source-port {
                  if-feature generalflow-port ;
                  description 'The source port,ranges from 1025 to 65535(defaul'
                            + 't:49184).'
                              ;
                  type uint16 {
                    range 1025..65535 {
                      description 'The range of port number.'
                                  ;
                    }
                  }
                  default 49184 ;
                  ncd:revise-date 2016-07-04 ;
                }
                leaf destination-mac {
                  description 'The destination MAC address.'
                              ;
                  type ncd:mac-address-none-zero ;
                }
                leaf destination-port {
                  if-feature generalflow-port ;
                  description 'The destination port,ranges from 1025 to 65535(d'
                            + 'efault:7).'
                              ;
                  type uint16 {
                    range '7 | 1025..65535'
                          {
                      description 'The range of port number.'
                                  ;
                    }
                  }
                  default 7 ;
                  ncd:revise-date 2016-07-04 ;
                }
                leaf vrf-name {
                  if-feature vrf-sqa ;
                  status obsolete {
                    ncd:revise-date 2017-07-07 ;
                  }
                  description 'The VRF name,the length of this string is from 1'
                            + ' to 32.'
                              ;
                  type string {
                    length 1..32 {
                      description 'The length of this string is from 1 to 32.'
                                  ;
                    }
                  }
                  ncd:revise-date 2017-03-03 ;
                }
                choice vlan-or-qinq {
                  description 'Choose one from vlan and qinq.'
                              ;
                  case vlan {
                    description 'Vlan information.'
                                ;
                    container vlan {
                      description 'Vlan information.'
                                  ;
                      presence 'vlan ID'
                               ;
                      leaf id {
                        description 'The value of vlan ID,ranges from 1 to 4094.'
                                    ;
                        type uint16 {
                          range 1..4094 {
                            description 'The range of vlan ID.'
                                        ;
                          }
                        }
                        mandatory true ;
                      }
                    }
                  }
                  case qinq {
                    description 'Qinq information.'
                                ;
                    container qinq {
                      description 'Qinq information.'
                                  ;
                      presence qinq ;
                      leaf internal-vlan-id {
                        description 'The value of internal vlan ID,ranges from '
                                  + '1 to 4094.'
                                    ;
                        type uint16 {
                          range 1..4094 {
                            description 'The range of vlan ID.'
                                        ;
                          }
                        }
                        mandatory true ;
                      }
                      leaf external-vlan-id {
                        description 'The value of external vlan ID,ranges from '
                                  + '1 to 4094.'
                                    ;
                        type uint16 {
                          range 1..4094 {
                            description 'The range of vlan ID.'
                                        ;
                          }
                        }
                        mandatory true ;
                      }
                    }
                  }
                }
                leaf priority-8021p {
                  description 'The value of priority-8021p,ranges from 0 to 7(d'
                            + 'efault:0).'
                              ;
                  type uint8 {
                    range 0..7 {
                      description 'The range of priority-8021p(default:0).'
                                  ;
                    }
                  }
                  default 0 ;
                }
                leaf dscp {
                  description 'The value of DSCP,ranges from 0 to 63(default:0).'
                              ;
                  type uint8 {
                    range 0..63 {
                      description 'The range of DSCP(default:0).'
                                  ;
                    }
                  }
                  default 0 ;
                }
                leaf free-arp-status {
                  description 'The status of free ARP,including enable and disa'
                            + 'ble(default:disable).'
                              ;
                  type enumeration {
                    enum disable {
                      value 0 ;
                      description 'The status of free-arp is disable.'
                                  ;
                    }
                    enum enable {
                      value 1 ;
                      description 'The status of free-arp is enable.'
                                  ;
                    }
                  }
                  default disable ;
                }
                leaf free-arp-interval {
                  description 'The interval of free ARP,ranges from 1s to 14400'
                            + 's(default:30s).'
                              ;
                  type uint32 {
                    range 1..14400 {
                      description 'The range of free-arp interval(default:30s).'
                                  ;
                    }
                  }
                  units s ;
                  default 30 ;
                }
                leaf nd-na-status {
                  if-feature nd-na-status ;
                  description 'The status of ND NA,including enable and disable'
                            + '(default:disable).'
                              ;
                  type enumeration {
                    enum disable {
                      value 0 ;
                      description 'The status of ND NA is disable.'
                                  ;
                    }
                    enum enable {
                      value 1 ;
                      description 'The status of ND NA is enable.'
                                  ;
                    }
                  }
                  default disable ;
                  ncd:revise-date 2019-04-30 ;
                }
                leaf nd-na-interval {
                  if-feature nd-na-interval ;
                  description 'The interval of ND NA,ranges from 1s to 14400s(d'
                            + 'efault:30s).'
                              ;
                  type uint32 {
                    range 1..14400 {
                      description 'The range of free-arp interval(default:30s).'
                                  ;
                    }
                  }
                  units s ;
                  default 30 ;
                  ncd:revise-date 2019-04-30 ;
                }
                leaf disnontest-8021p {
                  description 'The value of discard-non-test priority-8021p in '
                            + 'share mode,ranges from 0 to 7.'
                              ;
                  type uint8 {
                    range 0..7 {
                      description 'The range of priority-8021p.'
                                  ;
                    }
                  }
                }
                leaf disnontest-dscp {
                  description 'The value of discard-non-test DSCP in share mode'
                            + ',ranges from 0 to 63.'
                              ;
                  type uint8 {
                    range 0..63 {
                      description 'The range of DSCP.'
                                  ;
                    }
                  }
                }
                list packet-size {
                  description 'Configure the packet size.'
                              ;
                  key size ;
                  leaf size {
                    description 'The packet size,the upper limit of this parame'
                              + 'ter depend on the device.'
                                ;
                    type uint16 {
                      range 64..9216 {
                        description 'The range of packet size.'
                                    ;
                      }
                    }
                    units byte ;
                  }
                }
                container throughput {
                  description 'Configure throughput information.'
                              ;
                  presence throughput ;
                  leaf status {
                    description 'The status of throughput,including enable and '
                              + 'disable(default:disable).'
                                ;
                    type enumeration {
                      enum disable {
                        value 0 ;
                        description 'The throughput status is disable.'
                                    ;
                      }
                      enum enable {
                        value 1 ;
                        description 'The throughput status is enable.'
                                    ;
                      }
                    }
                    default disable ;
                  }
                  leaf rate-type {
                    description 'The rate type,including information rate and u'
                              + 'lr(default:information rate).'
                                ;
                    type enumeration {
                      enum ir {
                        value 1 ;
                        description 'The rate type is information rate.'
                                    ;
                      }
                      enum ulr {
                        value 2 ;
                        description 'The rate type is ulr.'
                                    ;
                      }
                    }
                    default ir ;
                  }
                  choice one-or-two-rate {
                    description 'Choose one from one rate and two rate.'
                                ;
                    case one-rate {
                      description 'One rate.'
                                  ;
                      container one-rate {
                        description 'One rate.'
                                    ;
                        presence 'one rate'
                                 ;
                        leaf rate {
                          description 'The value of one rate,the upper limit of'
                                    + ' this parameter depend on the device.'
                                      ;
                          type uint32 {
                            range 2..10000000 {
                              description 'The range of rate.'
                                          ;
                            }
                          }
                          units kbps ;
                          mandatory true ;
                        }
                      }
                    }
                    case two-rate {
                      description 'Two rate.'
                                  ;
                      container two-rate {
                        description 'Two rate.'
                                    ;
                        presence 'two rate'
                                 ;
                        leaf low-rate {
                          description 'The value of low rate,the upper limit of'
                                    + ' this parameter depend on the device.'
                                      ;
                          type uint32 {
                            range 1..10000000 {
                              description 'The range of rate.'
                                          ;
                            }
                          }
                          units kbps ;
                          mandatory true ;
                        }
                        leaf high-rate {
                          description 'The value of high rate,the upper limit o'
                                    + 'f this parameter depend on the device.'
                                      ;
                          type uint32 {
                            range 1..10000000 {
                              description 'The range of rate.'
                                          ;
                            }
                          }
                          units kbps ;
                          mandatory true ;
                        }
                      }
                    }
                  }
                  leaf one-rate-duration {
                    description 'The duration of one rate,ranges from 1s to 60s'
                              + '(default:4s).'
                                ;
                    type uint16 {
                      range 1..60 {
                        description 'The range of one rate duration(default:4s).'
                                    ;
                      }
                    }
                    units s ;
                    default 4 ;
                  }
                  leaf duration {
                    description 'The duration of one packet size,ranges from 10'
                              + 's to 172800s,if this value is not configured,t'
                              + 'he duration continues until the end of the tes'
                              + 't.'
                                ;
                    type uint32 {
                      range 10..172800 {
                        description 'The range of duration.'
                                    ;
                      }
                    }
                    units s ;
                  }
                  leaf precision {
                    description 'The value of precision,ranges from 1kbps to 10'
                              + '000kbps(default:1000kbps).'
                                ;
                    type uint32 {
                      range 1..10000 {
                        description 'The range of precision(default:1000kbps).'
                                    ;
                      }
                    }
                    units kbps ;
                    default 1000 ;
                  }
                  leaf timeout {
                    description 'The value of timeout,ranges from 1s to 60s(def'
                              + 'ault:4s).'
                                ;
                    type uint16 {
                      range 1..60 {
                        description 'The range of timeout(default:4s).'
                                    ;
                      }
                    }
                    units s ;
                    default 4 ;
                  }
                  leaf loss-ratio-threshold {
                    description 'The value of loss threshold,ranges from 0 to 1'
                              + '00(default:0).'
                                ;
                    type uint32 {
                      range 0..100 {
                        description 'The range of loss-threshold(default:0).'
                                    ;
                      }
                    }
                    default 0 ;
                  }
                }
                container loss {
                  description 'Configure loss information.'
                              ;
                  presence loss ;
                  leaf status {
                    description 'The status of loss,including enable and disabl'
                              + 'e(default:disable).'
                                ;
                    type enumeration {
                      enum disable {
                        value 0 ;
                        description 'The loss status is disable.'
                                    ;
                      }
                      enum enable {
                        value 1 ;
                        description 'The throughput status is enable.'
                                    ;
                      }
                    }
                    default disable ;
                  }
                  leaf rate-type {
                    description 'The rate type,including information rate and u'
                              + 'lr(default:information rate).'
                                ;
                    type enumeration {
                      enum ir {
                        value 1 ;
                        description 'The rate type is information rate.'
                                    ;
                      }
                      enum ulr {
                        value 2 ;
                        description 'The rate type is ulr.'
                                    ;
                      }
                    }
                    default ir ;
                  }
                  leaf rate {
                    description 'The value of rate,the upper limit of this para'
                              + 'meter depend on the device(default:1000kbps).'
                                ;
                    type uint32 {
                      range 1..10000000 {
                        description 'The range of rate(default:1000kbps).'
                                    ;
                      }
                    }
                    units kbps ;
                    default 1000 ;
                  }
                  leaf duration {
                    description 'The value of duration,ranges from 10s to 17280'
                              + '0s(default:60s).'
                                ;
                    type uint32 {
                      range 10..172800 {
                        description 'The range of duration.'
                                    ;
                      }
                    }
                    units s ;
                    default 60 ;
                  }
                  leaf timeout {
                    description 'The value of timeout,ranges from 1s to 60s(def'
                              + 'ault:4s).'
                                ;
                    type uint16 {
                      range 1..60 {
                        description 'The range of timeout(default:4s).'
                                    ;
                      }
                    }
                    units s ;
                    default 4 ;
                  }
                  leaf loss-ratio-threshold {
                    description 'The value of loss-ratio-threshold,ranges from '
                              + '0 to 100(default:0).'
                                ;
                    type uint32 {
                      range 0..100 {
                        description 'the range of loss-ratio-threshold(default:'
                                  + '0).'
                                    ;
                      }
                    }
                    default 0 ;
                  }
                }
                container delay {
                  description 'Configure delay information.'
                              ;
                  presence delay ;
                  leaf status {
                    description 'The status of delay,including enable and disab'
                              + 'le(default:disable).'
                                ;
                    type enumeration {
                      enum disable {
                        value 0 ;
                        description 'The delay status is disable.'
                                    ;
                      }
                      enum enable {
                        value 1 ;
                        description 'The delay status is enable.'
                                    ;
                      }
                    }
                    default disable ;
                  }
                  leaf rate-type {
                    description 'The rate type,including information rate and u'
                              + 'lr(default:information rate).'
                                ;
                    type enumeration {
                      enum ir {
                        value 1 ;
                        description 'The rate type is information rate.'
                                    ;
                      }
                      enum ulr {
                        value 2 ;
                        description 'The rate type is ulr.'
                                    ;
                      }
                    }
                    default ir ;
                  }
                  leaf rate {
                    description 'The value of rate,the upper limit of this para'
                              + 'meter depend on the device(default:1000kbps).'
                                ;
                    type uint32 {
                      range 0..10000000 {
                        description 'The range of rate(default:1000kbps).'
                                    ;
                      }
                    }
                    units kbps ;
                    default 1000 ;
                  }
                  leaf interval {
                    description 'The value of interval,ranges from 1s to 60s(de'
                              + 'fault:4s).'
                                ;
                    type uint8 {
                      range 1..60 {
                        description 'The range of interval(default:4s).'
                                    ;
                      }
                    }
                    units s ;
                    default 4 ;
                  }
                  leaf duration {
                    description 'The value of duration,ranges from 10s to 17280'
                              + '0s(default:60s).'
                                ;
                    type uint32 {
                      range 10..172800 {
                        description 'The range of duration(default:60s).'
                                    ;
                      }
                    }
                    units s ;
                    default 60 ;
                  }
                  leaf delay-threshold {
                    description 'The value of delay threshold,ranges from 1us t'
                              + 'o 1000000us(default:20000us).'
                                ;
                    type uint32 {
                      range 1..1000000 {
                        description 'The range of delay-threshold(default:20000'
                                  + 'us).'
                                    ;
                      }
                    }
                    units us ;
                    default 20000 ;
                  }
                  leaf jitter-threshold {
                    description 'The value of jitter threshold,ranges from 1us '
                              + 'to 1000000us(default:25000us).'
                                ;
                    type uint32 {
                      range 1..1000000 {
                        description 'The range of jitter-threshold(default:2500'
                                  + '0us).'
                                    ;
                      }
                    }
                    units us ;
                    default 25000 ;
                  }
                }
                container y1564 {
                  description 'Configure Y1564 information.'
                              ;
                  leaf status {
                    description 'The status of Y1564 test.'
                                ;
                    type enumeration {
                      enum disable {
                        value 0 ;
                        description 'The Y1564 status is disable.'
                                    ;
                      }
                      enum enable {
                        value 1 ;
                        description 'The Y1564 status is enable.'
                                    ;
                      }
                    }
                    default disable ;
                  }
                  leaf cir {
                    description 'The value of CIR rate in Y1564 test.'
                                ;
                    type uint32 {
                      range 1..10000000 {
                        description 'The range of cir rate(unit:kbps).'
                                    ;
                      }
                    }
                    units kbps ;
                  }
                  leaf eir {
                    description 'The value of EIR rate in Y1564 test.'
                                ;
                    type uint32 {
                      range 0..10000000 {
                        description 'The range of eir rate(unit:kbps).'
                                    ;
                      }
                    }
                    units kbps ;
                  }
                  leaf overload {
                    description 'The value of overload rate in Y1564 test.'
                                ;
                    type uint32 {
                      range 0..10000000 {
                        description 'The range of eir rate(unit:kbps).'
                                    ;
                      }
                    }
                    units kbps ;
                  }
                  leaf cir-test-type {
                    description 'The CIR test type of Y1564.'
                                ;
                    type enumeration {
                      enum simple {
                        value 1 ;
                        description 'The simple CIR test type.'
                                    ;
                      }
                      enum step-load {
                        value 2 ;
                        description 'The step-load CIR test type.'
                                    ;
                      }
                    }
                    default simple ;
                  }
                  leaf interval {
                    description 'The packet interval of Y1564 delay test.'
                                ;
                    type uint8 {
                      range 1..60 {
                        description 'The range of interval(default:4s).'
                                    ;
                      }
                    }
                    units s ;
                    default 4 ;
                  }
                  leaf duration {
                    description 'The duration of each rate in Y1564 test.'
                                ;
                    type uint32 {
                      range 10..172800 {
                        description 'The range of duration(default:60s).'
                                    ;
                      }
                    }
                    units s ;
                    default 60 ;
                  }
                  leaf timeout {
                    description 'The value of timeout in Y1564 packet loss test.'
                                ;
                    type uint16 {
                      range 1..60 {
                        description 'The range of timeout(default:4s).'
                                    ;
                      }
                    }
                    units s ;
                    default 4 ;
                  }
                  leaf loss-ratio-threshold {
                    description 'The value of loss-ratio-threshold(units:1/1000'
                              + '0).'
                                ;
                    type uint32 {
                      range 0..100 {
                        description 'The range of loss-ratio-threshold(default:'
                                  + '0).'
                                    ;
                      }
                    }
                    default 0 ;
                  }
                  leaf delay-threshold {
                    description 'The value of delay test threshold.'
                                ;
                    type uint32 {
                      range 1..1000000 {
                        description 'The range of delay-threshold(default:20000'
                                  + 'us).'
                                    ;
                      }
                    }
                    units us ;
                    default 20000 ;
                  }
                  leaf jitter-threshold {
                    description 'The value of jitter threshold.'
                                ;
                    type uint32 {
                      range 1..1000000 {
                        description 'The range of jitter-threshold(default:2500'
                                  + '0us).'
                                    ;
                      }
                    }
                    units us ;
                    default 25000 ;
                  }
                  leaf test-mode {
                    description 'The test mode of Y1564.'
                                ;
                    type enumeration {
                      enum configuration {
                        value 1 ;
                        description 'The configuration test mode.'
                                    ;
                      }
                      enum performance {
                        value 2 ;
                        description 'The performance test mode.'
                                    ;
                      }
                    }
                    default configuration ;
                  }
                  ncd:revise-date 2018-10-17 ;
                }
              }
              ncd:revise-date 2015-11-24 ;
            }
            case light-twamp {
              description 'Configure light TWAMP test parameters.'
                          ;
              container light-twamp {
                description 'Configure light TWAMP test parameters.'
                            ;
                leaf client-mode {
                  description 'Client mode, including L2 UNI mode,L2 bridge UNI'
                            + ' mode,L3 UNI mode,and L3 mode.'
                              ;
                  type enumeration {
                    enum l2-uni {
                      value 1 ;
                      description 'The client mode is L2 UNI.'
                                  ;
                    }
                    enum l3-uni {
                      value 2 ;
                      description 'The client mode is L3 UNI.'
                                  ;
                    }
                    enum l2-bridge-uni {
                      value 3 ;
                      description 'The client mode is L2 bridge UNI.'
                                  ;
                    }
                    enum l3 {
                      value 4 ;
                      description 'The client mode is L3.'
                                  ;
                    }
                    enum srv6-policy-sl {
                      value 5 ;
                      description 'The client mode is SRv6 policy SL.'
                                  ;
                    }
                  }
                }
                leaf reflector-mode {
                  if-feature reflector-mode ;
                  description 'Reflector mode,including standard mode and loopb'
                            + 'ack mode(default:standard mode).'
                              ;
                  type enumeration {
                    enum standard {
                      value 1 ;
                      description 'Standard mode.'
                                  ;
                    }
                    enum loopback {
                      value 2 ;
                      description 'Loopback mode.'
                                  ;
                    }
                  }
                  default standard ;
                  ncd:revise-date 2017-08-15 ;
                }
                leaf test-mode {
                  description 'Test mode,including online and offline.'
                              ;
                  type enumeration {
                    enum online {
                      value 1 ;
                      description 'The mode is online.'
                                  ;
                    }
                    enum offline {
                      value 2 ;
                      description 'The mode is offline.'
                                  ;
                    }
                  }
                }
                leaf inbound-interface {
                  description 'Interface name.'
                              ;
                  type ncd:ifname {
                    length 1..31 {
                      description 'The range of interface name length.'
                                  ;
                    }
                  }
                }
                leaf member-port {
                  description 'Member port name.'
                              ;
                  type ncd:ifname {
                    length 1..31 {
                      description 'The range of interface name length.'
                                  ;
                    }
                  }
                }
                choice ipv4-or-ipv6 {
                  description 'Choose one from ipv4 and ipv6.'
                              ;
                  case ipv4 {
                    description 'Type is ipv4.'
                                ;
                    leaf source-ip {
                      description 'The source IPv4 address.'
                                  ;
                      type ncd:ipv4-address-none-zero ;
                    }
                    leaf destination-ip {
                      description 'The destination IPv4 address.'
                                  ;
                      type ncd:ipv4-address-none-zero ;
                    }
                  }
                  case ipv6 {
                    description 'Type is ipv6.'
                                ;
                    leaf source-ipv6 {
                      if-feature ipv6-address ;
                      description 'The source ipv6 address.'
                                  ;
                      type ncd:ipv6-address ;
                    }
                    leaf destination-ipv6 {
                      if-feature ipv6-address ;
                      description 'The destination ipv6 address.'
                                  ;
                      type ncd:ipv6-address ;
                    }
                    ncd:revise-date 2019-04-30 ;
                  }
                }
                leaf source-mac {
                  description 'The source MAC address.'
                              ;
                  type ncd:mac-address-none-zero ;
                }
                leaf source-port {
                  description 'The source port,ranges from 1025 to 65535,or 862.'
                              ;
                  type uint16 {
                    range '862 | 1025..65535'
                          {
                      description 'The range of port number.'
                                  ;
                    }
                  }
                }
                leaf destination-mac {
                  description 'The destination MAC address.'
                              ;
                  type ncd:mac-address-none-zero ;
                }
                leaf destination-port {
                  description 'The destination port,ranges from 1025 to 65535,o'
                            + 'r 862.'
                              ;
                  type uint16 {
                    range '862 | 1025..65535'
                          {
                      description 'The range of port number.'
                                  ;
                    }
                  }
                }
                choice vlan-or-qinq {
                  description 'Choose one from vlan and qinq.'
                              ;
                  case vlan {
                    description 'Vlan information.'
                                ;
                    container vlan {
                      description 'Vlan information.'
                                  ;
                      presence 'vlan ID'
                               ;
                      leaf id {
                        description 'The value of vlan ID,ranges from 1 to 4094.'
                                    ;
                        type uint16 {
                          range 1..4094 {
                            description 'The range of vlan ID.'
                                        ;
                          }
                        }
                        mandatory true ;
                      }
                    }
                  }
                  case qinq {
                    description 'Qinq information.'
                                ;
                    container qinq {
                      description 'Qinq information.'
                                  ;
                      presence qinq ;
                      leaf internal-vlan-id {
                        description 'The value of internal vlan ID,ranges from '
                                  + '1 to 4094.'
                                    ;
                        type uint16 {
                          range 1..4094 {
                            description 'The range of vlan ID.'
                                        ;
                          }
                        }
                        mandatory true ;
                      }
                      leaf external-vlan-id {
                        description 'The value of external vlan ID,ranges from '
                                  + '1 to 4094.'
                                    ;
                        type uint16 {
                          range 1..4094 {
                            description 'The range of vlan ID.'
                                        ;
                          }
                        }
                        mandatory true ;
                      }
                    }
                  }
                }
                leaf priority-8021p {
                  description 'The value of priority-8021p,ranges from 0 to 7(d'
                            + 'efault:0).'
                              ;
                  type uint8 {
                    range 0..7 {
                      description 'The range of priority-8021p(default:0).'
                                  ;
                    }
                  }
                  default 0 ;
                }
                leaf dscp {
                  description 'The value of DSCP,ranges from 0 to 63(default:0).'
                              ;
                  type uint8 {
                    range 0..63 {
                      description 'The range of DSCP(default:0).'
                                  ;
                    }
                  }
                  default 0 ;
                }
                leaf free-arp-status {
                  description 'The status of free ARP,including enable and disa'
                            + 'ble(default:disable).'
                              ;
                  type enumeration {
                    enum disable {
                      value 0 ;
                      description 'The status of free-arp is disable.'
                                  ;
                    }
                    enum enable {
                      value 1 ;
                      description 'The status of free-arp is enable.'
                                  ;
                    }
                  }
                  default disable ;
                }
                leaf free-arp-interval {
                  description 'The interval of free ARP,ranges from 1s to 14400'
                            + 's(default:30s).'
                              ;
                  type uint32 {
                    range 1..14400 {
                      description 'The range of free-arp interval(default:30s).'
                                  ;
                    }
                  }
                  units s ;
                  default 30 ;
                }
                leaf nd-na-status {
                  if-feature nd-na-status ;
                  description 'The status of ND NA,including enable and disable'
                            + '(default:disable).'
                              ;
                  type enumeration {
                    enum disable {
                      value 0 ;
                      description 'The status of ND NA is disable.'
                                  ;
                    }
                    enum enable {
                      value 1 ;
                      description 'The status of ND NA is enable.'
                                  ;
                    }
                  }
                  default disable ;
                  ncd:revise-date 2019-04-30 ;
                }
                leaf nd-na-interval {
                  if-feature nd-na-interval ;
                  description 'The interval of ND NA,ranges from 1s to 14400s(d'
                            + 'efault:30s).'
                              ;
                  type uint32 {
                    range 1..14400 {
                      description 'The range of free-arp interval(default:30s).'
                                  ;
                    }
                  }
                  units s ;
                  default 30 ;
                  ncd:revise-date 2019-04-30 ;
                }
                leaf duration {
                  description 'The value of duration,ranges from 0,10s to 86400'
                            + 's,0 means continuous testing(default:60s).'
                              ;
                  type uint32 {
                    range '0 | 10..86400'
                          {
                      description 'The range of duration(default:60s).'
                                  ;
                    }
                  }
                  units s ;
                  default 60 ;
                }
                leaf interval {
                  description 'The value of interval,ranges from 1 to 600 when '
                            + 'unit is 100ms,ranges from 1 to 1000 when unit is'
                            + ' 100us,ranges from 50 to 100000 when unit is us('
                            + 'default:10).'
                              ;
                  type uint32 {
                    range 1..100000 {
                      description 'The range of interval(default:10).'
                                  ;
                    }
                  }
                  default 10 ;
                }
                leaf padding-length {
                  description 'Padding length,the upper limit of this parameter'
                            + ' depends on the device.(default:29bytes).'
                              ;
                  type uint16 {
                    range 29..65535 {
                      description 'The value of this parameter ranges from 29by'
                                + 'tes to 65535bytes(default:29bytes),the upper'
                                + ' limit of this parameter depend on the devic'
                                + 'e.'
                                  ;
                    }
                  }
                  units byte ;
                  default 29 ;
                }
                leaf report-interval {
                  description 'The report interval,ranges from 1s to 86400s.'
                              ;
                  type uint32 {
                    range 1..86400 {
                      description 'The range of report interval.'
                                  ;
                    }
                  }
                  units s ;
                }
                leaf timestamp-format {
                  if-feature timestamp-format ;
                  description 'Timestamp format,including PTP and NTP(default:P'
                            + 'TP).'
                              ;
                  type enumeration {
                    enum ptp {
                      value 1 ;
                      description 'PTP format.'
                                  ;
                    }
                    enum ntp {
                      value 2 ;
                      description 'NTP format.'
                                  ;
                    }
                  }
                  default ptp ;
                  ncd:revise-date 2017-08-15 ;
                }
                leaf delay-statistics-mode {
                  if-feature delay-statistics-mode ;
                  description 'The delay statistics mode,including bidirection,'
                            + 'unidirection and both(default:both).'
                              ;
                  type enumeration {
                    enum bidirection {
                      value 1 ;
                      description 'The delay statistics mode is bidirection.'
                                  ;
                    }
                    enum unidirection {
                      value 2 ;
                      description 'The delay statistics mode is unidirection.'
                                  ;
                    }
                    enum both {
                      value 3 ;
                      description 'The delay statistics mode is both bidirectio'
                                + 'n and unidirection.'
                                  ;
                    }
                  }
                  default both ;
                  ncd:revise-date 2019-05-17 ;
                }
                leaf proactive-test {
                  description 'Start or stop proactive test.'
                              ;
                  type enumeration {
                    enum stop {
                      value 0 ;
                      description 'Stop test.'
                                  ;
                    }
                    enum start {
                      value 1 ;
                      description 'Start test.'
                                  ;
                    }
                  }
                  default stop ;
                }
                leaf statistics-interval {
                  if-feature statistics-interval ;
                  description 'The value of statistics interval,ranges from 5s '
                            + 'to 60s(default:15s).'
                              ;
                  type uint16 {
                    range 5..60 {
                      description 'The range of interval(default:15s).'
                                  ;
                    }
                  }
                  units s ;
                  default 15 ;
                  ncd:revise-date 2017-09-05 ;
                }
                leaf timeout {
                  if-feature timeout ;
                  description 'The value of timeout,ranges from 1s to 10s(defau'
                            + 'lt:5s).'
                              ;
                  type uint16 {
                    range 1..10 {
                      description 'The range of timeout(default:5s).'
                                  ;
                    }
                  }
                  units s ;
                  default 5 ;
                  ncd:revise-date 2017-09-05 ;
                }
                container interval-unit {
                  description 'Interval unit.'
                              ;
                  choice interval-unit {
                    description 'Interval unit.'
                                ;
                    default unit-100millisecond ;
                    case unit-100millisecond {
                      description 'Interval unit is 100millisecond.'
                                  ;
                      leaf unit-100millisecond {
                        description 'Interval unit is 100millisecond.'
                                    ;
                        type empty ;
                      }
                    }
                    case unit-microsecond {
                      description 'Interval unit is microsecond.'
                                  ;
                      leaf unit-microsecond {
                        if-feature interval-unit-us ;
                        description 'Interval unit is microsecond.'
                                    ;
                        type empty ;
                      }
                    }
                  }
                  ncd:revise-date 2017-09-05 ;
                }
                leaf packet-matching-mode {
                  if-feature packet-matching-mode ;
                  description 'Packet matching mode,including extend mode and s'
                            + 'tandard mode(default:extend mode).'
                              ;
                  type enumeration {
                    enum extend {
                      value 1 ;
                      description 'Extend mode.'
                                  ;
                    }
                    enum standard {
                      value 2 ;
                      description 'Standard mode.'
                                  ;
                    }
                  }
                  default extend ;
                  ncd:revise-date 2018-05-03 ;
                }
                leaf performance-statistics {
                  if-feature performance-statistics ;
                  description 'performance statistics,including enable and disa'
                            + 'ble(default:enable).'
                              ;
                  type enumeration {
                    enum enable {
                      value 1 ;
                      description 'Status is enable.'
                                  ;
                    }
                    enum disable {
                      value 0 ;
                      description 'Status is disable.'
                                  ;
                    }
                  }
                  default enable ;
                  ncd:revise-date 2018-05-03 ;
                }
                leaf vrf-name {
                  if-feature vrf-name ;
                  description 'The VRF name,the length of this string is from 1'
                            + ' to 32.'
                              ;
                  type string {
                    length 1..32 {
                      description 'The length of this string is from 1 to 32.'
                                  ;
                    }
                  }
                  ncd:revise-date 2019-07-22 ;
                }
                container sr-policy {
                  if-feature sr-policy ;
                  description 'Configure sr-policy parameters.'
                              ;
                  presence sr-policy ;
                  leaf color {
                    description 'The color of policy.'
                                ;
                    type uint32 {
                      range 1..4294967295 ;
                    }
                    mandatory true ;
                  }
                  container end-point {
                    description 'Configure end point.'
                                ;
                    leaf end-point-v6 {
                      description 'The ipv6 address of end-point.'
                                  ;
                      type ncd:ipv6-address-none-zero ;
                      mandatory true ;
                    }
                  }
                  container protocol-origin {
                    description 'Configure Protocol origin.'
                                ;
                    choice type {
                      description 'Protocol type.'
                                  ;
                      mandatory true ;
                      case bgp {
                        description 'Protocol BGP.'
                                    ;
                        container bgp {
                          description 'Protocol BGP.'
                                      ;
                          leaf discriminator {
                            description 'BGP discriminator.'
                                        ;
                            type uint32 {
                              range 0..4294967295 ;
                            }
                            mandatory true ;
                          }
                        }
                      }
                      case configuration {
                        description 'Protocol configuration.'
                                    ;
                        container configuration {
                          description 'Protocol configuration.'
                                      ;
                          leaf discriminator {
                            description 'Configuration discriminator.'
                                        ;
                            type uint32 {
                              range 0..4294967295 ;
                            }
                            mandatory true ;
                          }
                        }
                      }
                    }
                  }
                  leaf sl-index {
                    description 'The segment-list index.'
                                ;
                    type uint8 {
                      range 0..255 ;
                    }
                    mandatory true ;
                  }
                  ncd:revise-date 2020-12-07 ;
                }
                leaf delay-mode {
                  if-feature delay-mode ;
                  description 'The delay mode,including accurate,average(defaul'
                            + 't:average).'
                              ;
                  type enumeration {
                    enum average {
                      value 1 ;
                      description 'The delay mode is average.'
                                  ;
                    }
                    enum accurate {
                      value 2 ;
                      description 'The delay mode is accurate.'
                                  ;
                    }
                  }
                  default average ;
                  ncd:revise-date 2020-12-24 ;
                }
              }
              ncd:revise-date 2016-02-17 ;
            }
            case proactive-ping {
              description 'Configure proactive PING test parameters.'
                          ;
              container proactive-ping {
                description 'Configure proactive PING test parameters.'
                            ;
                leaf type {
                  description 'Test type,including standard, nni and uni.'
                              ;
                  type enumeration {
                    enum standard {
                      value 0 ;
                      description 'The type is standard.'
                                  ;
                    }
                    enum uni {
                      value 1 ;
                      description 'The type is UNI.'
                                  ;
                    }
                    enum nni {
                      value 2 ;
                      description 'The type is NNI.'
                                  ;
                    }
                  }
                  default standard ;
                }
                choice ip-addr-family {
                  description 'Choose one from ipv4 and ipv6.'
                              ;
                  case ipv4 {
                    description 'Type is ipv4.'
                                ;
                    leaf source-ip {
                      description 'The source IPv4 address.'
                                  ;
                      type ncd:ipv4-address-none-zero ;
                    }
                    leaf destination-ip {
                      description 'The destination IPv4 address.'
                                  ;
                      type ncd:ipv4-address-none-zero ;
                    }
                    leaf nexthop-address {
                      description 'Next hop IPv4 address.'
                                  ;
                      type ncd:ipv4-address-none-zero ;
                    }
                  }
                  case ipv6 {
                    description 'Type is ipv6.'
                                ;
                    leaf source-ipv6 {
                      description 'The source IPv6 address.'
                                  ;
                      type ncd:ipv6-address-none-zero ;
                    }
                    leaf destination-ipv6 {
                      description 'The destination IPv6 address.'
                                  ;
                      type ncd:ipv6-address-none-zero ;
                    }
                    leaf nexthop-address-ipv6 {
                      description 'Next hop IPv6 address.'
                                  ;
                      type ncd:ipv6-address-none-zero ;
                    }
                    ncd:revise-date 2020-04-08 ;
                  }
                }
                leaf vrf-name {
                  description 'The VRF name,the length of this string is from 1'
                            + ' to 32.'
                              ;
                  type string {
                    length 1..32 {
                      description 'This string length ranges from 1 to 32.'
                                  ;
                    }
                  }
                }
                leaf out-interface {
                  description 'Interface name.'
                              ;
                  type ncd:ifname {
                    length 1..31 {
                      description 'The range of interface name length.'
                                  ;
                    }
                  }
                }
                leaf dscp {
                  description 'The value of DSCP,ranges from 0 to 63(default:0).'
                              ;
                  type uint8 {
                    range 0..63 {
                      description 'The range of DSCP(default:0).'
                                  ;
                    }
                  }
                  default 0 ;
                }
                leaf interval {
                  description 'The value of interval,ranges from 1 to 600(defau'
                            + 'lt:10).'
                              ;
                  type uint32 {
                    range 1..600 {
                      description 'The range of interval(default:10).'
                                  ;
                    }
                  }
                  units 100ms ;
                  default 10 ;
                }
                leaf packet-size {
                  description 'Packet size,ranges from 36bytes to 1500bytes(def'
                            + 'ault:36bytes).'
                              ;
                  type uint16 {
                    range 36..1500 {
                      description 'The range of packet size(default:36bytes).'
                                  ;
                    }
                  }
                  units byte ;
                  default 36 ;
                }
                leaf performance-statistics-status {
                  description 'The status of performance statistics,including e'
                            + 'nable and disable(default:enable).'
                              ;
                  type enumeration {
                    enum disable {
                      value 0 ;
                      description 'Performance statistics disable.'
                                  ;
                    }
                    enum enable {
                      value 1 ;
                      description 'Performance statistics enable.'
                                  ;
                    }
                  }
                  default enable ;
                }
                leaf proactive-test {
                  description 'Start or stop proactive test(default:stop).'
                              ;
                  type enumeration {
                    enum stop {
                      value 0 ;
                      description 'Stop test.'
                                  ;
                    }
                    enum start {
                      value 1 ;
                      description 'Start test.'
                                  ;
                    }
                  }
                  default stop ;
                }
                leaf bind-oma-interface {
                  if-feature bind-oma-interface ;
                  description 'Bind OMA interface.'
                              ;
                  type ncd:ifname {
                    length 1..31 {
                      description 'The range of interface name length.'
                                  ;
                    }
                  }
                  ncd:revise-date 2018-05-03 ;
                }
                leaf specify-interface {
                  if-feature specify-interface ;
                  description 'specify interface.'
                              ;
                  type ncd:ifname {
                    length 1..31 {
                      description 'The range of interface name length.'
                                  ;
                    }
                  }
                  ncd:revise-date 2018-05-03 ;
                }
                leaf pattern {
                  if-feature pattern ;
                  description 'The pattern of proactive-ping, from <0-9>,<a-f>o'
                            + 'r<A-F>.'
                              ;
                  type string {
                    length 4 {
                      description 'The pattern string.'
                                  ;
                    }
                  }
                  ncd:revise-date 2019-11-27 ;
                }
              }
              ncd:revise-date 2017-08-15 ;
            }
          }
          choice trap-switch {
            description 'Turn on or turn off trap function.'
                        ;
            default disable ;
            case enable {
              description 'Turn on trap function.'
                          ;
              container enable {
                description 'Turn on trap function.'
                            ;
                leaf trap-percent {
                  description 'Turning on trap function,and configure trap pers'
                            + 'ent.'
                              ;
                  type uint32 {
                    range 1..100 {
                      description 'The loss ratio threshold ranges from 1 to 10'
                                + '0.'
                                  ;
                    }
                  }
                  mandatory true ;
                }
              }
            }
            case disable {
              description 'Turn off trap function.'
                          ;
              container disable {
                description 'Turn off trap function.'
                            ;
                leaf disable {
                  description 'Turn off trap function.'
                              ;
                  type empty ;
                }
              }
            }
          }
          container timing {
            description 'Start a test at certain times.'
                        ;
            presence 'use timerange to start test'
                     ;
            leaf timerange-name {
              description 'The configration of timerange name,this configuratio'
                        + 'n can be used to start a test at certain times,this '
                        + 'string length ranges from 1 to 31.'
                          ;
              type string {
                length 1..31 {
                  description 'this string length ranges from 1 to 31.'
                              ;
                }
              }
              mandatory true ;
            }
          }
          container policy {
            description 'Start a cycle test.'
                        ;
            presence 'use looptime to start test'
                     ;
            choice type {
              description 'Configue the type of policy in continuous cycle test.'
                          ;
              case loop-time {
                description 'The cycle test policy type is loop-time.'
                            ;
                leaf loop-time {
                  if-feature policy-loop ;
                  description 'Configure SQA test loop-time, ranges from 1s to '
                            + '86400s.'
                              ;
                  type uint32 {
                    range 1..86400 {
                      description 'Configure SQA test loop-time, ranges from 1s'
                                + ' to 86400s.'
                                  ;
                    }
                  }
                  mandatory true ;
                }
              }
              case frequency {
                description 'The cycle test policy type is frequency.'
                            ;
                leaf frequency {
                  if-feature policy-frequency ;
                  description 'Configure SQA frequency of cycle test, ranges fr'
                            + 'om 10s to 86400s.'
                              ;
                  type uint32 {
                    range 10..86400 {
                      description 'Configure SQA frequency of continuous test, '
                                + 'ranges from 10s to 86400s.'
                                  ;
                    }
                  }
                  mandatory true ;
                }
                ncd:revise-date 2020-09-07 ;
              }
            }
            ncd:revise-date 2017-06-14 ;
          }
          container delay-threshold {
            description 'Configure delay-threshold.'
                        ;
            presence 'configure delay-threshold for a test'
                     ;
            leaf delay-threshold-value {
              if-feature delay-threshold ;
              description 'Configure delay-threshold value, ranges from 1ms to '
                        + '10000ms.'
                          ;
              type uint32 {
                range 1..10000 {
                  description 'The value of delay-threshold, ranges from 1ms to'
                            + ' 10000ms.'
                              ;
                }
              }
              mandatory true ;
            }
            leaf delay-threshold-type {
              if-feature delay-threshold ;
              description 'The delay-threshold type, including bidirectional, f'
                        + 'orward and reverse.'
                          ;
              type enumeration {
                enum bidirectional {
                  value 1 ;
                  description 'Bidirectional delay.'
                              ;
                }
                enum forward {
                  value 2 ;
                  description 'Forward delay.'
                              ;
                }
                enum reverse {
                  value 3 ;
                  description 'Reverse delay.'
                              ;
                }
              }
              mandatory true ;
            }
            ncd:revise-date 2017-06-14 ;
          }
        }
      }
      container servers {
        description 'Configure SQA server info.'
                    ;
        list server {
          description 'Configure SQA server info.'
                      ;
          key type ;
          leaf type {
            description 'Configure SQA UDP or TCP server.'
                        ;
            type enumeration {
              enum tcp-server {
                value 2 ;
                description 'Configure SQA TCP server.'
                            ;
              }
              enum udp-server {
                value 9 ;
                description 'Configure SQA UDP server.'
                            ;
              }
            }
          }
          choice ip-addr-family {
            description 'Choose one from IPv4 and IPv6.'
                        ;
            mandatory true ;
            case ipv4 {
              description 'Type is IPv4.'
                          ;
              leaf destination-ip {
                description 'Listening IPv4 address.'
                            ;
                type ncd:ipv4-address ;
                mandatory true ;
              }
            }
            case ipv6 {
              description 'Type is IPv6.'
                          ;
              leaf destination-ipv6 {
                description 'Listening IPv6 address.'
                            ;
                type ncd:ipv6-address ;
                mandatory true ;
              }
              leaf vrf-name {
                description 'The VRF name,the length of this string is from 1 t'
                          + 'o 32.'
                            ;
                type string {
                  length 1..32 {
                    description 'The length of this string is from 1 to 32.'
                                ;
                  }
                }
              }
              ncd:revise-date 2020-02-18 ;
            }
          }
          leaf destination-port {
            description 'Listening port number,ranges from 1025 to 65535.'
                        ;
            type uint16 {
              range 1025..65535 {
                description 'This parameter ranges from 1025 to 65535.'
                            ;
              }
            }
            mandatory true ;
          }
        }
      }
      container reflectors {
        description 'Reflector information.'
                    ;
        list reflector {
          description 'Reflector information.'
                      ;
          key reflector-id ;
          leaf reflector-id {
            description 'Reflector ID,ranges from 1 to 65535.'
                        ;
            type uint16 {
              range 1..65535 {
                description 'The range of reflector ID.'
                            ;
              }
            }
          }
          leaf inbound-interface {
            description 'Interface name.'
                        ;
            type ncd:ifname {
              length 1..31 {
                description 'The range of interface name length.'
                            ;
              }
            }
            mandatory true ;
          }
          leaf reflector-mode {
            description 'Reflector mode,including L2 mode,L3 mode.'
                        ;
            type enumeration {
              enum l2 {
                value 2 ;
                description 'The reflector mode is L2.'
                            ;
              }
              enum l3 {
                value 3 ;
                description 'The reflector mode is L3.'
                            ;
              }
            }
            mandatory true ;
          }
          leaf test-mode {
            description 'Test mode,including online and offline.'
                        ;
            type enumeration {
              enum online {
                value 1 ;
                description 'The mode is online.'
                            ;
              }
              enum offline {
                value 2 ;
                description 'The mode is offline.'
                            ;
              }
            }
            mandatory true ;
          }
          leaf source-mac {
            description 'The source MAC address.'
                        ;
            type ncd:mac-address-none-zero ;
          }
          choice ipv4-or-ipv6 {
            description 'Choose one from ipv4 and ipv6.'
                        ;
            case ipv4 {
              description 'Type is ipv4.'
                          ;
              leaf source-ip {
                description 'The source IPv4 address.'
                            ;
                type ncd:ipv4-address-none-zero ;
              }
              leaf destination-ip {
                description 'The destination IPv4 address.'
                            ;
                type ncd:ipv4-address-none-zero ;
              }
            }
            case ipv6 {
              description 'Type is ipv6.'
                          ;
              leaf source-ipv6 {
                if-feature ipv6-address ;
                description 'The source IPv6 address.'
                            ;
                type ncd:ipv6-address ;
              }
              leaf destination-ipv6 {
                if-feature ipv6-address ;
                description 'The destination IPv6 address.'
                            ;
                type ncd:ipv6-address ;
              }
              ncd:revise-date 2019-04-30 ;
            }
          }
          leaf destination-mac {
            description 'The destination MAC address.'
                        ;
            type ncd:mac-address-none-zero ;
          }
          leaf source-port {
            description 'The source port,ranges from 1 to 65535(default:49184).'
                        ;
            type uint16 {
              range 1..65535 {
                description 'The range of port number(default:49184).'
                            ;
              }
            }
            default 49184 ;
          }
          leaf destination-port {
            description 'The destination port,ranges from 1 to 65535(default:7).'
                        ;
            type uint16 {
              range 1..65535 {
                description 'The range of port number(default:7).'
                            ;
              }
            }
            default 7 ;
          }
          choice vlan-or-qinq {
            description 'Choose one from vlan and qinq.'
                        ;
            case vlan {
              description 'Vlan information.'
                          ;
              container vlan {
                description 'Vlan information.'
                            ;
                presence 'vlan ID'
                         ;
                leaf id {
                  description 'The value of vlan ID,ranges from 1 to 4094.'
                              ;
                  type uint16 {
                    range 1..4094 {
                      description 'The range of vlan ID.'
                                  ;
                    }
                  }
                  mandatory true ;
                }
              }
            }
            case qinq {
              description 'Qinq information.'
                          ;
              container qinq {
                description 'Qinq information.'
                            ;
                presence qinq ;
                leaf internal-vlan-id {
                  description 'The value of internal vlan ID,ranges from 1 to 4'
                            + '094.'
                              ;
                  type uint16 {
                    range 1..4094 {
                      description 'The range of vlan ID.'
                                  ;
                    }
                  }
                  mandatory true ;
                }
                leaf external-vlan-id {
                  description 'The value of external vlan ID,ranges from 1 to 4'
                            + '094.'
                              ;
                  type uint16 {
                    range 1..4094 {
                      description 'The range of vlan ID.'
                                  ;
                    }
                  }
                  mandatory true ;
                }
              }
            }
          }
          leaf priority-8021p {
            description 'The value of priority-8021p,ranges from 0 to 7(default'
                      + ':0).'
                        ;
            type uint8 {
              range 0..7 {
                description 'The range of priority-8021p(default:0).'
                            ;
              }
            }
          }
          leaf dscp {
            description 'The value of DSCP,ranges from 0 to 63(default:0).'
                        ;
            type uint8 {
              range 0..63 {
                description 'The range of DSCP(default:0).'
                            ;
              }
            }
          }
          choice interface-mode {
            description 'Interface mode.'
                        ;
            default share ;
            case share {
              description 'Share mode.'
                          ;
              container share {
                description 'Share mode.'
                            ;
                leaf disnontest-8021p {
                  description 'The value of discard-non-test priority-8021p in '
                            + 'share mode,ranges from 0 to 7.'
                              ;
                  type uint8 {
                    range 0..7 {
                      description 'The range of priority-8021p.'
                                  ;
                    }
                  }
                }
                leaf disnontest-dscp {
                  description 'The value of discard-non-test DSCP in share mode'
                            + ',ranges from 0 to 63.'
                              ;
                  type uint8 {
                    range 0..63 {
                      description 'The range of DSCP.'
                                  ;
                    }
                  }
                }
              }
            }
            case exclusive {
              description 'Exclusive mode.'
                          ;
              container exclusive {
                description 'Exclusive mode.'
                            ;
                leaf exclusive {
                  description 'Exclusive mode.'
                              ;
                  type empty ;
                  mandatory true ;
                }
              }
            }
          }
          leaf ageing-time {
            description 'The value of ageing time,ranges from 10s to 173400s(de'
                      + 'fault:14400s),0 means continuous.'
                        ;
            type uint32 {
              range '0 | 10..173400'
                    {
                description 'The range is 10s to 173400s(default:14400s),0 mean'
                          + 's continuous.'
                            ;
              }
            }
            units s ;
            default 14400 ;
          }
        }
        ncd:revise-date 2015-11-24 ;
      }
      container reflector-free-arps {
        description 'The free ARP information of reflector.'
                    ;
        list reflector-free-arp {
          description 'The free ARP information of reflector.'
                      ;
          key reflector-id ;
          leaf reflector-id {
            description 'Reflector ID,ranges from 1 to 65535.'
                        ;
            type uint16 {
              range 1..65535 {
                description 'The range of reflector ID.'
                            ;
              }
            }
          }
          leaf local-ipv4 {
            description 'The local IPv4 address.'
                        ;
            type ncd:ipv4-address-none-zero ;
            mandatory true ;
          }
          leaf interval {
            description 'The value of interval,ranges from 1s to 14400s(default'
                      + ':30s).'
                        ;
            type uint32 {
              range 1..14400 {
                description 'The range of interval(default:30s).'
                            ;
              }
            }
            units s ;
            default 30 ;
          }
          choice vlan-or-qinq {
            description 'Choose one from vlan and qinq.'
                        ;
            case vlan {
              description 'Vlan information.'
                          ;
              container vlan {
                description 'Vlan information.'
                            ;
                presence 'vlan ID'
                         ;
                leaf id {
                  description 'The value of vlan ID,ranges from 1 to 4094.'
                              ;
                  type uint16 {
                    range 1..4094 {
                      description 'The range of vlan ID.'
                                  ;
                    }
                  }
                  mandatory true ;
                }
              }
            }
            case qinq {
              description 'Qinq information.'
                          ;
              container qinq {
                description 'Qinq information.'
                            ;
                presence qinq ;
                leaf internal-vlan-id {
                  description 'The value of internal vlan ID,ranges from 1 to 4'
                            + '094.'
                              ;
                  type uint16 {
                    range 1..4094 {
                      description 'The range of vlan ID.'
                                  ;
                    }
                  }
                  mandatory true ;
                }
                leaf external-vlan-id {
                  description 'The value of external vlan ID,ranges from 1 to 4'
                            + '094.'
                              ;
                  type uint16 {
                    range 1..4094 {
                      description 'The range of vlan ID.'
                                  ;
                    }
                  }
                  mandatory true ;
                }
              }
            }
          }
        }
        ncd:revise-date 2015-11-24 ;
      }
      container reflector-nd-nas {
        description 'The ND NA information of reflector.'
                    ;
        list reflector-nd-na {
          description 'The ND NA information of reflector.'
                      ;
          key reflector-id ;
          leaf reflector-id {
            description 'Reflector ID,ranges from 1 to 65535.'
                        ;
            type uint16 {
              range 1..65535 {
                description 'The range of reflector ID.'
                            ;
              }
            }
          }
          leaf local-ipv6 {
            if-feature ipv6-address ;
            description 'The local IPv6 address.'
                        ;
            type ncd:ipv6-address ;
            mandatory true ;
          }
          leaf interval {
            description 'The value of interval,ranges from 1s to 14400s(default'
                      + ':30s).'
                        ;
            type uint32 {
              range 1..14400 {
                description 'The range of interval(default:30s).'
                            ;
              }
            }
            units s ;
            default 30 ;
          }
          choice vlan-or-qinq {
            description 'Choose one from vlan and qinq.'
                        ;
            case vlan {
              description 'Vlan information.'
                          ;
              container vlan {
                description 'Vlan information.'
                            ;
                presence 'vlan ID'
                         ;
                leaf id {
                  description 'The value of vlan ID,ranges from 1 to 4094.'
                              ;
                  type uint16 {
                    range 1..4094 {
                      description 'The range of vlan ID.'
                                  ;
                    }
                  }
                  mandatory true ;
                }
              }
            }
            case qinq {
              description 'Qinq information.'
                          ;
              container qinq {
                description 'Qinq information.'
                            ;
                presence qinq ;
                leaf internal-vlan-id {
                  description 'The value of internal vlan ID,ranges from 1 to 4'
                            + '094.'
                              ;
                  type uint16 {
                    range 1..4094 {
                      description 'The range of vlan ID.'
                                  ;
                    }
                  }
                  mandatory true ;
                }
                leaf external-vlan-id {
                  description 'The value of external vlan ID,ranges from 1 to 4'
                            + '094.'
                              ;
                  type uint16 {
                    range 1..4094 {
                      description 'The range of vlan ID.'
                                  ;
                    }
                  }
                  mandatory true ;
                }
              }
            }
          }
        }
        ncd:revise-date 2019-04-30 ;
      }
      container twamp-reflectors {
        description 'TWAMP reflector information.'
                    ;
        list twamp-reflector {
          description 'TWAMP reflector information.'
                      ;
          key reflector-id ;
          leaf reflector-id {
            description 'Reflector ID,ranges from 1 to 65535.'
                        ;
            type uint16 {
              range 1..65535 {
                description 'The range of reflector ID.'
                            ;
              }
            }
          }
          leaf inbound-interface {
            description 'Interface name.'
                        ;
            type ncd:ifname {
              length 1..31 {
                description 'The range of interface name length.'
                            ;
              }
            }
          }
          leaf vrf-name {
            if-feature vrf-name ;
            description 'The VRF name,the length of this string ranges from 1 t'
                      + 'o 32.'
                        ;
            type string {
              length 1..32 {
                description 'The length of this string is from 1 to 32.'
                            ;
              }
            }
            ncd:revise-date 2019-01-05 ;
          }
          leaf test-mode {
            description 'Test mode,including online and offline.'
                        ;
            type enumeration {
              enum online {
                value 1 ;
                description 'The mode is online.'
                            ;
              }
              enum offline {
                value 2 ;
                description 'The mode is offline.'
                            ;
              }
            }
          }
          choice ipv4-or-ipv6 {
            description 'Choose one from ipv4 and ipv6.'
                        ;
            mandatory true ;
            case ipv4 {
              description 'Type is ipv4.'
                          ;
              leaf source-ip {
                description 'The source IPv4 address.'
                            ;
                type ncd:ipv4-address-none-zero ;
                mandatory true ;
              }
              leaf destination-ip {
                description 'The destination IPv4 address.'
                            ;
                type ncd:ipv4-address-none-zero ;
                mandatory true ;
              }
            }
            case ipv6 {
              description 'Type is ipv6.'
                          ;
              leaf source-ipv6 {
                if-feature ipv6-address ;
                description 'The source IPv6 address.'
                            ;
                type ncd:ipv6-address ;
                mandatory true ;
              }
              leaf destination-ipv6 {
                if-feature ipv6-address ;
                description 'The destination IPv6 address.'
                            ;
                type ncd:ipv6-address ;
                mandatory true ;
              }
              ncd:revise-date 2019-04-30 ;
            }
          }
          leaf source-port {
            description 'The source port,ranges from 1025 to 65535,or 862.'
                        ;
            type uint16 {
              range '862 | 1025..65535'
                    {
                description 'The range of port number.'
                            ;
              }
            }
          }
          leaf destination-port {
            description 'The destination port,ranges from 1025 to 65535,or 862.'
                        ;
            type uint16 {
              range '862 | 1025..65535'
                    {
                description 'The range of port number.'
                            ;
              }
            }
            mandatory true ;
          }
          leaf source-mac {
            description 'The source MAC address.'
                        ;
            type ncd:mac-address-none-zero ;
          }
          leaf destination-mac {
            description 'The destination MAC address.'
                        ;
            type ncd:mac-address-none-zero ;
          }
          choice vlan-or-qinq {
            description 'Choose one from vlan and qinq.'
                        ;
            case vlan {
              description 'Vlan information.'
                          ;
              container vlan {
                description 'Vlan information.'
                            ;
                presence 'vlan ID'
                         ;
                leaf id {
                  description 'The value of vlan ID,ranges from 1 to 4094.'
                              ;
                  type uint16 {
                    range 1..4094 {
                      description 'The range of vlan ID.'
                                  ;
                    }
                  }
                  mandatory true ;
                }
              }
            }
            case qinq {
              description 'Qinq information.'
                          ;
              container qinq {
                description 'Qinq information.'
                            ;
                presence qinq ;
                leaf internal-vlan-id {
                  description 'The value of internal vlan ID,ranges from 1 to 4'
                            + '094.'
                              ;
                  type uint16 {
                    range 1..4094 {
                      description 'The range of vlan ID.'
                                  ;
                    }
                  }
                  mandatory true ;
                }
                leaf external-vlan-id {
                  description 'The value of external vlan ID,ranges from 1 to 4'
                            + '094.'
                              ;
                  type uint16 {
                    range 1..4094 {
                      description 'The range of vlan ID.'
                                  ;
                    }
                  }
                  mandatory true ;
                }
              }
            }
          }
          leaf priority-8021p {
            description 'The value of priority-8021p,ranges from 0 to 7.'
                        ;
            type uint8 {
              range 0..7 {
                description 'The range of priority-8021p.'
                            ;
              }
            }
          }
          leaf dscp {
            description 'The value of DSCP,ranges from 0 to 63.'
                        ;
            type uint8 {
              range 0..63 {
                description 'The range of DSCP.'
                            ;
              }
            }
          }
          leaf timestamp-format {
            if-feature timestamp-format ;
            description 'Timestamp format,including PTP and NTP(default:PTP).'
                        ;
            type enumeration {
              enum ptp {
                value 1 ;
                description 'PTP format.'
                            ;
              }
              enum ntp {
                value 2 ;
                description 'NTP format.'
                            ;
              }
            }
            default ptp ;
            ncd:revise-date 2017-08-15 ;
          }
          leaf ageing-time {
            description 'The value of ageing time,ranges from 10s to 173400s(de'
                      + 'fault:0s),0 means continuous.'
                        ;
            type uint32 {
              range '0 | 10..173400'
                    {
                description 'The range is 10s to 173400s(default:0s),0 means co'
                          + 'ntinuous.'
                            ;
              }
            }
            units s ;
            default 0 ;
          }
        }
        ncd:revise-date 2016-02-17 ;
      }
    }
  }
  container state {
    config false ;
    description 'SQA state model Info.'
                ;
    container sqa {
      description 'SQA state parameters.'
                  ;
      container icmp-results {
        description 'The ICMP test result.'
                    ;
        list icmp-result {
          description 'The ICMP test result.'
                      ;
          key test-number ;
          leaf test-number {
            description 'The value of test Index,the upper limit of this parame'
                      + 'ter depend on the device.'
                        ;
            type uint32 {
              range 1..1024 {
                description 'The test number ranges from 1 to 1024.'
                            ;
              }
            }
          }
          leaf repeat-count {
            description 'The count of sending ICMP packets.'
                        ;
            type uint16 {
              range 1..65535 {
                description 'The count of sending ICMP packets.'
                            ;
              }
            }
          }
          leaf response-count {
            description 'The count of receiving ICMP packets.'
                        ;
            type uint16 {
              range 0..65535 {
                description 'The count of receiving ICMP packets.'
                            ;
              }
            }
          }
          leaf destination-ip {
            description 'The destination IPv4 address.'
                        ;
            type ncd:ipv4-address ;
          }
          leaf min-rtt {
            description 'The minimal value of RTT.'
                        ;
            type uint32 ;
            units ms ;
          }
          leaf max-rtt {
            description 'The maximal value of RTT.'
                        ;
            type uint32 ;
            units ms ;
          }
          leaf avg-rtt {
            description 'The averange value of RTT.'
                        ;
            type uint32 ;
            units ms ;
          }
          leaf sum-rtt {
            description 'The sum value of RTT.'
                        ;
            type uint32 ;
            units ms ;
          }
          leaf min-positive-jitter {
            description 'The minimal value of positive jitter.'
                        ;
            type uint32 ;
            units ms ;
          }
          leaf max-positive-jitter {
            description 'The maximal value of positive jitter.'
                        ;
            type uint32 ;
            units ms ;
          }
          leaf avg-positive-jitter {
            description 'The averange value of positive jitter.'
                        ;
            type uint32 ;
            units ms ;
          }
          leaf sum-positive-jitter {
            description 'The sum value of positive jitter.'
                        ;
            type uint32 ;
            units ms ;
          }
          leaf min-negative-jitter {
            description 'The minimal value of negative jitter.'
                        ;
            type uint32 ;
            units ms ;
          }
          leaf max-negative-jitter {
            description 'The maximal value of negative jitter.'
                        ;
            type uint32 ;
            units ms ;
          }
          leaf avg-negative-jitter {
            description 'The averange value of negative jitter.'
                        ;
            type uint32 ;
            units ms ;
          }
          leaf sum-negative-jitter {
            description 'The sum value of negative jitter.'
                        ;
            type uint32 ;
            units ms ;
          }
          leaf min-jitter {
            description 'The minimal value of jitter.'
                        ;
            type uint32 ;
            units ms ;
          }
          leaf max-jitter {
            description 'The maximal value of jitter.'
                        ;
            type uint32 ;
            units ms ;
          }
          leaf avg-jitter {
            description 'The averange value of jitter.'
                        ;
            type uint32 ;
            units ms ;
          }
          leaf sum-jitter {
            description 'The sum value of jitter.'
                        ;
            type uint32 ;
            units ms ;
          }
          leaf pkt-loss-rate {
            description 'The ratio of lossing packets in the ICMP test.'
                        ;
            type string {
              length 2..4 {
                description 'The range of lossing packets ratio.'
                            ;
              }
            }
          }
          leaf probe-time {
            description 'The end time of ICMP test.'
                        ;
            type ncd:string-with-blank {
              length 19 {
                description 'The end time of ICMP test.'
                            ;
              }
            }
          }
          leaf destination-ipv6 {
            description 'The destination IPv6 address.'
                        ;
            type ncd:ipv6-address ;
            ncd:revise-date 2020-03-18 ;
          }
        }
      }
      container udp-results {
        description 'The UDP test result.'
                    ;
        list udp-result {
          description 'The UDP test result.'
                      ;
          key test-number ;
          leaf test-number {
            description 'The value of test Index,the upper limit of this parame'
                      + 'ter depend on the device.'
                        ;
            type uint32 {
              range 1..1024 {
                description 'The test number ranges from 1 to 1024.'
                            ;
              }
            }
          }
          leaf repeat-count {
            description 'The count of sending UDP packets.'
                        ;
            type uint16 {
              range 1..1000 {
                description 'The count of sending UDP packets.'
                            ;
              }
            }
          }
          leaf response-count {
            description 'The count of receiving UDP packets.'
                        ;
            type uint16 {
              range 0..1000 {
                description 'The count of receiving UDP packets.'
                            ;
              }
            }
          }
          leaf destination-ip {
            description 'The destination IPv4 address.'
                        ;
            type ncd:ipv4-address ;
          }
          leaf min-rtt {
            description 'The minimal value of RTT.'
                        ;
            type uint32 ;
            units ms ;
          }
          leaf max-rtt {
            description 'The maximal value of RTT.'
                        ;
            type uint32 ;
            units ms ;
          }
          leaf avg-rtt {
            description 'The averange value of RTT.'
                        ;
            type uint32 ;
            units ms ;
          }
          leaf sum-rtt {
            description 'The sum value of RTT.'
                        ;
            type uint32 ;
            units ms ;
          }
          leaf min-positive-jitter {
            description 'The minimal value of positive jitter.'
                        ;
            type uint32 ;
            units ms ;
          }
          leaf max-positive-jitter {
            description 'The maximal value of positive jitter.'
                        ;
            type uint32 ;
            units ms ;
          }
          leaf avg-positive-jitter {
            description 'The averange value of positive jitter.'
                        ;
            type uint32 ;
            units ms ;
          }
          leaf sum-positive-jitter {
            description 'The sum value of positive jitter.'
                        ;
            type uint32 ;
            units ms ;
          }
          leaf min-negative-jitter {
            description 'The minimal value of negative jitter.'
                        ;
            type uint32 ;
            units ms ;
          }
          leaf max-negative-jitter {
            description 'The maximal value of negative jitter.'
                        ;
            type uint32 ;
            units ms ;
          }
          leaf avg-negative-jitter {
            description 'The averange value of negative jitter.'
                        ;
            type uint32 ;
            units ms ;
          }
          leaf sum-negative-jitter {
            description 'The sum value of negative jitter.'
                        ;
            type uint32 ;
            units ms ;
          }
          leaf min-jitter {
            description 'The minimal value of jitter.'
                        ;
            type uint32 ;
            units ms ;
          }
          leaf max-jitter {
            description 'The maximal value of jitter.'
                        ;
            type uint32 ;
            units ms ;
          }
          leaf avg-jitter {
            description 'The averange value of jitter.'
                        ;
            type uint32 ;
            units ms ;
          }
          leaf sum-jitter {
            description 'The sum value of jitter.'
                        ;
            type uint32 ;
            units ms ;
          }
          leaf pkt-loss-rate {
            description 'The ratio of lossing packets in the UDP test'
                        ;
            type string {
              length 2..4 {
                description 'The range of lossing packets ratio.'
                            ;
              }
            }
          }
          leaf probe-time {
            description 'The end time of UDP test.'
                        ;
            type ncd:string-with-blank {
              length 19 {
                description 'The end time of UDP test.'
                            ;
              }
            }
          }
          leaf destination-ipv6 {
            description 'The destination IPv6 address.'
                        ;
            type ncd:ipv6-address ;
            ncd:revise-date 2020-03-18 ;
          }
        }
      }
      container tcp-results {
        description 'The TCP test result.'
                    ;
        list tcp-result {
          description 'The TCP test result.'
                      ;
          key test-number ;
          leaf test-number {
            description 'The value of test Index,the upper limit of this parame'
                      + 'ter depend on the device.'
                        ;
            type uint32 {
              range 1..1024 {
                description 'The test number ranges from 1 to 1024.'
                            ;
              }
            }
          }
          leaf repeat-count {
            description 'The count of sending link requests.'
                        ;
            type uint16 {
              range 1..200 {
                description 'The count of sending link requests.'
                            ;
              }
            }
          }
          leaf response-count {
            description 'The count of receiving link answer.'
                        ;
            type uint16 {
              range 0..200 {
                description 'The count of receiving link answer.'
                            ;
              }
            }
          }
          leaf destination-ip {
            description 'The destination IPv4 address.'
                        ;
            type ncd:ipv4-address ;
          }
          leaf min-rtt {
            description 'The minimal time of establishing link.'
                        ;
            type uint32 ;
            units ms ;
          }
          leaf max-rtt {
            description 'The maximal time of establishing link.'
                        ;
            type uint32 ;
            units ms ;
          }
          leaf avg-rtt {
            description 'The averange time of establishing link.'
                        ;
            type uint32 ;
            units ms ;
          }
          leaf sum-rtt {
            description 'The sum time of establishing link.'
                        ;
            type uint32 ;
            units ms ;
          }
          leaf probe-time {
            description 'The end time of TCP test.'
                        ;
            type ncd:string-with-blank {
              length 19 {
                description 'The end time of TCP test.'
                            ;
              }
            }
          }
          leaf destination-ipv6 {
            description 'The destination IPv6 address.'
                        ;
            type ncd:ipv6-address ;
            ncd:revise-date 2020-03-18 ;
          }
        }
      }
      container ftp-results {
        description 'The FTP test result.'
                    ;
        list ftp-result {
          description 'The FTP test result.'
                      ;
          key test-number ;
          leaf test-number {
            description 'The value of test Index,the upper limit of this parame'
                      + 'ter depend on the device.'
                        ;
            type uint32 {
              range 1..1024 {
                description 'The test number ranges from 1 to 1024.'
                            ;
              }
            }
          }
          leaf last-rtt {
            description 'The time is used to transfer this file.'
                        ;
            type uint32 ;
            units s ;
          }
          leaf read-bytes {
            description 'The size of this file.'
                        ;
            type uint32 ;
            units Byte ;
          }
          leaf probe-time {
            description 'The end time of FTP test.'
                        ;
            type ncd:string-with-blank {
              length 19 {
                description 'The end time of FTP test.'
                            ;
              }
            }
          }
        }
      }
      container dns-results {
        description 'The DNS test result.'
                    ;
        list dns-result {
          description 'The DNS test result.'
                      ;
          key test-number ;
          leaf test-number {
            description 'The value of test Index,the upper limit of this parame'
                      + 'ter depend on the device.'
                        ;
            type uint32 {
              range 1..1024 {
                description 'The test number ranges from 1 to 1024.'
                            ;
              }
            }
          }
          leaf repeat-count {
            description 'The count of sending DNS requests.'
                        ;
            type uint16 {
              range 1..10 {
                description 'The count of sending DNS requests.'
                            ;
              }
            }
          }
          leaf response-count {
            description 'The count of receiving right answer.'
                        ;
            type uint16 {
              range 0..10 {
                description 'The count of receiving right answer.'
                            ;
              }
            }
          }
          leaf destination-url {
            description 'The destination domain name.'
                        ;
            type string {
              length 1..128 {
                description 'The destination domain name.'
                            ;
              }
            }
          }
          leaf resolved-ip {
            description 'The domain name was resolved to an IP address through '
                      + 'the DNS.'
                        ;
            type ncd:ipv4-address ;
          }
          leaf min-rtt {
            description 'The minimal time of resolving a domain name.'
                        ;
            type uint32 ;
            units ms ;
          }
          leaf max-rtt {
            description 'The maximal time of resolving a domain name.'
                        ;
            type uint32 ;
            units ms ;
          }
          leaf avg-rtt {
            description 'The averange time of resolving a domain name.'
                        ;
            type uint32 ;
            units ms ;
          }
          leaf sum-rtt {
            description 'The sum time of resolving a domain name.'
                        ;
            type uint32 ;
            units ms ;
          }
          leaf probe-time {
            description 'The end time of DNS test.'
                        ;
            type ncd:string-with-blank {
              length 19 {
                description 'The end time of DNS test.'
                            ;
              }
            }
          }
        }
      }
      container udpjitter-results {
        description 'The udpjitter test result.'
                    ;
        list udpjitter-result {
          description 'The udpjitter test result.'
                      ;
          key test-number ;
          leaf test-number {
            description 'The value of test Index,the upper limit of this parame'
                      + 'ter depend on the device.'
                        ;
            type uint32 {
              range 1..1024 {
                description 'The test number ranges from 1 to 1024.'
                            ;
              }
            }
          }
          leaf repeat-count {
            description 'The count of sending UDP packets.'
                        ;
            type uint16 {
              range 1..1000 {
                description 'The count of sending UDP packets.'
                            ;
              }
            }
          }
          leaf response-count {
            description 'The count of receiving UDP packets.'
                        ;
            type uint16 {
              range 0..1000 {
                description 'The count of receiving UDP packets.'
                            ;
              }
            }
          }
          leaf destination-ip {
            description 'The destination IPv4 address.'
                        ;
            type ncd:ipv4-address ;
          }
          leaf min-rtt-sd {
            description 'The minimal value of delay from source to destination.'
                        ;
            type uint32 ;
            units ms ;
          }
          leaf max-rtt-sd {
            description 'The maximal value of delay from source to destination.'
                        ;
            type uint32 ;
            units ms ;
          }
          leaf avg-rtt-sd {
            description 'The averange value of delay from source to destination.'
                        ;
            type uint32 ;
            units ms ;
          }
          leaf sum-rtt-sd {
            description 'The sum value of delay from source to destination.'
                        ;
            type uint32 ;
            units ms ;
          }
          leaf min-rtt-ds {
            description 'The minimal value of delay from destination to source.'
                        ;
            type uint32 ;
            units ms ;
          }
          leaf max-rtt-ds {
            description 'The maximal value of delay from destination to source.'
                        ;
            type uint32 ;
            units ms ;
          }
          leaf avg-rtt-ds {
            description 'The averange value of delay from destination to source.'
                        ;
            type uint32 ;
            units ms ;
          }
          leaf sum-rtt-ds {
            description 'The sum value of delay from destination to source.'
                        ;
            type uint32 ;
            units ms ;
          }
          leaf min-positive-jitter-sd {
            description 'The minimal value of positive jitter from source to de'
                      + 'stination.'
                        ;
            type uint32 ;
            units ms ;
          }
          leaf max-positive-jitter-sd {
            description 'The maximal value of positive jitter from source to de'
                      + 'stination.'
                        ;
            type uint32 ;
            units ms ;
          }
          leaf avg-positive-jitter-sd {
            description 'The averange value of positive jitter from source to d'
                      + 'estination.'
                        ;
            type uint32 ;
            units ms ;
          }
          leaf sum-positive-jitter-sd {
            description 'The sum value of positive jitter from source to destin'
                      + 'ation.'
                        ;
            type uint32 ;
            units ms ;
          }
          leaf min-negative-jitter-sd {
            description 'The minimal value of negtive jitter from source to des'
                      + 'tination.'
                        ;
            type uint32 ;
            units ms ;
          }
          leaf max-negative-jitter-sd {
            description 'The maximal value of negtive jitter from source to des'
                      + 'tination.'
                        ;
            type uint32 ;
            units ms ;
          }
          leaf avg-negative-jitter-sd {
            description 'The averange value of negtive jitter from source to de'
                      + 'stination.'
                        ;
            type uint32 ;
            units ms ;
          }
          leaf sum-negative-jitter-sd {
            description 'The sum value of negtive jitter from source to destina'
                      + 'tion.'
                        ;
            type uint32 ;
            units ms ;
          }
          leaf min-positive-jitter-ds {
            description 'The minimal value of positive jitter from destination '
                      + 'to source.'
                        ;
            type uint32 ;
            units ms ;
          }
          leaf max-positive-jitter-ds {
            description 'The maximal value of positive jitter from destination '
                      + 'to source.'
                        ;
            type uint32 ;
            units ms ;
          }
          leaf avg-positive-jitter-ds {
            description 'The averange value of positive jitter from destination'
                      + ' to source.'
                        ;
            type uint32 ;
            units ms ;
          }
          leaf sum-positive-jitter-ds {
            description 'The sum value of positive jitter from destination to s'
                      + 'ource.'
                        ;
            type uint32 ;
            units ms ;
          }
          leaf min-negative-jitter-ds {
            description 'The minimal value of negtive jitter from destination t'
                      + 'o source.'
                        ;
            type uint32 ;
            units ms ;
          }
          leaf max-negative-jitter-ds {
            description 'The maximal value of negtive jitter from destination t'
                      + 'o source.'
                        ;
            type uint32 ;
            units ms ;
          }
          leaf avg-negative-jitter-ds {
            description 'The averange value of negtive jitter from destination '
                      + 'to source'
                        ;
            type uint32 ;
            units ms ;
          }
          leaf sum-negative-jitter-ds {
            description 'The sum value of negtive jitter from destination to so'
                      + 'urce.'
                        ;
            type uint32 ;
          }
          leaf pkt-loss-number-sd {
            description 'The number of lossing packets from source to destinati'
                      + 'on.'
                        ;
            type uint16 ;
          }
          leaf pkt-loss-number-ds {
            description 'The number of lossing packets from destination to sour'
                      + 'ce.'
                        ;
            type uint16 ;
          }
          leaf probe-time {
            description 'The end time of udpjitter test.'
                        ;
            type ncd:string-with-blank {
              length 19 {
                description 'The end time of udpjitter test.'
                            ;
              }
            }
          }
          leaf destination-ipv6 {
            description 'The destination IPv6 address.'
                        ;
            type ncd:ipv6-address ;
            ncd:revise-date 2020-03-18 ;
          }
        }
      }
      container snmp-results {
        description 'The SNMP test result.'
                    ;
        list snmp-result {
          description 'The SNMP test result.'
                      ;
          key test-number ;
          leaf test-number {
            description 'The value of test Index,the upper limit of this parame'
                      + 'ter depend on the device.'
                        ;
            type uint32 {
              range 1..1024 {
                description 'The test number ranges from 1 to 1024.'
                            ;
              }
            }
          }
          leaf last-rtt {
            description 'The time required to complete this test.'
                        ;
            type uint32 ;
            units ms ;
          }
          leaf probe-time {
            description 'The end time of SNMP test.'
                        ;
            type ncd:string-with-blank {
              length 19 {
                description 'The end time of SNMP test.'
                            ;
              }
            }
          }
        }
      }
      container http-results {
        description 'The HTTP test result.'
                    ;
        list http-result {
          description 'The HTTP test result.'
                      ;
          key test-number ;
          leaf test-number {
            description 'The value of test Index,the upper limit of this parame'
                      + 'ter depend on the device.'
                        ;
            type uint32 {
              range 1..1024 {
                description 'The test number ranges from 1 to 1024.'
                            ;
              }
            }
          }
          leaf repeat-count {
            description 'The count of sending HTTP request.'
                        ;
            type uint16 {
              range 1..10 {
                description 'The count of sending HTTP request.'
                            ;
              }
            }
          }
          leaf response-count {
            description 'The count of receiving HTTP answer.'
                        ;
            type uint16 {
              range 0..10 {
                description 'The count of receiving HTTP answer.'
                            ;
              }
            }
          }
          leaf destination-ip {
            description 'The destination IP address.'
                        ;
            type ncd:ipv4-address ;
          }
          leaf destination-url {
            description 'The destination domain name.'
                        ;
            type string {
              length 1..128 {
                description 'The destination domain name.'
                            ;
              }
            }
          }
          leaf min-dns-rtt {
            description 'The minimal time of resolving a domain name.'
                        ;
            type uint32 ;
            units ms ;
          }
          leaf max-dns-rtt {
            description 'The maximal time of resolving a domain name.'
                        ;
            type uint32 ;
            units ms ;
          }
          leaf avg-dns-rtt {
            description 'The averange time of resolving a domain name.'
                        ;
            type uint32 ;
            units ms ;
          }
          leaf sum-dns-rtt {
            description 'The sum time of resolving a domain name.'
                        ;
            type uint32 ;
            units ms ;
          }
          leaf min-tcp-connection-rtt {
            description 'The minimal time of establishing link.'
                        ;
            type uint32 ;
            units ms ;
          }
          leaf max-tcp-connection-rtt {
            description 'The maximal time of establishing link.'
                        ;
            type uint32 ;
            units ms ;
          }
          leaf avg-tcp-connection-rtt {
            description 'The averange time of establishing link.'
                        ;
            type uint32 ;
            units ms ;
          }
          leaf sum-tcp-connection-rtt {
            description 'The sum time of establishing link.'
                        ;
            type uint32 ;
            units ms ;
          }
          leaf min-http-connection-rtt {
            description 'The minimal time of completing http request.'
                        ;
            type uint32 ;
            units ms ;
          }
          leaf max-http-connection-rtt {
            description 'The maximal time of completing http request.'
                        ;
            type uint32 ;
            units ms ;
          }
          leaf avg-http-connection-rtt {
            description 'The averange time of completing http request.'
                        ;
            type uint32 ;
            units ms ;
          }
          leaf sum-http-connection-rtt {
            description 'The sum time of completing http request.'
                        ;
            type uint32 ;
            units ms ;
          }
          leaf min-rtt {
            description 'The minimal time required to complete this whole test.'
                        ;
            type uint32 ;
            units ms ;
          }
          leaf max-rtt {
            description 'The maximal time required to complete this whole test.'
                        ;
            type uint32 ;
            units ms ;
          }
          leaf avg-rtt {
            description 'The averange time required to complete this whole test.'
                        ;
            type uint32 ;
            units ms ;
          }
          leaf sum-rtt {
            description 'The sum time required to complete this whole test.'
                        ;
            type uint32 ;
            units ms ;
          }
          leaf probe-time {
            description 'The end time of HTTP test.'
                        ;
            type ncd:string-with-blank {
              length 19 {
                description 'The end time of HTTP test.'
                            ;
              }
            }
          }
        }
      }
      container icmpjitter-results {
        description 'The icmpjitter test result.'
                    ;
        list icmpjitter-result {
          description 'The icmpjitter test result.'
                      ;
          key test-number ;
          leaf test-number {
            description 'The value of test Index,the upper limit of this parame'
                      + 'ter depend on the device.'
                        ;
            type uint32 {
              range 1..1024 {
                description 'The test number ranges from 1 to 1024.'
                            ;
              }
            }
          }
          leaf repeat-count {
            description 'The count of sending ICMP packets.'
                        ;
            type uint16 {
              range 1..65535 {
                description 'The count of sending ICMP packets.'
                            ;
              }
            }
          }
          leaf response-count {
            description 'The count of receiving ICMP packets.'
                        ;
            type uint16 {
              range 0..65535 {
                description 'The count of receiving ICMP packets.'
                            ;
              }
            }
          }
          leaf destination-ip {
            description 'The destination IPv4 address.'
                        ;
            type ncd:ipv4-address ;
          }
          leaf min-rtt-sd {
            description 'The minimal value of delay from source to destination.'
                        ;
            type uint32 ;
            units ms ;
          }
          leaf max-rtt-sd {
            description 'The maximal value of delay from source to destination.'
                        ;
            type uint32 ;
            units ms ;
          }
          leaf avg-rtt-sd {
            description 'The averange value of delay from source to destination.'
                        ;
            type uint32 ;
            units ms ;
          }
          leaf sum-rtt-sd {
            description 'The sum value of delay from source to destination.'
                        ;
            type uint32 ;
            units ms ;
          }
          leaf min-rtt-ds {
            description 'The minimal value of delay from destination to source.'
                        ;
            type uint32 ;
            units ms ;
          }
          leaf max-rtt-ds {
            description 'The maximal value of delay from destination to source.'
                        ;
            type uint32 ;
            units ms ;
          }
          leaf avg-rtt-ds {
            description 'The averange value of delay from destination to source.'
                        ;
            type uint32 ;
            units ms ;
          }
          leaf sum-rtt-ds {
            description 'The sum value of delay from destination to source.'
                        ;
            type uint32 ;
            units ms ;
          }
          leaf min-positive-jitter-sd {
            description 'The minimal value of positive jitter from source to de'
                      + 'stination.'
                        ;
            type uint32 ;
            units ms ;
          }
          leaf max-positive-jitter-sd {
            description 'The maximal value of positive jitter from source to de'
                      + 'stination.'
                        ;
            type uint32 ;
            units ms ;
          }
          leaf avg-positive-jitter-sd {
            description 'The averange value of positive jitter from source to d'
                      + 'estination.'
                        ;
            type uint32 ;
            units ms ;
          }
          leaf sum-positive-jitter-sd {
            description 'The sum value of positive jitter from source to destin'
                      + 'ation.'
                        ;
            type uint32 ;
            units ms ;
          }
          leaf min-negative-jitter-sd {
            description 'The minimal value of negtive jitter from source to des'
                      + 'tination.'
                        ;
            type uint32 ;
            units ms ;
          }
          leaf max-negative-jitter-sd {
            description 'The maximal value of negtive jitter from source to des'
                      + 'tination.'
                        ;
            type uint32 ;
            units ms ;
          }
          leaf avg-negative-jitter-sd {
            description 'The averange value of negtive jitter from source to de'
                      + 'stination.'
                        ;
            type uint32 ;
            units ms ;
          }
          leaf sum-negative-jitter-sd {
            description 'The sum value of negtive jitter from source to destina'
                      + 'tion.'
                        ;
            type uint32 ;
            units ms ;
          }
          leaf min-positive-jitter-ds {
            description 'The minimal value of positive jitter from destination '
                      + 'to source.'
                        ;
            type uint32 ;
            units ms ;
          }
          leaf max-positive-jitter-ds {
            description 'The maximal value of positive jitter from destination '
                      + 'to source.'
                        ;
            type uint32 ;
            units ms ;
          }
          leaf avg-positive-jitter-ds {
            description 'The averange value of positive jitter from destination'
                      + ' to source.'
                        ;
            type uint32 ;
            units ms ;
          }
          leaf sum-positive-jitter-ds {
            description 'The sum value of positive jitter from destination to s'
                      + 'ource.'
                        ;
            type uint32 ;
            units ms ;
          }
          leaf min-negative-jitter-ds {
            description 'The minimal value of negtive jitter from destination t'
                      + 'o source.'
                        ;
            type uint32 ;
            units ms ;
          }
          leaf max-negative-jitter-ds {
            description 'The maximal value of negtive jitter from destination t'
                      + 'o source.'
                        ;
            type uint32 ;
            units ms ;
          }
          leaf avg-negative-jitter-ds {
            description 'The averange value of negtive jitter from destination '
                      + 'to source.'
                        ;
            type uint32 ;
            units ms ;
          }
          leaf sum-negative-jitter-ds {
            description 'The sum value of negtive jitter from destination to so'
                      + 'urce.'
                        ;
            type uint32 ;
            units ms ;
          }
          leaf probe-time {
            description 'The end time of ICMPjitter test.'
                        ;
            type ncd:string-with-blank {
              length 19 {
                description 'The end time of ICMPjitter test.'
                            ;
              }
            }
          }
          leaf min-rtt {
            description 'The minimum value of RTT.'
                        ;
            type uint32 ;
            units ms ;
            ncd:revise-date 2020-08-11 ;
          }
          leaf max-rtt {
            description 'The maximum value of RTT.'
                        ;
            type uint32 ;
            units ms ;
            ncd:revise-date 2020-08-11 ;
          }
          leaf avg-rtt {
            description 'The averange value of RTT.'
                        ;
            type uint32 ;
            units ms ;
            ncd:revise-date 2020-08-11 ;
          }
          leaf sum-rtt {
            description 'The sum value of RTT.'
                        ;
            type uint32 ;
            units ms ;
            ncd:revise-date 2020-08-11 ;
          }
          leaf cur-rtt {
            description 'The current value of RTT.'
                        ;
            type uint32 ;
            units ms ;
            ncd:revise-date 2020-08-11 ;
          }
          leaf min-delay-jitter {
            description 'The minimum value of jitter.'
                        ;
            type uint32 ;
            units ms ;
            ncd:revise-date 2020-08-11 ;
          }
          leaf max-delay-jitter {
            description 'The maximum value of jitter.'
                        ;
            type uint32 ;
            units ms ;
            ncd:revise-date 2020-08-11 ;
          }
          leaf avg-delay-jitter {
            description 'The averange value of jitter.'
                        ;
            type uint32 ;
            units ms ;
            ncd:revise-date 2020-08-11 ;
          }
          leaf sum-delay-jitter {
            description 'The sum value of jitter.'
                        ;
            type uint32 ;
            units ms ;
            ncd:revise-date 2020-08-11 ;
          }
          leaf cur-delay-jitter {
            description 'The current value of jitter.'
                        ;
            type uint32 ;
            units ms ;
            ncd:revise-date 2020-08-11 ;
          }
          leaf cur-delay-jitter-sd {
            description 'The current value of jitter from source to destination.'
                        ;
            type uint32 ;
            units ms ;
            ncd:revise-date 2020-08-11 ;
          }
          leaf cur-delay-jitter-ds {
            description 'The current value of jitter from destination to source.'
                        ;
            type uint32 ;
            units ms ;
            ncd:revise-date 2020-08-11 ;
          }
          leaf pkt-loss-num {
            description 'The number of lossing packets in the ICMP test.'
                        ;
            type uint16 ;
            ncd:revise-date 2020-08-11 ;
          }
          leaf pkt-loss-rate {
            description 'The ratio of lossing packets in the ICMP test.'
                        ;
            type string {
              length 2..4 {
                description 'The range of lossing packets ratio.'
                            ;
              }
            }
            ncd:revise-date 2020-08-11 ;
          }
          leaf destination-ipv6 {
            description 'The destination IPv6 address.'
                        ;
            type ncd:ipv6-address ;
            ncd:revise-date 2020-08-11 ;
          }
        }
      }
      container reflector-informations {
        description 'Reflector configuration information.'
                    ;
        list reflector-information {
          description 'Reflector configuration information.'
                      ;
          key reflector-id ;
          leaf reflector-id {
            description 'Reflector ID,ranges from 1 to 65535.'
                        ;
            type uint16 {
              range 1..65535 {
                description 'The range of reflector ID.'
                            ;
              }
            }
          }
          leaf reflector-mode {
            description 'Reflector mode,including L2 mode,L3 mode.'
                        ;
            type enumeration {
              enum l2 {
                value 2 ;
                description 'The reflector mode is L2.'
                            ;
              }
              enum l3 {
                value 3 ;
                description 'The reflector mode is L3.'
                            ;
              }
            }
          }
          leaf inbound-interface {
            description 'Interface name.'
                        ;
            type ncd:ifname {
              length 1..31 {
                description 'The range of interface name length.'
                            ;
              }
            }
          }
          leaf interface-mode {
            description 'Interface mode,including share mode,exclusive mode.'
                        ;
            type enumeration {
              enum share {
                value 1 ;
                description 'The interface mode is share mode.'
                            ;
              }
              enum exclusive {
                value 2 ;
                description 'The interface mode is exclusive mode.'
                            ;
              }
            }
          }
          leaf test-mode {
            description 'Test mode,including online and offline.'
                        ;
            type enumeration {
              enum online {
                value 1 ;
                description 'The mode is online.'
                            ;
              }
              enum offline {
                value 2 ;
                description 'The mode is offline.'
                            ;
              }
            }
          }
          leaf disnontest-8021p {
            description 'The value of discard-non-test priority-8021p in share '
                      + 'mode,ranges from 0 to 7,255 is invalid.'
                        ;
            type uint8 {
              range '0..7 | 255'
                    {
                description 'The range of priority-8021p,255 is invalid.'
                            ;
              }
            }
          }
          leaf disnontest-dscp {
            description 'The value of discard-non-test DSCP in share mode,range'
                      + 's from 0 to 63,255 is invalid.'
                        ;
            type uint8 {
              range '0..63 | 255'
                    {
                description 'The range of DSCP,255 is invalid.'
                            ;
              }
            }
          }
          leaf ageing-time {
            description 'The value of ageing time,ranges from 10s to 173400s,0 '
                      + 'means continuous.'
                        ;
            type uint32 {
              range '0 | 10..173400'
                    {
                description 'The ranges of ageing time,0 means continuous.'
                            ;
              }
            }
            units s ;
          }
          leaf source-mac {
            description 'The source MAC address.'
                        ;
            type ncd:mac-address-none-zero ;
          }
          leaf destination-mac {
            description 'The destination MAC address.'
                        ;
            type ncd:mac-address-none-zero ;
          }
          leaf source-ip {
            description 'The source IPv4 address.'
                        ;
            type ncd:ipv4-address-none-zero ;
          }
          leaf destination-ip {
            description 'The destination IPv4 address.'
                        ;
            type ncd:ipv4-address-none-zero ;
          }
          leaf source-port {
            description 'The source port,ranges from 1 to 65535.'
                        ;
            type uint16 {
              range 1..65535 {
                description 'The range of port number.'
                            ;
              }
            }
          }
          leaf destination-port {
            description 'The destination port,ranges from 1 to 65535.'
                        ;
            type uint16 {
              range 1..65535 {
                description 'The range of port number.'
                            ;
              }
            }
          }
          leaf vlan-id {
            description 'The value of vlan ID,ranges from 1 to 4094,0 is invali'
                      + 'd.'
                        ;
            type uint16 {
              range 0..4094 {
                description 'The range of vlan ID,0 is invalid.'
                            ;
              }
            }
          }
          leaf internal-vlan-id {
            description 'The value of internal vlan ID,ranges from 1 to 4094,0 '
                      + 'is invalid.'
                        ;
            type uint16 {
              range 0..4094 {
                description 'The range of vlan ID,0 is invalid.'
                            ;
              }
            }
          }
          leaf external-vlan-id {
            description 'The value of external vlan ID,ranges from 1 to 4094,0 '
                      + 'is invalid.'
                        ;
            type uint16 {
              range 0..4094 {
                description 'The range of vlan ID,0 is invalid.'
                            ;
              }
            }
          }
          leaf priority-8021p {
            description 'The value of priority-8021p,ranges from 0 to 7,255 is '
                      + 'invalid.'
                        ;
            type uint8 {
              range '0..7 | 255'
                    {
                description 'The range of priority-8021p,255 is invalid.'
                            ;
              }
            }
          }
          leaf dscp {
            description 'The value of DSCP,ranges from 0 to 63,255 is invalid.'
                        ;
            type uint8 {
              range '0..63 | 255'
                    {
                description 'The range of DSCP,255 is invalid.'
                            ;
              }
            }
          }
          leaf free-arp-status {
            description 'The free ARP status,including enable and disable.'
                        ;
            type enumeration {
              enum disable {
                value 0 ;
                description 'The free ARP status is disable.'
                            ;
              }
              enum enable {
                value 1 ;
                description 'The free ARP status is enable.'
                            ;
              }
            }
          }
          leaf free-arp-ip {
            description 'The local IPv4 address of free ARP.'
                        ;
            type ncd:ipv4-address-none-zero ;
          }
          leaf free-arp-vlan-id {
            description 'The value of vlan ID,ranges from 1 to 4094,0 is invali'
                      + 'd.'
                        ;
            type uint16 {
              range 0..4094 {
                description 'The range of vlan ID,0 is invalid.'
                            ;
              }
            }
          }
          leaf free-arp-internal-id {
            description 'The value of internal vlan ID,ranges from 1 to 4094,0 '
                      + 'is invalid.'
                        ;
            type uint16 {
              range 0..4094 {
                description 'The range of vlan ID,0 is invalid.'
                            ;
              }
            }
          }
          leaf free-arp-external-id {
            description 'The value of external vlan ID,ranges from 1 to 4094,0 '
                      + 'is invalid.'
                        ;
            type uint16 {
              range 0..4094 {
                description 'The range of vlan ID,0 is invalid.'
                            ;
              }
            }
          }
          leaf free-arp-interval {
            description 'The value of interval,ranges from 1s to 14400s.'
                        ;
            type uint32 {
              range 0..14400 {
                description 'The range of free ARP interval,0 is invalid.'
                            ;
              }
            }
            units s ;
          }
        }
        ncd:revise-date 2015-11-24 ;
      }
      container twamp-reflector-informations {
        list twamp-reflector-information {
          key reflector-id ;
          leaf reflector-id {
            description 'Reflector ID,ranges from 1 to 65535.'
                        ;
            type uint16 {
              range 1..65535 {
                description 'The range of reflector ID.'
                            ;
              }
            }
          }
          leaf inbound-interface {
            description 'Interface name.'
                        ;
            type ncd:ifname {
              length 1..31 {
                description 'The range of interface name length.'
                            ;
              }
            }
          }
          leaf test-mode {
            description 'Test mode,including online and offline.'
                        ;
            type enumeration {
              enum online {
                value 1 ;
                description 'The mode is online.'
                            ;
              }
              enum offline {
                value 2 ;
                description 'The mode is offline.'
                            ;
              }
              enum null {
                value 0 ;
                description 'The mode is not configured.'
                            ;
              }
            }
          }
          leaf source-mac {
            description 'The source MAC address.'
                        ;
            type ncd:mac-address-none-zero ;
          }
          leaf destination-mac {
            description 'The destination MAC address.'
                        ;
            type ncd:mac-address-none-zero ;
          }
          leaf source-ip {
            description 'The source IPv4 address.'
                        ;
            type ncd:ipv4-address-none-zero ;
          }
          leaf destination-ip {
            description 'The destination IPv4 address.'
                        ;
            type ncd:ipv4-address-none-zero ;
          }
          leaf source-port {
            description 'The source port,ranges from 1 to 65535,0 is invalid.'
                        ;
            type uint16 {
              range 0..65535 {
                description 'The range of port number.'
                            ;
              }
            }
          }
          leaf destination-port {
            description 'The destination port,ranges from 1 to 65535.'
                        ;
            type uint16 {
              range 1..65535 {
                description 'The range of port number.'
                            ;
              }
            }
          }
          leaf vlan-id {
            description 'The value of vlan ID,ranges from 1 to 4094,0 is invali'
                      + 'd.'
                        ;
            type uint16 {
              range 0..4094 {
                description 'The range of vlan ID,0 is invalid.'
                            ;
              }
            }
          }
          leaf internal-vlan-id {
            description 'The value of internal vlan ID,ranges from 1 to 4094,0 '
                      + 'is invalid.'
                        ;
            type uint16 {
              range 0..4094 {
                description 'The range of vlan ID,0 is invalid.'
                            ;
              }
            }
          }
          leaf external-vlan-id {
            description 'The value of external vlan ID,ranges from 1 to 4094,0 '
                      + 'is invalid.'
                        ;
            type uint16 {
              range 0..4094 {
                description 'The range of vlan ID,0 is invalid.'
                            ;
              }
            }
          }
          leaf priority-8021p {
            description 'The value of priority-8021p,ranges from 0 to 7,255 is '
                      + 'invalid.'
                        ;
            type uint8 {
              range '0..7 | 255'
                    {
                description 'The range of priority-8021p,255 is invalid.'
                            ;
              }
            }
          }
          leaf dscp {
            description 'The value of DSCP,ranges from 0 to 63,255 is invalid.'
                        ;
            type uint8 {
              range '0..63 | 255'
                    {
                description 'The range of DSCP,255 is invalid.'
                            ;
              }
            }
          }
          leaf timestamp-format {
            if-feature timestamp-format ;
            description 'Timestamp format,including PTP and NTP.'
                        ;
            type enumeration {
              enum ptp {
                value 1 ;
                description 'PTP format.'
                            ;
              }
              enum ntp {
                value 2 ;
                description 'NTP format.'
                            ;
              }
            }
            ncd:revise-date 2017-08-15 ;
          }
          leaf ageing-time {
            description 'The value of ageing time,ranges from 10s to 173400s,0 '
                      + 'means continuous.'
                        ;
            type uint32 {
              range '0 | 10..173400'
                    {
                description 'The ranges of ageing time,0 means continuous.'
                            ;
              }
            }
            units s ;
          }
          leaf free-arp-status {
            description 'The free ARP status,including enable and disable.'
                        ;
            type enumeration {
              enum disable {
                value 0 ;
                description 'The free ARP status is disable.'
                            ;
              }
              enum enable {
                value 1 ;
                description 'The free ARP status is enable.'
                            ;
              }
            }
          }
          leaf free-arp-ip {
            description 'The local IPv4 address of free ARP.'
                        ;
            type ncd:ipv4-address-none-zero ;
          }
          leaf free-arp-vlan-id {
            description 'The value of vlan ID,ranges from 1 to 4094,0 is invali'
                      + 'd.'
                        ;
            type uint16 {
              range 0..4094 {
                description 'The range of vlan ID,0 is invalid.'
                            ;
              }
            }
          }
          leaf free-arp-internal-id {
            description 'The value of internal vlan ID,ranges from 1 to 4094,0 '
                      + 'is invalid.'
                        ;
            type uint16 {
              range 0..4094 {
                description 'The range of vlan ID,0 is invalid.'
                            ;
              }
            }
          }
          leaf free-arp-external-id {
            description 'The value of external vlan ID,ranges from 1 to 4094,0 '
                      + 'is invalid.'
                        ;
            type uint16 {
              range 0..4094 {
                description 'The range of vlan ID,0 is invalid.'
                            ;
              }
            }
          }
          leaf free-arp-interval {
            description 'The value of interval,ranges from 1s to 14400s.'
                        ;
            type uint32 {
              range 0..14400 {
                description 'The range of free ARP interval,0 is invalid.'
                            ;
              }
            }
            units s ;
          }
        }
        ncd:revise-date 2016-02-17 ;
      }
      container light-twamp-result {
        status obsolete {
          ncd:revise-date 2020-07-16 ;
        }
        description 'The test result of light TWAMP.'
                    ;
        list light-twamp-result {
          key test-number ;
          leaf test-number {
            description 'The value of test index,the upper limit of this parame'
                      + 'ter depends on the device.'
                        ;
            type uint32 ;
          }
          leaf packet-send-number {
            description 'The count of sending packets.'
                        ;
            type uint32 {
              range 0..4294967295 {
                description 'The range of sending packet number.'
                            ;
              }
            }
          }
          leaf packet-receive-number {
            description 'The count of receiving packets.'
                        ;
            type uint32 {
              range 0..4294967295 {
                description 'The range of receiving packet number.'
                            ;
              }
            }
          }
          leaf packet-loss-number {
            description 'The count of lossing packets.'
                        ;
            type uint32 {
              range 0..4294967295 {
                description 'The range of packe lossing number.'
                            ;
              }
            }
          }
          leaf packet-loss-ratio {
            description 'The packet loss ratio,precision is 1/1000000.'
                        ;
            type uint32 {
              range 0..4294967295 {
                description 'The range of packet lossing ratio.'
                            ;
              }
            }
          }
          leaf two-way-time-delay {
            description 'Two way packet delay.'
                        ;
            type uint64 ;
            units ns ;
          }
          leaf two-way-min-delay {
            description 'The minimum two way packet delay.'
                        ;
            type uint64 ;
            units ns ;
          }
          leaf two-way-max-delay {
            description 'The maximum two way packet delay.'
                        ;
            type uint64 ;
            units ns ;
          }
          leaf two-way-avg-delay {
            description 'The average two way packet delay.'
                        ;
            type uint64 ;
            units ns ;
          }
          leaf two-way-delay-jitter {
            description 'The two way packet delay jitter.'
                        ;
            type uint64 ;
            units ns ;
          }
          leaf two-way-min-jitter {
            description 'The minimum two way packet delay jitter.'
                        ;
            type uint64 ;
            units ns ;
          }
          leaf two-way-max-jitter {
            description 'The maximum two way packet delay jitter.'
                        ;
            type uint64 ;
            units ns ;
          }
          leaf two-way-avg-jitter {
            description 'The average two way packet delay jitter.'
                        ;
            type uint64 ;
            units ns ;
          }
          leaf forward-time-delay {
            description 'The forward packet delay.'
                        ;
            type uint64 ;
            units ns ;
          }
          leaf forward-min-delay {
            description 'The minimum forward packet delay.'
                        ;
            type uint64 ;
            units ns ;
          }
          leaf forward-max-delay {
            description 'The maximum forward packet delay.'
                        ;
            type uint64 ;
            units ns ;
          }
          leaf forward-avg-delay {
            description 'The average forward packet delay.'
                        ;
            type uint64 ;
            units ns ;
          }
          leaf forward-delay-jitter {
            description 'The forward packet delay jitter.'
                        ;
            type uint64 ;
            units ns ;
          }
          leaf forward-min-jitter {
            description 'The minimum forward packet delay jitter.'
                        ;
            type uint64 ;
            units ns ;
          }
          leaf forward-max-jitter {
            description 'The maximum forward packet delay jitter.'
                        ;
            type uint64 ;
            units ns ;
          }
          leaf forward-avg-jitter {
            description 'The average forward packet delay jitter.'
                        ;
            type uint64 ;
            units ns ;
          }
          leaf reverse-time-delay {
            description 'The reverse packet delay.'
                        ;
            type uint64 ;
            units ns ;
          }
          leaf reverse-min-delay {
            description 'The minimum reverse packet delay.'
                        ;
            type uint64 ;
            units ns ;
          }
          leaf reverse-max-delay {
            description 'The maximum reverse packet delay.'
                        ;
            type uint64 ;
            units ns ;
          }
          leaf reverse-avg-delay {
            description 'The average reverse packet delay.'
                        ;
            type uint64 ;
            units ns ;
          }
          leaf reverse-delay-jitter {
            description 'The reverse packet delay jitter.'
                        ;
            type uint64 ;
            units ns ;
          }
          leaf reverse-min-jitter {
            description 'The minimum reverse packet delay jitter.'
                        ;
            type uint64 ;
            units ns ;
          }
          leaf reverse-max-jitter {
            description 'The maximum reverse packet delay jitter.'
                        ;
            type uint64 ;
            units ns ;
          }
          leaf reverse-avg-jitter {
            description 'The average reverse packet delay jitter.'
                        ;
            type uint64 ;
            units ns ;
          }
        }
        ncd:revise-date 2019-06-24 ;
      }
      container light-twamp-results {
        description 'The test result of light TWAMP.'
                    ;
        list light-twamp-result {
          key test-number ;
          leaf test-number {
            description 'The value of test index,the upper limit of this parame'
                      + 'ter depends on the device.'
                        ;
            type uint32 ;
          }
          leaf packet-send-number {
            description 'The count of sending packets.'
                        ;
            type uint32 {
              range 0..4294967295 {
                description 'The range of sending packet number.'
                            ;
              }
            }
          }
          leaf packet-receive-number {
            description 'The count of receiving packets.'
                        ;
            type uint32 {
              range 0..4294967295 {
                description 'The range of receiving packet number.'
                            ;
              }
            }
          }
          leaf packet-loss-number {
            description 'The count of lossing packets.'
                        ;
            type uint32 {
              range 0..4294967295 {
                description 'The range of packe lossing number.'
                            ;
              }
            }
          }
          leaf packet-loss-ratio {
            description 'The packet loss ratio,precision is 1/1000000.'
                        ;
            type uint32 {
              range 0..4294967295 {
                description 'The range of packet lossing ratio.'
                            ;
              }
            }
          }
          leaf two-way-time-delay {
            description 'Two way packet delay.'
                        ;
            type uint64 ;
            units ns ;
          }
          leaf two-way-min-delay {
            description 'The minimum two way packet delay.'
                        ;
            type uint64 ;
            units ns ;
          }
          leaf two-way-max-delay {
            description 'The maximum two way packet delay.'
                        ;
            type uint64 ;
            units ns ;
          }
          leaf two-way-avg-delay {
            description 'The average two way packet delay.'
                        ;
            type uint64 ;
            units ns ;
          }
          leaf two-way-delay-jitter {
            description 'The two way packet delay jitter.'
                        ;
            type uint64 ;
            units ns ;
          }
          leaf two-way-min-jitter {
            description 'The minimum two way packet delay jitter.'
                        ;
            type uint64 ;
            units ns ;
          }
          leaf two-way-max-jitter {
            description 'The maximum two way packet delay jitter.'
                        ;
            type uint64 ;
            units ns ;
          }
          leaf two-way-avg-jitter {
            description 'The average two way packet delay jitter.'
                        ;
            type uint64 ;
            units ns ;
          }
          leaf forward-time-delay {
            description 'The forward packet delay.'
                        ;
            type uint64 ;
            units ns ;
          }
          leaf forward-min-delay {
            description 'The minimum forward packet delay.'
                        ;
            type uint64 ;
            units ns ;
          }
          leaf forward-max-delay {
            description 'The maximum forward packet delay.'
                        ;
            type uint64 ;
            units ns ;
          }
          leaf forward-avg-delay {
            description 'The average forward packet delay.'
                        ;
            type uint64 ;
            units ns ;
          }
          leaf forward-delay-jitter {
            description 'The forward packet delay jitter.'
                        ;
            type uint64 ;
            units ns ;
          }
          leaf forward-min-jitter {
            description 'The minimum forward packet delay jitter.'
                        ;
            type uint64 ;
            units ns ;
          }
          leaf forward-max-jitter {
            description 'The maximum forward packet delay jitter.'
                        ;
            type uint64 ;
            units ns ;
          }
          leaf forward-avg-jitter {
            description 'The average forward packet delay jitter.'
                        ;
            type uint64 ;
            units ns ;
          }
          leaf reverse-time-delay {
            description 'The reverse packet delay.'
                        ;
            type uint64 ;
            units ns ;
          }
          leaf reverse-min-delay {
            description 'The minimum reverse packet delay.'
                        ;
            type uint64 ;
            units ns ;
          }
          leaf reverse-max-delay {
            description 'The maximum reverse packet delay.'
                        ;
            type uint64 ;
            units ns ;
          }
          leaf reverse-avg-delay {
            description 'The average reverse packet delay.'
                        ;
            type uint64 ;
            units ns ;
          }
          leaf reverse-delay-jitter {
            description 'The reverse packet delay jitter.'
                        ;
            type uint64 ;
            units ns ;
          }
          leaf reverse-min-jitter {
            description 'The minimum reverse packet delay jitter.'
                        ;
            type uint64 ;
            units ns ;
          }
          leaf reverse-max-jitter {
            description 'The maximum reverse packet delay jitter.'
                        ;
            type uint64 ;
            units ns ;
          }
          leaf reverse-avg-jitter {
            description 'The average reverse packet delay jitter.'
                        ;
            type uint64 ;
            units ns ;
          }
        }
        ncd:revise-date 2020-07-16 ;
      }
    }
  }
  container operation {
    config false ;
    description 'SQA operations model Info.'
                ;
    container sqa {
      description 'SQA operation parameters.'
                  ;
      container test-operations {
        description 'The operation for this test.'
                    ;
        list test-operation {
          description 'The operation for this test.'
                      ;
          key number ;
          leaf number {
            description 'The value of test Index,the upper limit of this parame'
                      + 'ter depend on the device.'
                        ;
            type uint32 {
              range 1..1024 {
                description 'The test number ranges from 1 to 1024.'
                            ;
              }
            }
          }
          leaf operation {
            description 'Start or stop this test.'
                        ;
            type enumeration {
              enum begin {
                value 1 ;
                description 'Start this test.'
                            ;
              }
              enum stop {
                value 2 ;
                description 'Stop this test.'
                            ;
              }
            }
            mandatory true ;
          }
        }
      }
    }
  }
  notification icmp-event {
    description 'The ICMP test result.'
                ;
    list icmp-result {
      description 'The ICMP test result.'
                  ;
      key test-number ;
      leaf test-number {
        config false ;
        description 'The value of test index,the upper limit of this parameter '
                  + 'depends on the device.'
                    ;
        type uint32 {
          range 1..1024 {
            description 'The test number ranges from 1 to 1024.'
                        ;
          }
        }
      }
      leaf repeat-count {
        config false ;
        description 'The count of sending ICMP packets.'
                    ;
        type uint16 {
          range 1..65535 {
            description 'The count of sending ICMP packets.'
                        ;
          }
        }
      }
      leaf response-count {
        config false ;
        description 'The count of receiving ICMP packets.'
                    ;
        type uint16 {
          range 0..65535 {
            description 'The count of receiving ICMP packets.'
                        ;
          }
        }
      }
      leaf destination-ip {
        config false ;
        description 'The destination IPv4 address.'
                    ;
        type ncd:ipv4-address ;
      }
      leaf min-rtt {
        config false ;
        description 'The minimal value of RTT.'
                    ;
        type uint32 ;
        units ms ;
      }
      leaf max-rtt {
        config false ;
        description 'The maximal value of RTT.'
                    ;
        type uint32 ;
        units ms ;
      }
      leaf avg-rtt {
        config false ;
        description 'The averange value of RTT.'
                    ;
        type uint32 ;
        units ms ;
      }
      leaf sum-rtt {
        config false ;
        description 'The sum value of RTT.'
                    ;
        type uint32 ;
        units ms ;
      }
      leaf min-positive-jitter {
        config false ;
        description 'The minimal value of positive jitter.'
                    ;
        type uint32 ;
        units ms ;
      }
      leaf max-positive-jitter {
        config false ;
        description 'The maximal value of positive jitter.'
                    ;
        type uint32 ;
        units ms ;
      }
      leaf avg-positive-jitter {
        config false ;
        description 'The averange value of positive jitter.'
                    ;
        type uint32 ;
        units ms ;
      }
      leaf sum-positive-jitter {
        config false ;
        description 'The sum value of positive jitter.'
                    ;
        type uint32 ;
        units ms ;
      }
      leaf min-negative-jitter {
        config false ;
        description 'The minimal value of negative jitter.'
                    ;
        type uint32 ;
        units ms ;
      }
      leaf max-negative-jitter {
        config false ;
        description 'The maximal value of negative jitter.'
                    ;
        type uint32 ;
        units ms ;
      }
      leaf avg-negative-jitter {
        config false ;
        description 'The averange value of negative jitter.'
                    ;
        type uint32 ;
        units ms ;
      }
      leaf sum-negative-jitter {
        config false ;
        description 'The sum value of negative jitter.'
                    ;
        type uint32 ;
        units ms ;
      }
      leaf min-jitter {
        config false ;
        description 'The minimal value of jitter.'
                    ;
        type uint32 ;
        units ms ;
      }
      leaf max-jitter {
        config false ;
        description 'The maximal value of jitter.'
                    ;
        type uint32 ;
        units ms ;
      }
      leaf avg-jitter {
        config false ;
        description 'The averange value of jitter.'
                    ;
        type uint32 ;
        units ms ;
      }
      leaf sum-jitter {
        config false ;
        description 'The sum value of jitter.'
                    ;
        type uint32 ;
        units ms ;
      }
      leaf pkt-loss-rate {
        config false ;
        description 'The ratio of lossing packets in the ICMP test.'
                    ;
        type string {
          length 2..4 {
            description 'The range of lossing packets ratio.'
                        ;
          }
        }
      }
      leaf probe-time {
        config false ;
        description 'The end time of ICMP test.'
                    ;
        type ncd:string-with-blank {
          length 19 {
            description 'The end time of ICMP test.'
                        ;
          }
        }
      }
      leaf destination-ipv6 {
        config false ;
        description 'The destination IPv6 address.'
                    ;
        type ncd:ipv6-address ;
        ncd:revise-date 2020-03-18 ;
      }
    }
    ncd:revise-date 2015-08-20 ;
  }
  notification udp-event {
    description 'The UDP test result.'
                ;
    list udp-result {
      description 'The UDP test result.'
                  ;
      key test-number ;
      leaf test-number {
        config false ;
        description 'The value of test index,the upper limit of this parameter '
                  + 'depends on the device.'
                    ;
        type uint32 {
          range 1..1024 {
            description 'The test number ranges from 1 to 1024.'
                        ;
          }
        }
      }
      leaf repeat-count {
        config false ;
        description 'The count of sending UDP packets.'
                    ;
        type uint16 {
          range 1..1000 {
            description 'The count of sending UDP packets.'
                        ;
          }
        }
      }
      leaf response-count {
        config false ;
        description 'The count of receiving UDP packets.'
                    ;
        type uint16 {
          range 0..1000 {
            description 'The count of receiving UDP packets.'
                        ;
          }
        }
      }
      leaf destination-ip {
        config false ;
        description 'The destination IPv4 address.'
                    ;
        type ncd:ipv4-address ;
      }
      leaf min-rtt {
        config false ;
        description 'The minimal value of RTT.'
                    ;
        type uint32 ;
        units ms ;
      }
      leaf max-rtt {
        config false ;
        description 'The maximal value of RTT.'
                    ;
        type uint32 ;
        units ms ;
      }
      leaf avg-rtt {
        config false ;
        description 'The averange value of RTT.'
                    ;
        type uint32 ;
        units ms ;
      }
      leaf sum-rtt {
        config false ;
        description 'The sum value of RTT.'
                    ;
        type uint32 ;
        units ms ;
      }
      leaf min-positive-jitter {
        config false ;
        description 'The minimal value of positive jitter.'
                    ;
        type uint32 ;
        units ms ;
      }
      leaf max-positive-jitter {
        config false ;
        description 'The maximal value of positive jitter.'
                    ;
        type uint32 ;
        units ms ;
      }
      leaf avg-positive-jitter {
        config false ;
        description 'The averange value of positive jitter.'
                    ;
        type uint32 ;
        units ms ;
      }
      leaf sum-positive-jitter {
        config false ;
        description 'The sum value of positive jitter.'
                    ;
        type uint32 ;
        units ms ;
      }
      leaf min-negative-jitter {
        config false ;
        description 'The minimal value of negative jitter.'
                    ;
        type uint32 ;
        units ms ;
      }
      leaf max-negative-jitter {
        config false ;
        description 'The maximal value of negative jitter.'
                    ;
        type uint32 ;
        units ms ;
      }
      leaf avg-negative-jitter {
        config false ;
        description 'The averange value of negative jitter.'
                    ;
        type uint32 ;
        units ms ;
      }
      leaf sum-negative-jitter {
        config false ;
        description 'The sum value of negative jitter.'
                    ;
        type uint32 ;
        units ms ;
      }
      leaf min-jitter {
        config false ;
        description 'The minimal value of jitter.'
                    ;
        type uint32 ;
        units ms ;
      }
      leaf max-jitter {
        config false ;
        description 'The maximal value of jitter.'
                    ;
        type uint32 ;
        units ms ;
      }
      leaf avg-jitter {
        config false ;
        description 'The averange value of jitter.'
                    ;
        type uint32 ;
        units ms ;
      }
      leaf sum-jitter {
        config false ;
        description 'The sum value of jitter.'
                    ;
        type uint32 ;
        units ms ;
      }
      leaf pkt-loss-rate {
        config false ;
        description 'The ratio of lossing packets in the UDP test'
                    ;
        type string {
          length 2..4 {
            description 'The range of lossing packets ratio.'
                        ;
          }
        }
      }
      leaf probe-time {
        config false ;
        description 'The end time of UDP test.'
                    ;
        type ncd:string-with-blank {
          length 19 {
            description 'The end time of UDP test.'
                        ;
          }
        }
      }
      leaf destination-ipv6 {
        config false ;
        description 'The destination IPv6 address.'
                    ;
        type ncd:ipv6-address ;
        ncd:revise-date 2020-03-18 ;
      }
    }
    ncd:revise-date 2015-08-20 ;
  }
  notification tcp-event {
    description 'The TCP test result.'
                ;
    list tcp-result {
      description 'The TCP test result.'
                  ;
      key test-number ;
      leaf test-number {
        config false ;
        description 'The value of test index,the upper limit of this parameter '
                  + 'depends on the device.'
                    ;
        type uint32 {
          range 1..1024 {
            description 'The test number ranges from 1 to 1024.'
                        ;
          }
        }
      }
      leaf repeat-count {
        config false ;
        description 'The count of sending link requests.'
                    ;
        type uint16 {
          range 1..200 {
            description 'The count of sending link requests.'
                        ;
          }
        }
      }
      leaf response-count {
        config false ;
        description 'The count of receiving link answer.'
                    ;
        type uint16 {
          range 0..200 {
            description 'The count of receiving link answer.'
                        ;
          }
        }
      }
      leaf destination-ip {
        config false ;
        description 'The destination IPv4 address.'
                    ;
        type ncd:ipv4-address ;
      }
      leaf min-rtt {
        config false ;
        description 'The minimal time of establishing link.'
                    ;
        type uint32 ;
        units ms ;
      }
      leaf max-rtt {
        config false ;
        description 'The maximal time of establishing link.'
                    ;
        type uint32 ;
        units ms ;
      }
      leaf avg-rtt {
        config false ;
        description 'The averange time of establishing link.'
                    ;
        type uint32 ;
        units ms ;
      }
      leaf sum-rtt {
        config false ;
        description 'The sum time of establishing link.'
                    ;
        type uint32 ;
        units ms ;
      }
      leaf probe-time {
        config false ;
        description 'The end time of TCP test.'
                    ;
        type ncd:string-with-blank {
          length 19 {
            description 'The end time of TCP test.'
                        ;
          }
        }
      }
      leaf destination-ipv6 {
        config false ;
        description 'The destination IPv6 address.'
                    ;
        type ncd:ipv6-address ;
        ncd:revise-date 2020-03-18 ;
      }
    }
    ncd:revise-date 2015-08-20 ;
  }
  notification ftp-event {
    description 'The FTP test result.'
                ;
    list ftp-result {
      description 'The FTP test result.'
                  ;
      key test-number ;
      leaf test-number {
        config false ;
        description 'The value of test index,the upper limit of this parameter '
                  + 'depends on the device.'
                    ;
        type uint32 {
          range 1..1024 {
            description 'The test number ranges from 1 to 1024.'
                        ;
          }
        }
      }
      leaf last-rtt {
        config false ;
        description 'The time is used to transfer this file.'
                    ;
        type uint32 ;
        units s ;
      }
      leaf read-bytes {
        config false ;
        description 'The size of this file.'
                    ;
        type uint32 ;
        units Byte ;
      }
      leaf probe-time {
        config false ;
        description 'The end time of FTP test.'
                    ;
        type ncd:string-with-blank {
          length 19 {
            description 'The end time of FTP test.'
                        ;
          }
        }
      }
    }
    ncd:revise-date 2015-08-20 ;
  }
  notification dns-event {
    description 'The DNS test result.'
                ;
    list dns-result {
      description 'The DNS test result.'
                  ;
      key test-number ;
      leaf test-number {
        config false ;
        description 'The value of test index,the upper limit of this parameter '
                  + 'depends on the device.'
                    ;
        type uint32 {
          range 1..1024 {
            description 'The test number ranges from 1 to 1024.'
                        ;
          }
        }
      }
      leaf repeat-count {
        config false ;
        description 'The count of sending DNS requests.'
                    ;
        type uint16 {
          range 1..10 {
            description 'The count of sending DNS requests.'
                        ;
          }
        }
      }
      leaf response-count {
        config false ;
        description 'The count of receiving right answer.'
                    ;
        type uint16 {
          range 0..10 {
            description 'The count of receiving right answer.'
                        ;
          }
        }
      }
      leaf destination-url {
        config false ;
        description 'The destination domain name.'
                    ;
        type string {
          length 1..128 {
            description 'The destination domain name.'
                        ;
          }
        }
      }
      leaf resolved-ip {
        config false ;
        description 'The domain name was resolved to an IP address through the '
                  + 'DNS.'
                    ;
        type ncd:ipv4-address ;
      }
      leaf min-rtt {
        config false ;
        description 'The minimal time of resolving a domain name.'
                    ;
        type uint32 ;
        units ms ;
      }
      leaf max-rtt {
        config false ;
        description 'The maximal time of resolving a domain name.'
                    ;
        type uint32 ;
        units ms ;
      }
      leaf avg-rtt {
        config false ;
        description 'The averange time of resolving a domain name.'
                    ;
        type uint32 ;
        units ms ;
      }
      leaf sum-rtt {
        config false ;
        description 'The sum time of resolving a domain name.'
                    ;
        type uint32 ;
        units ms ;
      }
      leaf probe-time {
        config false ;
        description 'The end time of DNS test.'
                    ;
        type ncd:string-with-blank {
          length 19 {
            description 'The end time of DNS test.'
                        ;
          }
        }
      }
    }
    ncd:revise-date 2015-08-20 ;
  }
  notification udpjitter-event {
    description 'The udpjitter test result.'
                ;
    list udpjitter-result {
      description 'The udpjitter test result.'
                  ;
      key test-number ;
      leaf test-number {
        config false ;
        description 'The value of test index,the upper limit of this parameter '
                  + 'depends on the device.'
                    ;
        type uint32 {
          range 1..1024 {
            description 'The test number ranges from 1 to 1024.'
                        ;
          }
        }
      }
      leaf repeat-count {
        config false ;
        description 'The count of sending UDP packets.'
                    ;
        type uint16 {
          range 1..1000 {
            description 'The count of sending UDP packets.'
                        ;
          }
        }
      }
      leaf response-count {
        config false ;
        description 'The count of receiving UDP packets.'
                    ;
        type uint16 {
          range 0..1000 {
            description 'The count of receiving UDP packets.'
                        ;
          }
        }
      }
      leaf destination-ip {
        config false ;
        description 'The destination IPv4 address.'
                    ;
        type ncd:ipv4-address ;
      }
      leaf min-rtt-sd {
        config false ;
        description 'The minimal value of delay from source to destination.'
                    ;
        type uint32 ;
        units ms ;
      }
      leaf max-rtt-sd {
        config false ;
        description 'The maximal value of delay from source to destination.'
                    ;
        type uint32 ;
        units ms ;
      }
      leaf avg-rtt-sd {
        config false ;
        description 'The averange value of delay from source to destination.'
                    ;
        type uint32 ;
        units ms ;
      }
      leaf sum-rtt-sd {
        config false ;
        description 'The sum value of delay from source to destination.'
                    ;
        type uint32 ;
        units ms ;
      }
      leaf min-rtt-ds {
        config false ;
        description 'The minimal value of delay from destination to source.'
                    ;
        type uint32 ;
        units ms ;
      }
      leaf max-rtt-ds {
        config false ;
        description 'The maximal value of delay from destination to source.'
                    ;
        type uint32 ;
        units ms ;
      }
      leaf avg-rtt-ds {
        config false ;
        description 'The averange value of delay from destination to source.'
                    ;
        type uint32 ;
        units ms ;
      }
      leaf sum-rtt-ds {
        config false ;
        description 'The sum value of delay from destination to source.'
                    ;
        type uint32 ;
        units ms ;
      }
      leaf min-positive-jitter-sd {
        config false ;
        description 'The minimal value of positive jitter from source to destin'
                  + 'ation.'
                    ;
        type uint32 ;
        units ms ;
      }
      leaf max-positive-jitter-sd {
        config false ;
        description 'The maximal value of positive jitter from source to destin'
                  + 'ation.'
                    ;
        type uint32 ;
        units ms ;
      }
      leaf avg-positive-jitter-sd {
        config false ;
        description 'The averange value of positive jitter from source to desti'
                  + 'nation.'
                    ;
        type uint32 ;
        units ms ;
      }
      leaf sum-positive-jitter-sd {
        config false ;
        description 'The sum value of positive jitter from source to destinatio'
                  + 'n.'
                    ;
        type uint32 ;
        units ms ;
      }
      leaf min-negative-jitter-sd {
        config false ;
        description 'The minimal value of negtive jitter from source to destina'
                  + 'tion.'
                    ;
        type uint32 ;
        units ms ;
      }
      leaf max-negative-jitter-sd {
        config false ;
        description 'The maximal value of negtive jitter from source to destina'
                  + 'tion.'
                    ;
        type uint32 ;
        units ms ;
      }
      leaf avg-negative-jitter-sd {
        config false ;
        description 'The averange value of negtive jitter from source to destin'
                  + 'ation.'
                    ;
        type uint32 ;
        units ms ;
      }
      leaf sum-negative-jitter-sd {
        config false ;
        description 'The sum value of negtive jitter from source to destination.'
                    ;
        type uint32 ;
        units ms ;
      }
      leaf min-positive-jitter-ds {
        config false ;
        description 'The minimal value of positive jitter from destination to s'
                  + 'ource.'
                    ;
        type uint32 ;
        units ms ;
      }
      leaf max-positive-jitter-ds {
        config false ;
        description 'The maximal value of positive jitter from destination to s'
                  + 'ource.'
                    ;
        type uint32 ;
        units ms ;
      }
      leaf avg-positive-jitter-ds {
        config false ;
        description 'The averange value of positive jitter from destination to '
                  + 'source.'
                    ;
        type uint32 ;
        units ms ;
      }
      leaf sum-positive-jitter-ds {
        config false ;
        description 'The sum value of positive jitter from destination to sourc'
                  + 'e.'
                    ;
        type uint32 ;
        units ms ;
      }
      leaf min-negative-jitter-ds {
        config false ;
        description 'The minimal value of negtive jitter from destination to so'
                  + 'urce.'
                    ;
        type uint32 ;
        units ms ;
      }
      leaf max-negative-jitter-ds {
        config false ;
        description 'The maximal value of negtive jitter from destination to so'
                  + 'urce.'
                    ;
        type uint32 ;
        units ms ;
      }
      leaf avg-negative-jitter-ds {
        config false ;
        description 'The averange value of negtive jitter from destination to s'
                  + 'ource'
                    ;
        type uint32 ;
        units ms ;
      }
      leaf sum-negative-jitter-ds {
        config false ;
        description 'The sum value of negtive jitter from destination to source.'
                    ;
        type uint32 ;
      }
      leaf pkt-loss-number-sd {
        config false ;
        description 'The number of lossing packets from source to destination.'
                    ;
        type uint16 ;
      }
      leaf pkt-loss-number-ds {
        config false ;
        description 'The number of lossing packets from destination to source.'
                    ;
        type uint16 ;
      }
      leaf probe-time {
        config false ;
        description 'The end time of udpjitter test.'
                    ;
        type ncd:string-with-blank {
          length 19 {
            description 'The end time of udpjitter test.'
                        ;
          }
        }
      }
      leaf destination-ipv6 {
        config false ;
        description 'The destination IPv6 address.'
                    ;
        type ncd:ipv6-address ;
        ncd:revise-date 2020-03-18 ;
      }
    }
    ncd:revise-date 2015-08-20 ;
  }
  notification snmp-event {
    description 'The SNMP test result.'
                ;
    list snmp-result {
      description 'The SNMP test result.'
                  ;
      key test-number ;
      leaf test-number {
        config false ;
        description 'The value of test index,the upper limit of this parameter '
                  + 'depends on the device.'
                    ;
        type uint32 {
          range 1..1024 {
            description 'The test number ranges from 1 to 1024.'
                        ;
          }
        }
      }
      leaf last-rtt {
        config false ;
        description 'The time required to complete this test.'
                    ;
        type uint32 ;
        units ms ;
      }
      leaf probe-time {
        config false ;
        description 'The end time of SNMP test.'
                    ;
        type ncd:string-with-blank {
          length 19 {
            description 'The end time of SNMP test.'
                        ;
          }
        }
      }
    }
    ncd:revise-date 2015-08-20 ;
  }
  notification http-event {
    description 'The HTTP test result.'
                ;
    list http-result {
      description 'The HTTP test result.'
                  ;
      key test-number ;
      leaf test-number {
        config false ;
        description 'The value of test index,the upper limit of this parameter '
                  + 'depends on the device.'
                    ;
        type uint32 {
          range 1..1024 {
            description 'The test number ranges from 1 to 1024.'
                        ;
          }
        }
      }
      leaf repeat-count {
        config false ;
        description 'The count of sending HTTP request.'
                    ;
        type uint16 {
          range 1..10 {
            description 'The count of sending HTTP request.'
                        ;
          }
        }
      }
      leaf response-count {
        config false ;
        description 'The count of receiving HTTP answer.'
                    ;
        type uint16 {
          range 0..10 {
            description 'The count of receiving HTTP answer.'
                        ;
          }
        }
      }
      leaf destination-ip {
        config false ;
        description 'The destination IP address.'
                    ;
        type ncd:ipv4-address ;
      }
      leaf destination-url {
        config false ;
        description 'The destination domain name.'
                    ;
        type string {
          length 1..128 {
            description 'The destination domain name.'
                        ;
          }
        }
      }
      leaf min-dns-rtt {
        config false ;
        description 'The minimal time of resolving a domain name.'
                    ;
        type uint32 ;
        units ms ;
      }
      leaf max-dns-rtt {
        config false ;
        description 'The maximal time of resolving a domain name.'
                    ;
        type uint32 ;
        units ms ;
      }
      leaf avg-dns-rtt {
        config false ;
        description 'The averange time of resolving a domain name.'
                    ;
        type uint32 ;
        units ms ;
      }
      leaf sum-dns-rtt {
        config false ;
        description 'The sum time of resolving a domain name.'
                    ;
        type uint32 ;
        units ms ;
      }
      leaf min-tcp-connection-rtt {
        config false ;
        description 'The minimal time of establishing link.'
                    ;
        type uint32 ;
        units ms ;
      }
      leaf max-tcp-connection-rtt {
        config false ;
        description 'The maximal time of establishing link.'
                    ;
        type uint32 ;
        units ms ;
      }
      leaf avg-tcp-connection-rtt {
        config false ;
        description 'The averange time of establishing link.'
                    ;
        type uint32 ;
        units ms ;
      }
      leaf sum-tcp-connection-rtt {
        config false ;
        description 'The sum time of establishing link.'
                    ;
        type uint32 ;
        units ms ;
      }
      leaf min-http-connection-rtt {
        config false ;
        description 'The minimal time of completing http request.'
                    ;
        type uint32 ;
        units ms ;
      }
      leaf max-http-connection-rtt {
        config false ;
        description 'The maximal time of completing http request.'
                    ;
        type uint32 ;
        units ms ;
      }
      leaf avg-http-connection-rtt {
        config false ;
        description 'The averange time of completing http request.'
                    ;
        type uint32 ;
        units ms ;
      }
      leaf sum-http-connection-rtt {
        config false ;
        description 'The sum time of completing http request.'
                    ;
        type uint32 ;
        units ms ;
      }
      leaf min-rtt {
        config false ;
        description 'The minimal time required to complete this whole test.'
                    ;
        type uint32 ;
        units ms ;
      }
      leaf max-rtt {
        config false ;
        description 'The maximal time required to complete this whole test.'
                    ;
        type uint32 ;
        units ms ;
      }
      leaf avg-rtt {
        config false ;
        description 'The averange time required to complete this whole test.'
                    ;
        type uint32 ;
        units ms ;
      }
      leaf sum-rtt {
        config false ;
        description 'The sum time required to complete this whole test.'
                    ;
        type uint32 ;
        units ms ;
      }
      leaf probe-time {
        config false ;
        description 'The end time of HTTP test.'
                    ;
        type ncd:string-with-blank {
          length 19 {
            description 'The end time of HTTP test.'
                        ;
          }
        }
      }
    }
    ncd:revise-date 2015-08-20 ;
  }
  notification icmpjitter-event {
    description 'The icmpjitter test result.'
                ;
    list icmpjitter-result {
      description 'The icmpjitter test result.'
                  ;
      key test-number ;
      leaf test-number {
        config false ;
        description 'The value of test index,the upper limit of this parameter '
                  + 'depends on the device.'
                    ;
        type uint32 {
          range 1..1024 {
            description 'The test number ranges from 1 to 1024.'
                        ;
          }
        }
      }
      leaf repeat-count {
        config false ;
        description 'The count of sending ICMP packets.'
                    ;
        type uint16 {
          range 1..65535 {
            description 'The count of sending ICMP packets.'
                        ;
          }
        }
      }
      leaf response-count {
        config false ;
        description 'The count of receiving ICMP packets.'
                    ;
        type uint16 {
          range 0..65535 {
            description 'The count of receiving ICMP packets.'
                        ;
          }
        }
      }
      leaf destination-ip {
        config false ;
        description 'The destination IPv4 address.'
                    ;
        type ncd:ipv4-address ;
      }
      leaf min-rtt-sd {
        config false ;
        description 'The minimal value of delay from source to destination.'
                    ;
        type uint32 ;
        units ms ;
      }
      leaf max-rtt-sd {
        config false ;
        description 'The maximal value of delay from source to destination.'
                    ;
        type uint32 ;
        units ms ;
      }
      leaf avg-rtt-sd {
        config false ;
        description 'The averange value of delay from source to destination.'
                    ;
        type uint32 ;
        units ms ;
      }
      leaf sum-rtt-sd {
        config false ;
        description 'The sum value of delay from source to destination.'
                    ;
        type uint32 ;
        units ms ;
      }
      leaf min-rtt-ds {
        config false ;
        description 'The minimal value of delay from destination to source.'
                    ;
        type uint32 ;
        units ms ;
      }
      leaf max-rtt-ds {
        config false ;
        description 'The maximal value of delay from destination to source.'
                    ;
        type uint32 ;
        units ms ;
      }
      leaf avg-rtt-ds {
        config false ;
        description 'The averange value of delay from destination to source.'
                    ;
        type uint32 ;
        units ms ;
      }
      leaf sum-rtt-ds {
        config false ;
        description 'The sum value of delay from destination to source.'
                    ;
        type uint32 ;
        units ms ;
      }
      leaf min-positive-jitter-sd {
        config false ;
        description 'The minimal value of positive jitter from source to destin'
                  + 'ation.'
                    ;
        type uint32 ;
        units ms ;
      }
      leaf max-positive-jitter-sd {
        config false ;
        description 'The maximal value of positive jitter from source to destin'
                  + 'ation.'
                    ;
        type uint32 ;
        units ms ;
      }
      leaf avg-positive-jitter-sd {
        config false ;
        description 'The averange value of positive jitter from source to desti'
                  + 'nation.'
                    ;
        type uint32 ;
        units ms ;
      }
      leaf sum-positive-jitter-sd {
        config false ;
        description 'The sum value of positive jitter from source to destinatio'
                  + 'n.'
                    ;
        type uint32 ;
        units ms ;
      }
      leaf min-negative-jitter-sd {
        config false ;
        description 'The minimal value of negtive jitter from source to destina'
                  + 'tion.'
                    ;
        type uint32 ;
        units ms ;
      }
      leaf max-negative-jitter-sd {
        config false ;
        description 'The maximal value of negtive jitter from source to destina'
                  + 'tion.'
                    ;
        type uint32 ;
        units ms ;
      }
      leaf avg-negative-jitter-sd {
        config false ;
        description 'The averange value of negtive jitter from source to destin'
                  + 'ation.'
                    ;
        type uint32 ;
        units ms ;
      }
      leaf sum-negative-jitter-sd {
        config false ;
        description 'The sum value of negtive jitter from source to destination.'
                    ;
        type uint32 ;
        units ms ;
      }
      leaf min-positive-jitter-ds {
        config false ;
        description 'The minimal value of positive jitter from destination to s'
                  + 'ource.'
                    ;
        type uint32 ;
        units ms ;
      }
      leaf max-positive-jitter-ds {
        config false ;
        description 'The maximal value of positive jitter from destination to s'
                  + 'ource.'
                    ;
        type uint32 ;
        units ms ;
      }
      leaf avg-positive-jitter-ds {
        config false ;
        description 'The averange value of positive jitter from destination to '
                  + 'source.'
                    ;
        type uint32 ;
        units ms ;
      }
      leaf sum-positive-jitter-ds {
        config false ;
        description 'The sum value of positive jitter from destination to sourc'
                  + 'e.'
                    ;
        type uint32 ;
        units ms ;
      }
      leaf min-negative-jitter-ds {
        config false ;
        description 'The minimal value of negtive jitter from destination to so'
                  + 'urce.'
                    ;
        type uint32 ;
        units ms ;
      }
      leaf max-negative-jitter-ds {
        config false ;
        description 'The maximal value of negtive jitter from destination to so'
                  + 'urce.'
                    ;
        type uint32 ;
        units ms ;
      }
      leaf avg-negative-jitter-ds {
        config false ;
        description 'The averange value of negtive jitter from destination to s'
                  + 'ource.'
                    ;
        type uint32 ;
        units ms ;
      }
      leaf sum-negative-jitter-ds {
        config false ;
        description 'The sum value of negtive jitter from destination to source.'
                    ;
        type uint32 ;
        units ms ;
      }
      leaf probe-time {
        config false ;
        description 'The end time of ICMPjitter test.'
                    ;
        type ncd:string-with-blank {
          length 19 {
            description 'The end time of ICMPjitter test.'
                        ;
          }
        }
      }
      leaf min-rtt {
        config false ;
        description 'The minimum value of RTT.'
                    ;
        type uint32 ;
        units ms ;
        ncd:revise-date 2020-08-11 ;
      }
      leaf max-rtt {
        config false ;
        description 'The maximum value of RTT.'
                    ;
        type uint32 ;
        units ms ;
        ncd:revise-date 2020-08-11 ;
      }
      leaf avg-rtt {
        config false ;
        description 'The averange value of RTT.'
                    ;
        type uint32 ;
        units ms ;
        ncd:revise-date 2020-08-11 ;
      }
      leaf sum-rtt {
        config false ;
        description 'The sum value of RTT.'
                    ;
        type uint32 ;
        units ms ;
        ncd:revise-date 2020-08-11 ;
      }
      leaf cur-rtt {
        config false ;
        description 'The current value of RTT.'
                    ;
        type uint32 ;
        units ms ;
        ncd:revise-date 2020-08-11 ;
      }
      leaf min-delay-jitter {
        config false ;
        description 'The minimum value of jitter.'
                    ;
        type uint32 ;
        units ms ;
        ncd:revise-date 2020-08-11 ;
      }
      leaf max-delay-jitter {
        config false ;
        description 'The maximum value of jitter.'
                    ;
        type uint32 ;
        units ms ;
        ncd:revise-date 2020-08-11 ;
      }
      leaf avg-delay-jitter {
        config false ;
        description 'The averange value of jitter.'
                    ;
        type uint32 ;
        units ms ;
        ncd:revise-date 2020-08-11 ;
      }
      leaf sum-delay-jitter {
        config false ;
        description 'The sum value of jitter.'
                    ;
        type uint32 ;
        units ms ;
        ncd:revise-date 2020-08-11 ;
      }
      leaf cur-delay-jitter {
        config false ;
        description 'The current value of jitter.'
                    ;
        type uint32 ;
        units ms ;
        ncd:revise-date 2020-08-11 ;
      }
      leaf cur-delay-jitter-sd {
        config false ;
        description 'The current value of jitter from source to destination.'
                    ;
        type uint32 ;
        units ms ;
        ncd:revise-date 2020-08-11 ;
      }
      leaf cur-delay-jitter-ds {
        config false ;
        description 'The current value of jitter from destination to source.'
                    ;
        type uint32 ;
        units ms ;
        ncd:revise-date 2020-08-11 ;
      }
      leaf pkt-loss-num {
        config false ;
        description 'The number of lossing packets in the ICMP test.'
                    ;
        type uint16 ;
        ncd:revise-date 2020-08-11 ;
      }
      leaf pkt-loss-rate {
        config false ;
        description 'The ratio of lossing packets in the ICMP test.'
                    ;
        type string {
          length 2..4 {
            description 'The range of lossing packets ratio.'
                        ;
          }
        }
        ncd:revise-date 2020-08-11 ;
      }
      leaf destination-ipv6 {
        config false ;
        description 'The destination IPv6 address.'
                    ;
        type ncd:ipv6-address ;
        ncd:revise-date 2020-08-11 ;
      }
    }
    ncd:revise-date 2015-08-20 ;
  }
  notification throughput-event {
    description 'The throughput test result.'
                ;
    list throughput-result {
      description 'The throughput test result.'
                  ;
      key 'test-number packet-size'
          ;
      leaf test-number {
        config false ;
        description 'The value of test index,the upper limit of this parameter '
                  + 'depends on the device.'
                    ;
        type uint32 ;
      }
      leaf packet-size {
        config false ;
        description 'The packet size,ranges from 64bytes to 9216bytes.'
                    ;
        type uint16 {
          range 64..9216 {
            description 'The range of packet size.'
                        ;
          }
        }
        units byte ;
      }
      leaf inbound-interface {
        config false ;
        description 'Interface name.'
                    ;
        type ncd:ifname {
          length 1..31 {
            description 'The range of interface name length.'
                        ;
          }
        }
      }
      leaf priority-8021p {
        config false ;
        description 'The value of priority-8021p,ranges from 0 to 7.'
                    ;
        type uint8 {
          range 0..7 {
            description 'The range of priority-8021p.'
                        ;
          }
        }
      }
      leaf dscp {
        config false ;
        description 'The value of DSCP,ranges from 0 to 63.'
                    ;
        type uint8 {
          range 0..63 {
            description 'The range of DSCP.'
                        ;
          }
        }
      }
      leaf precision {
        config false ;
        description 'The test precision of throughput.'
                    ;
        type uint32 ;
        units kbps ;
      }
      leaf throughput {
        config false ;
        description 'The result of throughput.'
                    ;
        type uint32 ;
        units kbps ;
      }
      leaf information-rate {
        config false ;
        description 'The information rate.'
                    ;
        type uint32 ;
        units kbps ;
      }
      leaf loss-ratio {
        config false ;
        description 'The packet loss ratio,precision is 1/10000.'
                    ;
        type uint32 ;
      }
      leaf duration {
        config false ;
        description 'The duration of test.'
                    ;
        type uint32 ;
        units s ;
      }
      leaf status {
        config false ;
        description 'The result status of test,including success,fail(1) and fa'
                  + 'il(2),fail(1) means could not find throughtput in the spec'
                  + 'ified time,fail(2) means configuration of the lowest rate '
                  + 'can not meet the requirements of packet loss rate.'
                    ;
        type enumeration {
          enum success {
            value 1 ;
            description 'The test status is success.'
                        ;
          }
          enum fail-1 {
            value 2 ;
            description 'Could not find throughtput in the specified time.'
                        ;
          }
          enum fail-2 {
            value 3 ;
            description 'Configuration of the lowest rate can not meet the requ'
                      + 'irements of packet loss rate.'
                        ;
          }
        }
      }
    }
    ncd:revise-date 2015-11-24 ;
  }
  notification loss-event {
    description 'The loss test result.'
                ;
    list loss-result {
      description 'The loss test result.'
                  ;
      key 'test-number packet-size'
          ;
      leaf test-number {
        config false ;
        description 'The value of test index,the upper limit of this parameter '
                  + 'depends on the device.'
                    ;
        type uint32 ;
      }
      leaf packet-size {
        config false ;
        description 'The packet size,ranges from 64bytes to 9216bytes.'
                    ;
        type uint16 {
          range 64..9216 {
            description 'The range of packet size.'
                        ;
          }
        }
        units byte ;
      }
      leaf inbound-interface {
        config false ;
        description 'Interface name.'
                    ;
        type ncd:ifname {
          length 1..31 {
            description 'The range of interface name length.'
                        ;
          }
        }
      }
      leaf priority-8021p {
        config false ;
        description 'The value of priority-8021p,ranges from 0 to 7.'
                    ;
        type uint8 {
          range 0..7 {
            description 'The range of priority-8021p.'
                        ;
          }
        }
      }
      leaf dscp {
        config false ;
        description 'The value of DSCP,ranges from 0 to 63.'
                    ;
        type uint8 {
          range 0..63 {
            description 'The range of DSCP.'
                        ;
          }
        }
      }
      leaf loss-rate {
        config false ;
        description 'The rate value of test,ranges from 1kbps to 10000000kbps.'
                    ;
        type uint32 {
          range 1..10000000 {
            description 'The range of rate.'
                        ;
          }
        }
        units kbps ;
      }
      leaf loss-packet-number {
        config false ;
        description 'The packet loss number of test.'
                    ;
        type uint32 ;
      }
      leaf loss-ratio {
        config false ;
        description 'The packet loss ratio,precision is 1/10000.'
                    ;
        type uint32 ;
      }
      leaf duration {
        config false ;
        description 'The duration of test.'
                    ;
        type uint32 ;
        units s ;
      }
      leaf status {
        config false ;
        description 'The result status of test,including success and fail.'
                    ;
        type enumeration {
          enum success {
            value 1 ;
            description 'The test result status is success.'
                        ;
          }
          enum fail {
            value 2 ;
            description 'The test result status is fail.'
                        ;
          }
        }
      }
    }
    ncd:revise-date 2015-11-24 ;
  }
  notification delay-event {
    description 'The delay test result.'
                ;
    list delay-result {
      description 'The delay test result.'
                  ;
      key 'test-number packet-size'
          ;
      leaf test-number {
        config false ;
        description 'The value of test index,the upper limit of this parameter '
                  + 'depends on the device.'
                    ;
        type uint32 ;
      }
      leaf packet-size {
        config false ;
        description 'The packet size,ranges from 64bytes to 9216bytes.'
                    ;
        type uint16 {
          range 64..9216 {
            description 'The range of packet size.'
                        ;
          }
        }
        units byte ;
      }
      leaf inbound-interface {
        config false ;
        description 'Interface name.'
                    ;
        type ncd:ifname {
          length 1..31 {
            description 'The range of interface name length.'
                        ;
          }
        }
      }
      leaf priority-8021p {
        config false ;
        description 'The value of priority-8021p,ranges from 0 to 7.'
                    ;
        type uint8 {
          range 0..7 {
            description 'The range of priority-8021p.'
                        ;
          }
        }
      }
      leaf dscp {
        config false ;
        description 'The value of DSCP,ranges from 0 to 63.'
                    ;
        type uint8 {
          range 0..63 {
            description 'The range of DSCP.'
                        ;
          }
        }
      }
      leaf delay-rate {
        config false ;
        description 'The rate value of test,ranges from 1kbps to 10000000kbps.'
                    ;
        type uint32 {
          range 1..10000000 {
            description 'The range of rate.'
                        ;
          }
        }
        units kbps ;
      }
      leaf min-delay {
        config false ;
        description 'The minimal delay of test.'
                    ;
        type uint64 ;
        units us ;
      }
      leaf max-delay {
        config false ;
        description 'The maximal delay of test.'
                    ;
        type uint64 ;
        units us ;
      }
      leaf avg-delay {
        config false ;
        description 'The average delay of test.'
                    ;
        type uint64 ;
        units us ;
      }
      leaf min-jitter {
        config false ;
        description 'The minimal jitter of test.'
                    ;
        type uint64 ;
        units us ;
      }
      leaf max-jitter {
        config false ;
        description 'The maximal jitter of test.'
                    ;
        type uint64 ;
        units us ;
      }
      leaf avg-jitter {
        config false ;
        description 'The average jitter of test.'
                    ;
        type uint64 ;
        units us ;
      }
      leaf duration {
        config false ;
        description 'The duration of test.'
                    ;
        type uint32 ;
        units s ;
      }
      leaf status {
        config false ;
        description 'The result status of test,including success and fail.'
                    ;
        type enumeration {
          enum success {
            value 1 ;
            description 'The test result status is success.'
                        ;
          }
          enum fail {
            value 2 ;
            description 'The test result status is fail.'
                        ;
          }
        }
      }
    }
    ncd:revise-date 2015-11-24 ;
  }
  notification lighttwamp-event {
    description 'The test result of light TWAMP.'
                ;
    list lighttwamp-result {
      description 'The test result of light TWAMP.'
                  ;
      key test-number ;
      leaf test-number {
        config false ;
        description 'The value of test index,the upper limit of this parameter '
                  + 'depends on the device.'
                    ;
        type uint32 ;
      }
      leaf packet-send-number {
        config false ;
        description 'The count of sending packets.'
                    ;
        type uint32 {
          range 0..4294967295 {
            description 'The range of sending packet number.'
                        ;
          }
        }
      }
      leaf packet-receive-number {
        config false ;
        description 'The count of receiving packets.'
                    ;
        type uint32 {
          range 0..4294967295 {
            description 'The range of receiving packet number.'
                        ;
          }
        }
      }
      leaf packet-loss-number {
        config false ;
        description 'The count of lossing packets.'
                    ;
        type uint32 {
          range 0..4294967295 {
            description 'The range of packe lossing number.'
                        ;
          }
        }
      }
      leaf packet-loss-ratio {
        config false ;
        description 'The packet loss ratio,precision is 1/1000000.'
                    ;
        type uint32 {
          range 0..4294967295 {
            description 'The range of packet lossing ratio.'
                        ;
          }
        }
      }
      leaf two-way-time-delay {
        config false ;
        description 'Two way packet delay.'
                    ;
        type uint64 ;
        units ns ;
      }
      leaf two-way-min-delay {
        description 'The minimum two way packet delay.'
                    ;
        type uint64 ;
        units ns ;
      }
      leaf two-way-max-delay {
        config false ;
        description 'The maximum two way packet delay.'
                    ;
        type uint64 ;
        units ns ;
      }
      leaf two-way-avg-delay {
        config false ;
        description 'The average two way packet delay.'
                    ;
        type uint64 ;
        units ns ;
      }
      leaf two-way-delay-jitter {
        config false ;
        description 'The two way packet delay jitter.'
                    ;
        type uint64 ;
        units ns ;
      }
      leaf two-way-min-jitter {
        config false ;
        description 'The minimum two way packet delay jitter.'
                    ;
        type uint64 ;
        units ns ;
      }
      leaf two-way-max-jitter {
        config false ;
        description 'The maximum two way packet delay jitter.'
                    ;
        type uint64 ;
        units ns ;
      }
      leaf two-way-avg-jitter {
        config false ;
        description 'The average two way packet delay jitter.'
                    ;
        type uint64 ;
        units ns ;
      }
      leaf forward-time-delay {
        config false ;
        description 'The forward packet delay.'
                    ;
        type uint64 ;
        units ns ;
      }
      leaf forward-min-delay {
        config false ;
        description 'The minimum forward packet delay.'
                    ;
        type uint64 ;
        units ns ;
      }
      leaf forward-max-delay {
        config false ;
        description 'The maximum forward packet delay.'
                    ;
        type uint64 ;
        units ns ;
      }
      leaf forward-avg-delay {
        config false ;
        description 'The average forward packet delay.'
                    ;
        type uint64 ;
        units ns ;
      }
      leaf forward-delay-jitter {
        config false ;
        description 'The forward packet delay jitter.'
                    ;
        type uint64 ;
        units ns ;
      }
      leaf forward-min-jitter {
        config false ;
        description 'The minimum forward packet delay jitter.'
                    ;
        type uint64 ;
        units ns ;
      }
      leaf forward-max-jitter {
        config false ;
        description 'The maximum forward packet delay jitter.'
                    ;
        type uint64 ;
        units ns ;
      }
      leaf forward-avg-jitter {
        config false ;
        description 'The average forward packet delay jitter.'
                    ;
        type uint64 ;
        units ns ;
      }
      leaf reverse-time-delay {
        config false ;
        description 'The reverse packet delay.'
                    ;
        type uint64 ;
        units ns ;
      }
      leaf reverse-min-delay {
        config false ;
        description 'The minimum reverse packet delay.'
                    ;
        type uint64 ;
        units ns ;
      }
      leaf reverse-max-delay {
        config false ;
        description 'The maximum reverse packet delay.'
                    ;
        type uint64 ;
        units ns ;
      }
      leaf reverse-avg-delay {
        config false ;
        description 'The average reverse packet delay.'
                    ;
        type uint64 ;
        units ns ;
      }
      leaf reverse-delay-jitter {
        config false ;
        description 'The reverse packet delay jitter.'
                    ;
        type uint64 ;
        units ns ;
      }
      leaf reverse-min-jitter {
        config false ;
        description 'The minimum reverse packet delay jitter.'
                    ;
        type uint64 ;
        units ns ;
      }
      leaf reverse-max-jitter {
        config false ;
        description 'The maximum reverse packet delay jitter.'
                    ;
        type uint64 ;
        units ns ;
      }
      leaf reverse-avg-jitter {
        config false ;
        description 'The average reverse packet delay jitter.'
                    ;
        type uint64 ;
        units ns ;
      }
    }
    ncd:revise-date 2016-02-27 ;
  }
  notification y1564-event {
    description 'The Y1564 test result.'
                ;
    list y1564-result {
      description 'The Y1564 test result.'
                  ;
      key 'test-number packet-size'
          ;
      leaf test-number {
        config false ;
        description 'The value of test index,the upper limit of this parameter '
                  + 'depends on the device.'
                    ;
        type uint32 ;
        mandatory true ;
      }
      leaf packet-size {
        config false ;
        description 'The packet size.'
                    ;
        type uint16 {
          range 64..9216 {
            description 'The range of packet size.'
                        ;
          }
        }
        units byte ;
      }
      leaf inbound-interface {
        config false ;
        description 'The name of inbound interface.'
                    ;
        type ncd:ifname {
          length 1..31 {
            description 'The range of interface name length.'
                        ;
          }
        }
      }
      leaf priority-8021p {
        config false ;
        description 'The value of priority-8021p.'
                    ;
        type uint8 {
          range 0..7 {
            description 'The range of priority-8021p.'
                        ;
          }
        }
        default 0 ;
      }
      leaf dscp {
        config false ;
        description 'The value of DSCP.'
                    ;
        type uint8 {
          range 0..63 {
            description 'The range of DSCP.'
                        ;
          }
        }
        default 0 ;
      }
      leaf test-type {
        description 'Test type.'
                    ;
        type enumeration {
          enum cir {
            value 1 ;
            description 'CIR test type.'
                        ;
          }
          enum cir/eir {
            value 2 ;
            description 'CIR and EIR test type.'
                        ;
          }
          enum traffic_policing {
            value 3 ;
            description 'Traffic policing test type.'
                        ;
          }
        }
      }
      leaf ir {
        description 'Test information rate.'
                    ;
        type uint32 {
          range 0..10000000 {
            description 'The range of test information rate.'
                        ;
          }
        }
        units kbps ;
      }
      leaf loss-packet-number {
        config false ;
        description 'The packet loss number of test.'
                    ;
        type uint32 ;
        default 0 ;
      }
      leaf loss-ratio {
        config false ;
        description 'The packet loss ratio(precision:1/10000).'
                    ;
        type uint32 {
          range 0..10000 {
            description 'The range of loss ratio.'
                        ;
          }
        }
        default 0 ;
      }
      leaf min-delay {
        config false ;
        description 'The minimal delay of test.'
                    ;
        type uint64 ;
        units us ;
        default 0 ;
      }
      leaf max-delay {
        config false ;
        description 'The maximal delay of test.'
                    ;
        type uint64 ;
        units us ;
        default 0 ;
      }
      leaf avg-delay {
        config false ;
        description 'The average delay of test.'
                    ;
        type uint64 ;
        units us ;
        default 0 ;
      }
      leaf min-jitter {
        config false ;
        description 'The minimal jitter of test.'
                    ;
        type uint64 ;
        units us ;
        default 0 ;
      }
      leaf max-jitter {
        config false ;
        description 'The maximal jitter of test.'
                    ;
        type uint64 ;
        units us ;
        default 0 ;
      }
      leaf avg-jitter {
        config false ;
        description 'The average jitter of test.'
                    ;
        type uint64 ;
        units us ;
        default 0 ;
      }
      leaf status {
        config false ;
        description 'The result status of test.'
                    ;
        type enumeration {
          enum pass {
            value 1 ;
            description 'The test result is pass.'
                        ;
          }
          enum fail {
            value 2 ;
            description 'The test result is fail.'
                        ;
          }
        }
      }
      leaf duration {
        config false ;
        description 'The duration of test.'
                    ;
        type uint32 {
          range 0..172800 {
            description 'The range of test duration.'
                        ;
          }
        }
        units s ;
        default 0 ;
      }
    }
    ncd:revise-date 2018-10-17 ;
  }
}
