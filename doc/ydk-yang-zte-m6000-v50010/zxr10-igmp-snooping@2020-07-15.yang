module zxr10-igmp-snooping {
  namespace 'http://www.zte.com.cn/zxr10/netconf/schema/rosng/igmp-snooping'
            ;
  prefix igs ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe IGMP snooping.'
              ;
  revision 2020-07-15 {
    description 'Add default value for node /igs:configuration/igs:igmp-snoopin'
              + 'g/igs:global/igs:host-aging-closedown'
                ;
  }
  revision 2019-12-05 {
    description 'add leaf node'+"\n"
              + '/igs:state/igs:igmp-snooping/igs:vbui/igs:member/igs:present-t'
              + 'ime,'+"\n"
              + '/igs:state/igs:igmp-snooping/igs:vrf/igs:member/igs:present-ti'
              + 'me,'+"\n"
              + '/igs:state/igs:igmp-snooping/igs:vxlan/igs:member/igs:present-'
              + 'time,'+"\n"
              + '/igs:state/igs:igmp-snooping/igs:ring-tree/igs:member/igs:pres'
              + 'ent-time,'+"\n"
              + '/igs:state/igs:igmp-snooping/igs:vxlan/igs:mrouter/igs:present'
              + '-time,'+"\n"
              + '/igs:state/igs:igmp-snooping/igs:ring-tree/igs:mrouter/igs:pre'
              + 'sent-time.'+"\n"
              + 'add feature mvpls general-state-mrouter'
                ;
  }
  revision 2019-11-04 {
    description 'Add container:'+"\n"
              + '/igs:configuration/igs:igmp-snooping/global/logging/'+"\n"
              + 'Add node:'+"\n"
              + '/igs:configuration/igs:igmp-snooping/global/logging/packet-rep'
              + 'ort;'+"\n"
              + '/igs:configuration/igs:igmp-snooping/global/logging/overrun-re'
              + 'port;'+"\n"
              + 'add feature:logging'
                ;
  }
  revision 2019-10-08 {
    description 'Remove the project tag of 99 from the vxlan feature.'
                ;
  }
  revision 2018-08-07 {
    description 'Add node:/igs:configuration/igs:igmp-snooping/global/querier-s'
              + 'end-to-mrouter;'+"\n"
              + '/igs:configuration/igs:igmp-snooping/igs:vpls/igs:vpls/querier'
              + '-send-to-mrouter;'+"\n"
              + '/igs:configuration/igs:igmp-snooping/igs:vpls/igs:vpls/interfa'
              + 'ce/querier-send-to-mrouter;'+"\n"
              + '/igs:configuration/igs:igmp-snooping/igs:vlans/igs:vlan/querie'
              + 'r-send-to-mrouter;'+"\n"
              + '/igs:configuration/igs:igmp-snooping/igs:vlans/igs:vlan/interf'
              + 'aces/interface/querier-send-to-mrouter;'+"\n"
              + 'add feature:querier-send-to-mrouter'
                ;
  }
  revision 2018-07-03 {
    description 'Add the default value to the leaf redundancy-pw-mrouter-transm'
              + 'itting in list VPLS.'
                ;
  }
  revision 2018-06-13 {
    description 'Add path:/igs:configuration/igs:igmp-snooping/igs:evpn-vpls, /'
              + 'state/igmp-snooping/evpn-vpls,operation/igmp-snooping/clear/gr'
              + 'oup/instance/evpn-vpls,operation/igmp-snooping/clear/groups/ty'
              + 'pe/evpn-vpls'+"\n"
              + 'Add feature:evpn-vpls'
                ;
  }
  revision 2018-05-30 {
    description 'Add leaf node:/igs:configuration/igs:igmp-snooping/igs:vlans/i'
              + 'gs:vlan/igs:query-interval'+"\n"
              + 'Add feature:vlan-query-interval'
                ;
  }
  revision 2018-04-03 {
    description 'Add leaf node:/igs:configuration/igs:igmp-snooping/igs:vpls/ig'
              + 's:vpls/igs:redundancy-pw-mrouter-transmitting.'+"\n"
              + 'Add typedef:redundancy-pw-transmitting-type.'+"\n"
              + 'Add feature:redundancy-pw-mrouter-transmitting.'
                ;
  }
  revision 2018-02-12 {
    description 'Add path:/igs:configuration/igs:igmp-snooping/igs:global/igs:h'
              + 'ost-aging-closedown,'+"\n"
              + '/igs:configuration/igs:igmp-snooping/igs:global/igs:transmit-p'
              + 'kt,'+"\n"
              + '/igs:configuration/igs:igmp-snooping/igs:vlans/igs:vlan/igs:ma'
              + 'x-member-num,'+"\n"
              + '/igs:configuration/igs:igmp-snooping/igs:vlans/igs:vlan/igs:to'
              + 'pology-chg,'+"\n"
              + '/igs:configuration/igs:igmp-snooping/igs:vlans/igs:vlan/igs:gr'
              + 'oup-spe-query-suppress,'+"\n"
              + '/igs:configuration/igs:igmp-snooping/igs:ip-global,'+"\n"
              + '/igs:configuration/igs:igmp-snooping/igs:groups,'+"\n"
              + '/igs:configuration/igs:igmp-snooping/igs:interfaces,'+"\n"
              + '/igs:state/igs:igmp-snooping/igs:vpls/igs:member/igs:present-t'
              + 'ime,'+"\n"
              + '/igs:state/igs:igmp-snooping/igs:vlan/igs:member/igs:present-t'
              + 'ime,'+"\n"
              + '/igs:state/igs:igmp-snooping/igs:ip-global/igs:member/igs:pres'
              + 'ent-time,'+"\n"
              + '/igs:state/igs:igmp-snooping/igs:mrouter/igs:present-time.'+"\n"
              + 'Add feature:host-aging-closedown,transmit-to-block-port,topolo'
              + 'gy-change,max-host-in-group,max-host-in-interface,max-host-in-'
              + 'vlan,group-specific-query-suppress,supervlan-member,transmit-f'
              + 'rom-block-port,group,interface,mrouter-version.'
                ;
  }
  revision 2017-10-27 {
    description 'Add path:/igs:configuration/igs:igmp-snooping/igs:ring-trees, '
              + '/state/igmp-snooping/ring-tree,operation/igmp-snooping/clear/g'
              + 'roup/instance/ring-tree,operation/igmp-snooping/clear/groups/t'
              + 'ype/ring-tree'+"\n"
              + 'Add feature:ring-tree'
                ;
  }
  revision 2017-07-27 {
    description 'Add path:/igs:configuration/igs:igmp-snooping/igs:vxlans/igs:v'
              + 'xlan/igs:mrouters/igs:mrouter/igs:untag;/igs:configuration/igs'
              + ':igmp-snooping/igs:vxlans/igs:vxlan/igs:members/igs:member/igs'
              + ':untag'
                ;
  }
  revision 2017-05-23 {
    description 'Add path:configuration/igmp-snooping/vxlans, state/igmp-snoopi'
              + 'ng/vxlan,operation/igmp-snooping/clear/group/instance/vxlan,op'
              + 'eration/igmp-snooping/clear/groups/type/vxlan'+"\n"
              + 'Add feature:vpls,vlan,vxlan,vbui,vrf,ip-global'
                ;
  }
  revision 2016-11-08 {
    description "Add path:state/igmp-snooping/mrouter's query term: vlan-id+int"
              + "erface-name,vpls-name+interface-name"
                ;
  }
  revision 2015-11-25 {
    description 'Modify leaf node attribute, node path:/configuration/igmp-snoo'
              + 'ping/vpls/vpls/m-vpls/default/m-vpls-name'
                ;
  }
  revision 2015-10-30 {
    description 'Add leaf node, node path: /state/igmp-snooping/mrouter/querier'
              + '-ip.'
                ;
  }
  revision 2015-09-15 {
    description 'Modify leaf node type, node path: /operation/igmp-snooping/cle'
              + 'ar/groups/type/ip-global/ip-global, /operation/igmp-snooping/c'
              + 'lear/groups/type/all/all-groups, /operation/igmp-snooping/clea'
              + 'r/group/instance/ip-global/ip-global.'
                ;
  }
  revision 2015-06-05 {
    description 'Modify /configuration/igmp-snooping/vpls/vpls/acl-name and /co'
              + 'nfiguration/igmp-snooping/vlans/vlan/acl-name length range (1.'
              + '.31 to 0..31)'
                ;
  }
  revision 2015-03-02 {
    description 'Add clear operation and global summary show.'
                ;
  }
  revision 2015-02-12 {
    description 'Modify m-vpls configuration. Add default and groups container.'
              + 'Change proper noun, such as vpls,vlan,id etc, from lowercase i'
              + 'nto capital.'
                ;
  }
  revision 2014-04-28 {
    description 'Add the VLAN configuration. Add the mrouter state and the memb'
              + 'er state of instance VLAN, VBUI,VRF and IP-GLOBAL.'
                ;
  }
  revision 2014-01-08 {
    description 'Add the range of leaf max-group-num and max-member-num ,modify'
              + ' the range of leaf last-mem-qry-interval ,modify the type of l'
              + 'eaf interface.'
                ;
  }
  revision 2013-09-17 {
    description 'Modify the key of list member in state ,delete the mandatory a'
              + 'nd add length range of leaf name in list VPLS.'
                ;
  }
  revision 2013-08-01 {
    description 'Initial version.'
                ;
  }
  feature vpls {
    description 'IGMP snooping over VPLS.'
                ;
  }
  feature vlan {
    description 'IGMP snooping over VLAN.'
                ;
  }
  feature vxlan {
    description 'IGMP snooping over VXLAN.'
                ;
  }
  feature vbui {
    description 'IGMP snooping over VBUI.'
                ;
  }
  feature vrf {
    description 'IGMP snooping over VRF.'
                ;
  }
  feature ip-global {
    description 'IGMP snooping over IP-global.'
                ;
  }
  feature ring-tree {
    description 'IGMP snooping over Ring Tree.'
                ;
  }
  feature host-aging-closedown {
    description 'Host aging closedown.'
                ;
  }
  feature transmit-to-block-port {
    description 'Transmit packets through block ports.'
                ;
  }
  feature topology-change {
    description 'Response or send packets when the topology changes.'
                ;
  }
  feature max-host-in-group {
    description 'Max access members in the specific group.'
                ;
  }
  feature max-host-in-interface {
    description 'Max access members in the specific interface.'
                ;
  }
  feature max-host-in-vlan {
    description 'Max access members in the specific VLAN.'
                ;
  }
  feature group-specific-query-suppress {
    description 'Group-specific query suppression in transparent mode.'
                ;
  }
  feature supervlan-member {
    description 'Supervlan members.'
                ;
  }
  feature transmit-from-block-port {
    description 'Transmit packets from block ports.'
                ;
  }
  feature group {
    description 'IGMP snooping group configuration.'
                ;
  }
  feature interface {
    description 'IGMP snooping interface configuration.'
                ;
  }
  feature mrouter-version {
    description 'IGMP snooping mrouter verison.'
                ;
  }
  feature redundancy-pw-mrouter-transmitting {
    description 'The mode of transmitting IGMP report/leave packets from mroute'
              + 'r can be configured.'
                ;
  }
  feature vlan-query-interval {
    description 'The query interval configuration in vlan mode.'
                ;
  }
  feature evpn-vpls {
    description 'IGMP snooping over EVPN-VPLS.'
                ;
  }
  feature querier-send-to-mrouter {
    description 'Querier sends query to mrouter.'
                ;
  }
  feature logging {
    description 'Logging igmp packets.'
                ;
  }
  feature mvpls {
    description 'IGMP snooping mvpls configuration.'
                ;
  }
  feature general-state-mrouter {
    description 'IGMP snooping suppoer general state mrouter.'
                ;
  }
  typedef switch-type {
    type enumeration {
      enum disable {
        value 0 ;
        description 'Disable this switch.'
                    ;
      }
      enum enable {
        value 1 ;
        description 'Enable this switch.'
                    ;
      }
    }
    description 'Type of switch status.'
                ;
  }
  typedef packet-dispose-type {
    type enumeration {
      enum accept {
        value 0 ;
        description 'Accept packet mode.'
                    ;
      }
      enum ignore {
        value 1 ;
        description 'Ignore packet mode.'
                    ;
      }
      enum discard {
        value 2 ;
        description 'Discard packet mode.'
                    ;
      }
    }
    description 'Type of packet dispose.'
                ;
  }
  typedef work-mode-type {
    type enumeration {
      enum proxy {
        value 0 ;
        description 'Proxy mode.'
                    ;
      }
      enum route {
        value 1 ;
        description 'Route mode'
                    ;
      }
      enum transparent {
        value 2 ;
        description 'Transparent mode.'
                    ;
      }
    }
    description 'Type of work mode.'
                ;
  }
  typedef version-type {
    type enumeration {
      enum v1 {
        value 1 ;
        description 'IGMP version1.'
                    ;
      }
      enum v2 {
        value 2 ;
        description 'IGMP version2.'
                    ;
      }
      enum v3 {
        value 3 ;
        description 'IGMP version3.'
                    ;
      }
    }
    description 'The version of IGMP.'
                ;
  }
  typedef mode-type {
    type enumeration {
      enum dynamic {
        value 0 ;
        description 'Dynamic mode.'
                    ;
      }
      enum static {
        value 1 ;
        description 'Static mode.'
                    ;
      }
    }
    description 'Type of mode. include dynamic mode or static mode.'
                ;
  }
  typedef mrouter-version-type {
    type enumeration {
      enum v1 {
        value 5 ;
        description 'Mrouter port version 1.'
                    ;
      }
      enum v2 {
        value 7 ;
        description 'Mrouter port version 2.'
                    ;
      }
      enum v3 {
        value 9 ;
        description 'Mrouter port version 3.'
                    ;
      }
    }
    description 'The version of IGMP mrouter port.'
                ;
  }
  typedef redundancy-pw-transmitting-type {
    type enumeration {
      enum double {
        value 2 ;
        description 'If set to double,It means that IGMP packets will be sent t'
                  + 'hrough both working PW and protection PW.'
                    ;
      }
      enum single {
        value 1 ;
        description 'If set to single,It means that IGMP packets will be sent t'
                  + 'hrough only working PW.'
                    ;
      }
    }
    description 'Redundancy PW transmitting mode:single or double.'
                ;
  }
  container configuration {
    description 'Configuration model.'
                ;
    container igmp-snooping {
      description 'Configure IGMP snooping parameters.'
                  ;
      container global {
        description 'IGMP snooping global configure.'
                    ;
        leaf global-enable {
          description 'Enable/disable IGMP snooping in this device.Its default '
                    + 'value depends on the product.'
                      ;
          type switch-type ;
        }
        leaf global-query-enable {
          description 'Enable/disable IGMP queries in this device.'
                      ;
          type switch-type ;
          default disable ;
        }
        leaf query-interval {
          description 'Configure query interval.The query interval is the inter'
                    + 'val between general queries sent by the querier.'
                      ;
          type uint16 {
            range 30..65535 ;
          }
          units second ;
          default 125 ;
        }
        leaf query-rsp-interval {
          description 'Configure query response interval. The response interval'
                    + ' inserted into the periodic general queries.'
                      ;
          type uint8 {
            range 1..255 ;
          }
          units 'tick (1 tick = 100ms)'
                ;
          default 100 ;
        }
        leaf v1-packet-dispose {
          description 'The disposal mode of IGMPv1 Report message.'
                      ;
          type packet-dispose-type ;
          default accept ;
        }
        leaf v2-packet-dispose {
          description 'The disposal mode of IGMPV2 Report/Leave message.'
                      ;
          type packet-dispose-type ;
          default accept ;
        }
        leaf v3-packet-dispose {
          description 'The disposal mode of IGMPV3 Report message.'
                      ;
          type packet-dispose-type ;
          default discard ;
        }
        leaf host-aging-closedown {
          // if-feature host-aging-closedown ;
          description 'Configure host aging closedown.'
                      ;
          type switch-type ;
          default disable ;
          ncd:revise-date 2018-02-12 ;
        }
        container transmit-to-block-port {
          // if-feature transmit-to-block-port ;
          description 'Transmit packets through block ports.'
                      ;
          leaf trans-query-to-block-port {
            description 'Configure query packet through blocked port.'
                        ;
            type switch-type ;
            default disable ;
          }
          leaf trans-report-leave-to-block-port {
            description 'Configure report and leave packet through blocked port.'
                        ;
            type switch-type ;
            default disable ;
          }
          ncd:revise-date 2018-02-12 ;
        }
        container transmit-from-block-port {
          // if-feature transmit-from-block-port ;
          description 'Transmit packets from block ports.'
                      ;
          leaf trans-query-from-block-port {
            description 'Allow to transmit query packet from blocked port.'
                        ;
            type switch-type ;
            default disable ;
          }
          ncd:revise-date 2018-02-12 ;
        }
        leaf querier-send-to-mrouter {
          // if-feature querier-send-to-mrouter ;
          description 'Configure querier sending query to mrouter.'
                      ;
          type enumeration {
            enum enable {
              value 1 ;
              description 'Configure sending query to mrouter enable.'
                          ;
            }
            enum disable {
              value 2 ;
              description 'Configure sending query to mrouter disable.'
                          ;
            }
          }
          default disable ;
          ncd:revise-date 2018-08-07 ;
        }
        container logging {
          description 'Logging the igmp packet.'
                      ;
          leaf packet-report {
            // if-feature logging ;
            description 'Logging the IGMP report.'
                        ;
            type switch-type ;
            default disable ;
          }
          leaf overrun-report {
            // if-feature logging ;
            description 'Logging the IGMP report for group or member number ove'
                      + 'rrun.'
                        ;
            type switch-type ;
            default disable ;
          }
          ncd:revise-date 2019-11-04 ;
        }
      }
      container vpls {
        // if-feature vpls ;
        description "IGMP snooping VPLS configure.Can't config IGMP snooping in"
                  + " VPLS if the VPLS instance not exist.If IGMP snooping conf"
                  + "iguration exist in VPLS,the VPLS instance can't be deleted"
                  + "."
                    ;
        list vpls {
          description 'The config of instance VPLS.'
                      ;
          key name ;
          leaf name {
            description 'Submode instance Name of VPLS.'
                        ;
            type string {
              length 1..32 ;
            }
          }
          leaf snooping-switch {
            description 'Enable/disable IGMP snooping in this instance.'
                        ;
            type switch-type ;
            default disable ;
          }
          leaf member-fast-leave {
            description 'Enable/disable group membership fast leave in this ins'
                      + 'tance.'
                        ;
            type switch-type ;
            default disable ;
          }
          leaf acl-name {
            description 'Configure an ACL rule in this instance.'
                        ;
            type string {
              length 0..31 ;
            }
          }
          leaf member-time-out {
            description 'Member aging time in this instance.'
                        ;
            type uint16 {
              range 30..65535 ;
            }
            units second ;
            default 260 ;
          }
          leaf mrouter-time-out {
            description 'Multicast router port aging time in this instance.'
                        ;
            type uint16 {
              range 30..65535 ;
            }
            units second ;
            default 260 ;
          }
          leaf work-mode {
            description 'Work mode in this instance: proxy, transparent or rout'
                      + 'er.'
                        ;
            type work-mode-type ;
            default proxy ;
          }
          leaf proxy-ip {
            description 'This IP address is used as source IP when sending IGMP'
                      + ' Report and Leave in proxy mode.'
                        ;
            type ncd:ipv4-address ;
          }
          leaf query-ip {
            description 'This IP address is used as source IP when sending IGMP'
                      + ' Query.'
                        ;
            type ncd:ipv4-address ;
          }
          leaf max-group-num {
            description 'Max number of multicast group can access in this insta'
                      + 'nce.Its default value and maximum value depends on the'
                      + ' product.'
                        ;
            type uint32 {
              range 1..4294967295 ;
            }
          }
          leaf ndl-enable {
            description 'Enable/disable all ports are not allowed to learn dyna'
                      + 'mic mrouter port(s).'
                        ;
            type switch-type ;
            default disable ;
          }
          leaf last-mem-qry-interval {
            description 'The last member query interval is the max response tim'
                      + 'e inserted into group-specific queries sent in respons'
                      + 'e to leave group messages, and is also the amount of t'
                      + 'ime between group-specific query messages.'
                        ;
            type uint16 {
              range 1..25 ;
            }
            units second ;
            default 1 ;
          }
          leaf query-version {
            description 'Querier version: V1, V2 or V3.'
                        ;
            type version-type ;
            default v2 ;
          }
          leaf query-enable {
            description 'Enable/disable querier in this instance.'
                        ;
            type switch-type ;
            default disable ;
          }
          leaf redundancy-pw-mrouter-transmitting {
            // if-feature redundancy-pw-mrouter-transmitting ;
            description 'Configure redundancy PW mrouter transmitting mode:sing'
                      + 'le or double.'
                        ;
            type redundancy-pw-transmitting-type ;
            default double ;
            ncd:revise-date 2018-04-03 ;
          }
          leaf querier-send-to-mrouter {
            // if-feature querier-send-to-mrouter ;
            description 'Configure querier sending query to mrouter.'
                        ;
            type enumeration {
              enum unconfigured {
                value 0 ;
                description 'Function of sending query to mrouter is unconfigur'
                          + 'ed.'
                            ;
              }
              enum enable {
                value 1 ;
                description 'Configure sending query to mrouter enable.'
                            ;
              }
              enum disable {
                value 2 ;
                description 'Configure sending query to mrouter disable.'
                            ;
              }
            }
            default unconfigured ;
            ncd:revise-date 2018-08-07 ;
          }
          list drop {
            description 'The config of group with drop in instance VPLS.The max'
                      + '-elements depends on the product.'
                        ;
            key group-ip ;
            leaf group-ip {
              description 'Group IP address.'
                          ;
              type ncd:ipv4-address ;
            }
          }
          list prejoin {
            description 'The config of group with prejoin in instance VPLS.The '
                      + 'max-elements depends on the product.'
                        ;
            key group-ip ;
            leaf group-ip {
              description 'Group IP address.'
                          ;
              type ncd:ipv4-address ;
            }
          }
          list max-member-num {
            description 'The config of group with max-member-num in instance VP'
                      + 'LS.The max-elements depends on the product.'
                        ;
            key group-ip ;
            leaf group-ip {
              description 'Group IP address.'
                          ;
              type ncd:ipv4-address ;
            }
            leaf max-member-num {
              description 'Max number of IGMP member can access to this group.I'
                        + 'ts default value and maximum'+"\n"
                        + 'value depends on the product.'
                          ;
              type uint32 {
                range 1..4294967295 ;
              }
            }
          }
          list member {
            description 'The config of static member in instance VPLS.The max-e'
                      + 'lements depends on the product.'
                        ;
            key 'group-ip interface'
                ;
            leaf group-ip {
              description 'Group IP address.'
                          ;
              type ncd:ipv4-address ;
            }
            leaf interface {
              description 'Interface name.'
                          ;
              type ncd:ifname ;
            }
          }
          list interface {
            description 'The config of interface in instance VPLS.'
                        ;
            key name ;
            leaf name {
              description 'Interface name.'
                          ;
              type ncd:ifname ;
            }
            leaf snooping-switch {
              description 'Enable/Disable IGMP snooping in the interface.'
                          ;
              type switch-type ;
              default enable ;
            }
            leaf mrouter-guard {
              description 'Interface multicast router guard function is enabled.'
                          ;
              type switch-type ;
              default disable ;
            }
            leaf querier-send-to-mrouter {
              // if-feature querier-send-to-mrouter ;
              description 'Configure querier sending query to mrouter.'
                          ;
              type enumeration {
                enum unconfigured {
                  value 0 ;
                  description 'Function of sending query to mrouter is unconfig'
                            + 'ured.'
                              ;
                }
                enum enable {
                  value 1 ;
                  description 'Configure sending query to mrouter enable.'
                              ;
                }
                enum disable {
                  value 2 ;
                  description 'Configure sending query to mrouter disable.'
                              ;
                }
              }
              default unconfigured ;
              ncd:revise-date 2018-08-07 ;
            }
          }
          list mrouter {
            description 'The config of static mrouter in instance VPLS.The max-'
                      + 'elements depends on the product.'
                        ;
            key interface ;
            leaf interface {
              description 'Interface name.'
                          ;
              type ncd:ifname ;
            }
          }
          list ndl {
            description 'The config of port not allowed to learn dynamic mroute'
                      + 'r in instance VPLS.The max-elements depends on the pro'
                      + 'duct.'
                        ;
            key interface ;
            leaf interface {
              description 'Interface name.'
                          ;
              type ncd:ifname ;
            }
          }
          container m-vpls {
            // if-feature mvpls ;
            description 'The config of multicast VPLS in instance VPLS.The max-'
                      + 'elements depends on the product.'
                        ;
            container default {
              description 'The config of default multicast VPLS in instance VPL'
                        + 'S.'
                          ;
              presence default ;
              leaf m-vpls-name {
                description 'The config of default multicast VPLS in instance V'
                          + 'PLS.'
                            ;
                type string {
                  length 1..32 ;
                }
                mandatory true ;
              }
            }
            container groups {
              description 'The specific group of multicast VPLS in instance VPL'
                        + 'S.'
                          ;
              list group {
                description 'The specific group of multicast VPLS in instance V'
                          + 'PLS.'
                            ;
                key group-ip ;
                leaf group-ip {
                  description 'Group IP address.'
                              ;
                  type ncd:ipv4-address ;
                }
                leaf m-vpls-name {
                  description 'Multicast VPLS name.'
                              ;
                  type string {
                    length 1..32 ;
                  }
                  mandatory true ;
                }
              }
            }
          }
        }
      }
      container vlans {
        // if-feature vlan ;
        description "IGMP snooping VLAN configure.Can't config IGMP snooping in"
                  + " VLAN if the VLAN instance not exist.If IGMP snooping conf"
                  + "iguration exist in VLAN,the VLAN instance can't be deleted"
                  + "."
                    ;
        list vlan {
          description 'The config of instance VLAN.'
                      ;
          key id ;
          leaf id {
            description 'Submode instance ID of VLAN.'
                        ;
            type uint16 {
              range 1..4094 ;
            }
          }
          leaf snooping-switch {
            description 'Enable/disable IGMP snooping in this instance.'
                        ;
            type switch-type ;
            default disable ;
          }
          leaf member-fast-leave {
            description 'Enable/disable group membership fast leave in this ins'
                      + 'tance.'
                        ;
            type switch-type ;
            default disable ;
          }
          leaf acl-name {
            description 'Configure an ACL rule in this instance.'
                        ;
            type string {
              length 0..31 ;
            }
          }
          leaf member-time-out {
            description 'Member aging time in this instance.'
                        ;
            type uint16 {
              range 30..65535 ;
            }
            units second ;
            default 260 ;
          }
          leaf mrouter-time-out {
            description 'Multicast router port aging time in this instance.'
                        ;
            type uint16 {
              range 30..65535 ;
            }
            units second ;
            default 260 ;
          }
          leaf work-mode {
            description 'Work mode in this instance: proxy, transparent or rout'
                      + 'er.'
                        ;
            type work-mode-type ;
            default proxy ;
          }
          leaf proxy-ip {
            description 'This IP address is used as source IP when sending IGMP'
                      + ' Report and Leave in proxy mode.'
                        ;
            type ncd:ipv4-address ;
          }
          leaf query-ip {
            description 'This IP address is used as source IP when sending IGMP'
                      + ' Query.'
                        ;
            type ncd:ipv4-address ;
          }
          leaf max-group-num {
            description 'Max number of multicast group can access in this insta'
                      + 'nce.Its default value and maximum value depends on the'
                      + ' product.'
                        ;
            type uint32 {
              range 1..4294967295 ;
            }
          }
          leaf ndl-enable {
            description 'Enable/disable all ports are not allowed to learn dyna'
                      + 'mic mrouter port(s).'
                        ;
            type switch-type ;
            default disable ;
          }
          leaf last-mem-qry-interval {
            description 'The last member query interval is the max response tim'
                      + 'e inserted into group-specific queries sent in respons'
                      + 'e to leave group messages, and is also the amount of t'
                      + 'ime between group-specific query messages.'
                        ;
            type uint16 {
              range 1..25 ;
            }
            units second ;
            default 1 ;
          }
          leaf query-version {
            description 'Querier version: V1, V2 or V3.'
                        ;
            type version-type ;
            default v2 ;
          }
          leaf query-enable {
            description 'Enable/disable querier in this instance.'
                        ;
            type switch-type ;
            default disable ;
          }
          leaf querier-send-to-mrouter {
            // if-feature querier-send-to-mrouter ;
            description 'Configure querier sending query to mrouter.'
                        ;
            type enumeration {
              enum unconfigured {
                value 0 ;
                description 'Function of sending query to mrouter is unconfigur'
                          + 'ed.'
                            ;
              }
              enum enable {
                value 1 ;
                description 'Configure sending query to mrouter enable.'
                            ;
              }
              enum disable {
                value 2 ;
                description 'Configure sending query to mrouter disable.'
                            ;
              }
            }
            default unconfigured ;
            ncd:revise-date 2018-08-07 ;
          }
          container drops {
            list drop {
              description 'The config of group with drop in instance VLAN.The m'
                        + 'ax-elements depends on the product.'
                          ;
              key group-ip ;
              leaf group-ip {
                description 'Group IP address.'
                            ;
                type ncd:ipv4-address ;
              }
            }
          }
          container prejoins {
            list prejoin {
              description 'The config of group with prejoin in instance VLAN.Th'
                        + 'e max-elements depends on the product.'
                          ;
              key group-ip ;
              leaf group-ip {
                description 'Group IP address.'
                            ;
                type ncd:ipv4-address ;
              }
            }
          }
          container max-member-nums {
            list max-member-num {
              description 'The config of group with max-member-num in instance '
                        + 'VLAN.The max-elements depends on the product.'
                          ;
              key group-ip ;
              leaf group-ip {
                description 'Group IP address.'
                            ;
                type ncd:ipv4-address ;
              }
              leaf max-member-num {
                description 'Max number of IGMP member can access to this group'
                          + '.Its default value and maximum'+"\n"
                          + 'value depends on the product.'
                            ;
                type uint32 {
                  range 1..4000 ;
                }
              }
            }
          }
          container members {
            list member {
              description 'The config of static member in instance VLAN.The max'
                        + '-elements depends on the product.'
                          ;
              key 'group-ip interface'
                  ;
              leaf group-ip {
                description 'Group IP address.'
                            ;
                type ncd:ipv4-address ;
              }
              leaf interface {
                description 'Interface name.'
                            ;
                type ncd:ifname ;
              }
            }
          }
          container interfaces {
            list interface {
              description 'The config of interface in instance VLAN.'
                          ;
              key name ;
              leaf name {
                description 'Interface name.'
                            ;
                type ncd:ifname ;
              }
              leaf mrouter-guard {
                description 'Interface multicast router guard function is enabl'
                          + 'ed.'
                            ;
                type switch-type ;
                default disable ;
              }
              leaf querier-send-to-mrouter {
                // if-feature querier-send-to-mrouter ;
                description 'Configure querier sending query to mrouter.'
                            ;
                type enumeration {
                  enum unconfigured {
                    value 0 ;
                    description 'Function of sending query to mrouter is unconf'
                              + 'igured.'
                                ;
                  }
                  enum enable {
                    value 1 ;
                    description 'Configure sending query to mrouter enable.'
                                ;
                  }
                  enum disable {
                    value 2 ;
                    description 'Configure sending query to mrouter disable.'
                                ;
                  }
                }
                default unconfigured ;
                ncd:revise-date 2018-08-07 ;
              }
            }
          }
          container mrouters {
            list mrouter {
              description 'The config of static mrouter in instance VLAN.The ma'
                        + 'x-elements depends on the product.'
                          ;
              key interface ;
              leaf interface {
                description 'Interface name.'
                            ;
                type ncd:ifname ;
              }
              leaf version {
                // if-feature mrouter-version ;
                description 'Mrouter port version: V1, V2 or V3.'
                            ;
                type mrouter-version-type ;
                default v2 ;
                ncd:revise-date 2018-02-12 ;
              }
            }
          }
          container ndls {
            list ndl {
              description 'The config of port not allowed to learn dynamic mrou'
                        + 'ter in instance VLAN.The max-elements depends on the'
                        + ' product.'
                          ;
              key interface ;
              leaf interface {
                description 'Interface name.'
                            ;
                type ncd:ifname ;
              }
            }
          }
          leaf max-member-num {
            // if-feature max-host-in-vlan ;
            description 'Max number of IGMP member can access to this instance.'
                      + 'Its maximum value depends on the product.'
                        ;
            type uint32 {
              range 1..4000 ;
            }
            ncd:revise-date 2018-02-12 ;
          }
          container topology-chg {
            // if-feature topology-change ;
            leaf response-spe-leave {
              description 'Response special leave when the topology changes.'
                          ;
              type switch-type ;
            }
            leaf send-general-query {
              description 'Send general query when the topology changes.'
                          ;
              type switch-type ;
            }
            leaf send-spe-leave {
              description 'Send special leave when the topology changes.'
                          ;
              type switch-type ;
            }
            ncd:revise-date 2018-02-12 ;
          }
          container group-spe-query-suppress {
            // if-feature group-specific-query-suppress ;
            description 'Configure group-specific query suppression in transpar'
                      + 'ent mode.'
                        ;
            choice suppress-config {
              description 'Suppress configuration.'
                          ;
              case suppress-without-time-out {
                description 'Enable group-specific query suppression function w'
                          + 'ithout specified leaving host time out.'
                            ;
                leaf suppress-without-time-out {
                  description 'Enable group-specific query suppression function.'
                              ;
                  type empty ;
                }
              }
              case suppress-with-time-out {
                description 'Enable group-specific query suppression function w'
                          + 'ith specified leaving host time out.'
                            ;
                leaf suppress-with-time-out {
                  description 'Enable group-specific query suppression and spec'
                            + 'ify leaving host time out.'
                              ;
                  type uint16 {
                    range 2..175 ;
                  }
                  units second ;
                }
              }
              case unsuppress {
                description 'Disable group-specific query suppression function.'
                            ;
                leaf unsuppress {
                  description 'Disable group-specific query suppression functio'
                            + 'n.'
                              ;
                  type empty ;
                }
              }
            }
            ncd:revise-date 2018-02-12 ;
          }
          leaf query-interval {
            // if-feature vlan-query-interval ;
            description 'Configure query interval of vlan instance.The query in'
                      + 'terval is the interval between general queries sent by'
                      + ' the querier.'
                        ;
            type uint16 {
              range 30..65535 ;
            }
            units second ;
            ncd:revise-date 2018-05-30 ;
          }
        }
      }
      container vxlans {
        // if-feature vxlan ;
        description "IGMP snooping VXLAN configure.Can't config IGMP snooping i"
                  + "n VXLAN if the VXLAN instance not exist.If IGMP snooping c"
                  + "onfiguration exist in VXLAN,the VXLAN instance can't be de"
                  + "leted."
                    ;
        list vxlan {
          description 'The config of instance VXLAN.'
                      ;
          key id ;
          leaf id {
            description 'Submode instance ID of VXLAN.'
                        ;
            type uint32 {
              range 1..16777215 ;
            }
          }
          leaf snooping-switch {
            description 'Enable/disable IGMP snooping in this instance.'
                        ;
            type switch-type ;
            default disable ;
          }
          leaf member-fast-leave {
            description 'Enable/disable group membership fast leave in this ins'
                      + 'tance.'
                        ;
            type switch-type ;
            default disable ;
          }
          leaf acl-name {
            description 'Configure an ACL rule in this instance.'
                        ;
            type string {
              length 0..31 ;
            }
          }
          leaf member-time-out {
            description 'Member aging time in this instance.'
                        ;
            type uint16 {
              range 30..65535 ;
            }
            units second ;
            default 260 ;
          }
          leaf mrouter-time-out {
            description 'Multicast router port aging time in this instance.'
                        ;
            type uint16 {
              range 30..65535 ;
            }
            units second ;
            default 260 ;
          }
          leaf work-mode {
            description 'Work mode in this instance: proxy, transparent or rout'
                      + 'er.'
                        ;
            type work-mode-type ;
            default proxy ;
          }
          leaf proxy-ip {
            description 'This IP address is used as source IP when sending IGMP'
                      + ' Report and Leave in proxy mode.'
                        ;
            type ncd:ipv4-address ;
          }
          leaf query-ip {
            description 'This IP address is used as source IP when sending IGMP'
                      + ' Query.'
                        ;
            type ncd:ipv4-address ;
          }
          leaf max-group-num {
            description 'Max number of multicast group can access in this insta'
                      + 'nce.Its default value and maximum value depends on the'
                      + ' product.'
                        ;
            type uint32 {
              range 1..4294967295 ;
            }
          }
          leaf ndl-enable {
            description 'Enable/disable all ports are not allowed to learn dyna'
                      + 'mic mrouter port(s).'
                        ;
            type switch-type ;
            default disable ;
          }
          leaf last-mem-qry-interval {
            description 'The last member query interval is the max response tim'
                      + 'e inserted into group-specific queries sent in respons'
                      + 'e to leave group messages, and is also the amount of t'
                      + 'ime between group-specific query messages.'
                        ;
            type uint16 {
              range 1..25 ;
            }
            units second ;
            default 1 ;
          }
          leaf query-version {
            description 'Querier version: V1, V2 or V3.'
                        ;
            type version-type ;
            default v2 ;
          }
          leaf query-enable {
            description 'Enable/disable querier in this instance.'
                        ;
            type switch-type ;
            default disable ;
          }
          container drops {
            list drop {
              description 'The config of group with drop in instance VXLAN.The '
                        + 'max-elements depends on the product.'
                          ;
              key group-ip ;
              leaf group-ip {
                description 'Group IP address.'
                            ;
                type ncd:ipv4-address ;
              }
            }
          }
          container prejoins {
            list prejoin {
              description 'The config of group with prejoin in instance VXLAN.T'
                        + 'he max-elements depends on the product.'
                          ;
              key group-ip ;
              leaf group-ip {
                description 'Group IP address.'
                            ;
                type ncd:ipv4-address ;
              }
            }
          }
          container max-member-nums {
            list max-member-num {
              description 'The config of group with max-member-num in instance '
                        + 'VXLAN.The max-elements depends on the product.'
                          ;
              key group-ip ;
              leaf group-ip {
                description 'Group IP address.'
                            ;
                type ncd:ipv4-address ;
              }
              leaf max-member-num {
                description 'Max number of IGMP member can access to this group'
                          + '.Its default value and maximum'+"\n"
                          + 'value depends on the product.'
                            ;
                type uint32 {
                  range 1..4000 ;
                }
              }
            }
          }
          container members {
            list member {
              description 'The config of static member in instance VXLAN.The ma'
                        + 'x-elements depends on the product.'
                          ;
              key 'group-ip interface untag'
                  ;
              leaf group-ip {
                description 'Group IP address.'
                            ;
                type ncd:ipv4-address ;
              }
              leaf interface {
                description 'Interface name.'
                            ;
                type ncd:ifname ;
              }
              leaf untag {
                description 'Untag interface.'
                            ;
                type switch-type ;
                ncd:revise-date 2017-07-27 ;
              }
            }
          }
          container interfaces {
            list interface {
              description 'The config of interface in instance VXLAN.'
                          ;
              key name ;
              leaf name {
                description 'Interface name.'
                            ;
                type ncd:ifname ;
              }
              leaf mrouter-guard {
                description 'Interface multicast router guard function is enabl'
                          + 'ed.'
                            ;
                type switch-type ;
                default disable ;
              }
            }
          }
          container mrouters {
            list mrouter {
              description 'The config of static mrouter in instance VXLAN.The m'
                        + 'ax-elements depends on the product.'
                          ;
              key 'interface untag'
                  ;
              leaf interface {
                description 'Interface name.'
                            ;
                type ncd:ifname ;
              }
              leaf untag {
                description 'Untag interface.'
                            ;
                type switch-type ;
                ncd:revise-date 2017-07-27 ;
              }
              leaf version {
                description 'Mrouter port version: V1, V2 or V3.'
                            ;
                type mrouter-version-type ;
                default v2 ;
              }
            }
          }
          container ndls {
            list ndl {
              description 'The config of port not allowed to learn dynamic mrou'
                        + 'ter in instance VXLAN.The max-elements depends on th'
                        + 'e product.'
                          ;
              key interface ;
              leaf interface {
                description 'Interface name.'
                            ;
                type ncd:ifname ;
              }
            }
          }
        }
        ncd:revise-date 2017-05-23 ;
      }
      container ring-trees {
        // if-feature ring-tree ;
        description "IGMP snooping Ring Tree configure.Can't config IGMP snoopi"
                  + "ng in Ring Tree if the Ring Tree instance not exist.If IGM"
                  + "P snooping configuration exist in Ring Tree,the Ring Tree "
                  + "instance can't be deleted."
                    ;
        list ring-tree {
          description 'The config of instance Ring Tree.'
                      ;
          key name ;
          leaf name {
            description 'Submode instance Name of Ring Tree.'
                        ;
            type string {
              length 1..32 ;
            }
          }
          leaf snooping-switch {
            description 'Enable/disable IGMP snooping in this instance.'
                        ;
            type switch-type ;
            default disable ;
          }
          leaf member-fast-leave {
            description 'Enable/disable group membership fast leave in this ins'
                      + 'tance.'
                        ;
            type switch-type ;
            default disable ;
          }
          leaf acl-name {
            description 'Configure an ACL rule in this instance.'
                        ;
            type string {
              length 0..31 ;
            }
          }
          leaf member-time-out {
            description 'Member aging time in this instance.'
                        ;
            type uint16 {
              range 30..65535 ;
            }
            units second ;
            default 260 ;
          }
          leaf mrouter-time-out {
            description 'Multicast router port aging time in this instance.'
                        ;
            type uint16 {
              range 30..65535 ;
            }
            units second ;
            default 260 ;
          }
          leaf work-mode {
            description 'Work mode in this instance: proxy, transparent or rout'
                      + 'er.'
                        ;
            type work-mode-type ;
            default proxy ;
          }
          leaf proxy-ip {
            description 'This IP address is used as source IP when sending IGMP'
                      + ' Report and Leave in proxy mode.'
                        ;
            type ncd:ipv4-address ;
          }
          leaf query-ip {
            description 'This IP address is used as source IP when sending IGMP'
                      + ' Query.'
                        ;
            type ncd:ipv4-address ;
          }
          leaf max-group-num {
            description 'Max number of multicast group can access in this insta'
                      + 'nce.Its default value and maximum value depends on the'
                      + ' product.'
                        ;
            type uint32 {
              range 1..4294967295 ;
            }
          }
          leaf ndl-enable {
            description 'Enable/disable all ports are not allowed to learn dyna'
                      + 'mic mrouter port(s).'
                        ;
            type switch-type ;
            default disable ;
          }
          leaf last-mem-qry-interval {
            description 'The last member query interval is the max response tim'
                      + 'e inserted into group-specific queries sent in respons'
                      + 'e to leave group messages, and is also the amount of t'
                      + 'ime between group-specific query messages.'
                        ;
            type uint16 {
              range 1..25 ;
            }
            units second ;
            default 1 ;
          }
          leaf query-version {
            description 'Querier version: V1, V2 or V3.'
                        ;
            type version-type ;
            default v2 ;
          }
          leaf query-enable {
            description 'Enable/disable querier in this instance.'
                        ;
            type switch-type ;
            default disable ;
          }
          container drops {
            list drop {
              description 'The config of group with drop in instance Ring Tree.'
                        + 'The max-elements depends on the product.'
                          ;
              key group-ip ;
              leaf group-ip {
                description 'Group IP address.'
                            ;
                type ncd:ipv4-address ;
              }
            }
          }
          container prejoins {
            list prejoin {
              description 'The config of group with prejoin in instance Ring Tr'
                        + 'ee.The max-elements depends on the product.'
                          ;
              key group-ip ;
              leaf group-ip {
                description 'Group IP address.'
                            ;
                type ncd:ipv4-address ;
              }
            }
          }
          container max-member-nums {
            list max-member-num {
              description 'The config of group with max-member-num in instance '
                        + 'Ring Tree.The max-elements depends on the product.'
                          ;
              key group-ip ;
              leaf group-ip {
                description 'Group IP address.'
                            ;
                type ncd:ipv4-address ;
              }
              leaf max-member-num {
                description 'Max number of IGMP member can access to this group'
                          + '.Its default value and maximum'+"\n"
                          + 'value depends on the product.'
                            ;
                type uint32 {
                  range 1..4000 ;
                }
              }
            }
          }
          container members {
            list member {
              description 'The config of static member in instance Ring Tree.Th'
                        + 'e max-elements depends on the product.'
                          ;
              key 'group-ip interface'
                  ;
              leaf group-ip {
                description 'Group IP address.'
                            ;
                type ncd:ipv4-address ;
              }
              leaf interface {
                description 'Interface name.'
                            ;
                type ncd:ifname ;
              }
            }
          }
          container interfaces {
            list interface {
              description 'The config of interface in instance Ring Tree.'
                          ;
              key name ;
              leaf name {
                description 'Interface name.'
                            ;
                type ncd:ifname ;
              }
              leaf mrouter-guard {
                description 'Interface multicast router guard function is enabl'
                          + 'ed.'
                            ;
                type switch-type ;
                default disable ;
              }
              leaf snooping-switch {
                description 'Enable/Disable IGMP snooping in the interface.'
                            ;
                type switch-type ;
                default enable ;
              }
            }
          }
          container mrouters {
            list mrouter {
              description 'The config of static mrouter in instance Ring Tree.T'
                        + 'he max-elements depends on the product.'
                          ;
              key interface ;
              leaf interface {
                description 'Interface name.'
                            ;
                type ncd:ifname ;
              }
            }
          }
          container ndls {
            list ndl {
              description 'The config of port not allowed to learn dynamic mrou'
                        + 'ter in instance Ring Tree.The max-elements depends o'
                        + 'n the product.'
                          ;
              key interface ;
              leaf interface {
                description 'Interface name.'
                            ;
                type ncd:ifname ;
              }
            }
          }
        }
        ncd:revise-date 2017-10-27 ;
      }
      container ip-global {
        // if-feature ip-global ;
        description 'IGMP snooping IP-global configure.'
                    ;
        container supervlan-members {
          // if-feature supervlan-member ;
          description 'The config of static member in IP-global.The max-element'
                    + 's depends on the product.'
                      ;
          list supervlan-member {
            description 'The config of static member in IP-global.The max-eleme'
                      + 'nts depends on the product.'
                        ;
            key 'group-ip supervlan-name subvlan-id interface'
                ;
            leaf group-ip {
              description 'Group IP address.'
                          ;
              type ncd:ipv4-address ;
            }
            leaf supervlan-name {
              description 'Supervlan interface name.'
                          ;
              type ncd:ifname ;
            }
            leaf subvlan-id {
              description 'VLAN ID.'
                          ;
              type uint16 {
                range 1..4094 ;
              }
            }
            leaf interface {
              description 'Interface name.'
                          ;
              type ncd:ifname ;
            }
          }
        }
        ncd:revise-date 2018-02-12 ;
      }
      container groups {
        // if-feature group ;
        description 'IGMP snooping global groups configure.'
                    ;
        list group {
          description 'Configure group max host number.'
                      ;
          key group-ip ;
          leaf group-ip {
            description 'Group IP address.'
                        ;
            type ncd:ipv4-address ;
          }
          leaf max-member-num {
            // if-feature max-host-in-group ;
            description 'Max number of IGMP member can access to this group.Its'
                      + ' maximum value depends on the product.'
                        ;
            type uint32 {
              range 1..4000 ;
            }
          }
        }
        ncd:revise-date 2018-02-12 ;
      }
      container interfaces {
        // if-feature interface ;
        description 'IGMP snooping global interfaces configure.'
                    ;
        list interface {
          key interface ;
          leaf interface {
            type ncd:ifname ;
          }
          leaf max-member-num {
            // if-feature max-host-in-interface ;
            description 'Max number of IGMP member can access to this interface'
                      + '.Its maximum value depends on the product.'
                        ;
            type uint32 {
              range 1..4000 ;
            }
          }
        }
        ncd:revise-date 2018-02-12 ;
      }
      container evpn-vplses {
        // if-feature evpn-vpls ;
        description "IGMP snooping EVPN VPLS configure.Can't config IGMP snoopi"
                  + "ng in EVPN VPLS if the EVPN VPLS instance not exist.If IGM"
                  + "P snooping configuration exist in EVPN VPLS,the EVPN VPLS "
                  + "instance can't be deleted."
                    ;
        list evpn-vpls {
          description 'The config of instance EVPN VPLS.'
                      ;
          key name ;
          leaf name {
            description 'Submode instance Name of EVPN VPLS.'
                        ;
            type string {
              length 1..32 ;
            }
          }
          leaf snooping-switch {
            description 'Enable/disable IGMP snooping in this instance.'
                        ;
            type switch-type ;
            default disable ;
          }
          leaf member-fast-leave {
            description 'Enable/disable group membership fast leave in this ins'
                      + 'tance.'
                        ;
            type switch-type ;
            default disable ;
          }
          leaf acl-name {
            description 'Configure an ACL rule in this instance.'
                        ;
            type string {
              length 0..31 ;
            }
          }
          leaf member-time-out {
            description 'Member aging time in this instance.'
                        ;
            type uint16 {
              range 30..65535 ;
            }
            units second ;
            default 260 ;
          }
          leaf mrouter-time-out {
            description 'Multicast router port aging time in this instance.'
                        ;
            type uint16 {
              range 30..65535 ;
            }
            units second ;
            default 260 ;
          }
          leaf work-mode {
            description 'Work mode in this instance: proxy, transparent or rout'
                      + 'er.'
                        ;
            type work-mode-type ;
            default proxy ;
          }
          leaf proxy-ip {
            description 'This IP address is used as source IP when sending IGMP'
                      + ' Report and Leave in proxy mode.'
                        ;
            type ncd:ipv4-address ;
          }
          leaf query-ip {
            description 'This IP address is used as source IP when sending IGMP'
                      + ' Query.'
                        ;
            type ncd:ipv4-address ;
          }
          leaf max-group-num {
            description 'Max number of multicast group can access in this insta'
                      + 'nce.Its default value and maximum value depends on the'
                      + ' product.'
                        ;
            type uint32 {
              range 1..4294967295 ;
            }
          }
          leaf max-member-num {
            description 'Max number of IGMP member can access to this instance.'
                      + 'Its maximum value depends on the product.'
                        ;
            type uint32 {
              range 1..4294967295 ;
            }
          }
          leaf ndl-enable {
            description 'Enable/disable all ports are not allowed to learn dyna'
                      + 'mic mrouter port(s).'
                        ;
            type switch-type ;
            default disable ;
          }
          leaf last-mem-qry-interval {
            description 'The last member query interval is the max response tim'
                      + 'e inserted into group-specific queries sent in respons'
                      + 'e to leave group messages, and is also the amount of t'
                      + 'ime between group-specific query messages.'
                        ;
            type uint16 {
              range 1..25 ;
            }
            units second ;
            default 1 ;
          }
          leaf query-version {
            description 'Querier version: V1, V2 or V3.'
                        ;
            type version-type ;
            default v2 ;
          }
          leaf query-enable {
            description 'Enable/disable querier in this instance.'
                        ;
            type switch-type ;
            default disable ;
          }
          leaf learning-vxlan-evpn-tunnel {
            description 'Learning vxlan-evpn-tunnel.'
                        ;
            type switch-type ;
            default disable ;
          }
          container drops {
            list drop {
              description 'The config of group with drop in instance EVPN VPLS.'
                        + 'The max-elements depends on the product.'
                          ;
              key group-ip ;
              leaf group-ip {
                description 'Group IP address.'
                            ;
                type ncd:ipv4-address ;
              }
            }
          }
          container prejoins {
            list prejoin {
              description 'The config of group with prejoin in instance EVPN VP'
                        + 'LS.The max-elements depends on the product.'
                          ;
              key group-ip ;
              leaf group-ip {
                description 'Group IP address.'
                            ;
                type ncd:ipv4-address ;
              }
            }
          }
          container max-member-nums {
            list max-member-num {
              description 'The config of group with max-member-num in instance '
                        + 'EVPN VPLS.The max-elements depends on the product.'
                          ;
              key group-ip ;
              leaf group-ip {
                description 'Group IP address.'
                            ;
                type ncd:ipv4-address ;
              }
              leaf max-member-num {
                description 'Max number of IGMP member can access to this group'
                          + '.Its default value and maximum'+"\n"
                          + 'value depends on the product.'
                            ;
                type uint32 {
                  range 1..4000 ;
                }
              }
            }
          }
          container mrouters {
            description 'The config of static mrouter in instance EVPN VPLS.The'
                      + ' max-elements depends on the product.'
                        ;
            list vlan-interface {
              description 'The config of static mrouter in instance EVPN VPLS, '
                        + 'when with VLAN interface.'
                          ;
              key 'vlan-interface interface'
                  ;
              leaf vlan-interface {
                description 'VLAN interface name.'
                            ;
                type ncd:ifname ;
              }
              leaf interface {
                description 'Interface name.'
                            ;
                type ncd:ifname ;
              }
              leaf version {
                description 'Mrouter port version: V1, V2 or V3.'
                            ;
                type mrouter-version-type ;
                default v2 ;
              }
            }
            list interface {
              description 'The config of static mrouter in instance EVPN VPLS, '
                        + 'support interfaces except vlan-interface and static-'
                        + 'tunnel.'
                          ;
              key 'interface untag'
                  ;
              leaf interface {
                description 'Interface name.'
                            ;
                type ncd:ifname ;
              }
              leaf untag {
                description 'Untag interface.'
                            ;
                type switch-type ;
              }
              leaf version {
                description 'Mrouter port version: V1, V2 or V3.'
                            ;
                type mrouter-version-type ;
                default v2 ;
              }
            }
            list static-tunnel {
              description 'The config of static mrouter in instance EVPN VPLS, '
                        + 'when with static tunnel.'
                          ;
              key 'interface vni'
                  ;
              leaf interface {
                description 'Interface name.'
                            ;
                type ncd:ifname ;
              }
              leaf vni {
                description 'VXLAN network ID.'
                            ;
                type uint32 {
                  range 1..16777215 ;
                }
              }
              leaf version {
                description 'Mrouter port version: V1, V2 or V3.'
                            ;
                type mrouter-version-type ;
                default v2 ;
              }
            }
          }
          container ports {
            description 'The config of port in instance EVPN VPLS.'
                        ;
            list vlan-interface {
              description 'The config of port in instance EVPN VPLS, when the p'
                        + 'ort is VLAN interface.'
                          ;
              key 'vlan-interface interface'
                  ;
              leaf vlan-interface {
                description 'VLAN interface name.'
                            ;
                type ncd:ifname ;
              }
              leaf interface {
                description 'Interface name.'
                            ;
                type ncd:ifname ;
              }
              leaf snooping-switch {
                description 'Enable/Disable IGMP snooping in the interface.'
                            ;
                type switch-type ;
                default enable ;
              }
              leaf mrouter-guard {
                description 'Interface multicast router guard function is enabl'
                          + 'ed.'
                            ;
                type switch-type ;
                default disable ;
              }
            }
            list interface {
              description 'The config of port in instance EVPN VPLS, support in'
                        + 'terfaces except vlan-interface and static-tunnel.'
                          ;
              key 'interface untag'
                  ;
              leaf interface {
                description 'Interface name.'
                            ;
                type ncd:ifname ;
              }
              leaf untag {
                description 'Untag interface.'
                            ;
                type switch-type ;
              }
              leaf snooping-switch {
                description 'Enable/Disable IGMP snooping in the interface.'
                            ;
                type switch-type ;
                default enable ;
              }
              leaf mrouter-guard {
                description 'Interface multicast router guard function is enabl'
                          + 'ed.'
                            ;
                type switch-type ;
                default disable ;
              }
            }
            list static-tunnel {
              description 'The config of port in instance EVPN VPLS, when the p'
                        + 'ort is static tunnel.'
                          ;
              key 'interface vni'
                  ;
              leaf interface {
                description 'Interface name.'
                            ;
                type ncd:ifname ;
              }
              leaf vni {
                description 'VXLAN network ID.'
                            ;
                type uint32 {
                  range 1..16777215 ;
                }
              }
              leaf snooping-switch {
                description 'Enable/Disable IGMP snooping in the interface.'
                            ;
                type switch-type ;
                default enable ;
              }
              leaf mrouter-guard {
                description 'Interface multicast router guard function is enabl'
                          + 'ed.'
                            ;
                type switch-type ;
                default disable ;
              }
            }
          }
          container members {
            description 'The config of static member in instance EVPN VPLS.The '
                      + 'max-elements depends on the product.'
                        ;
            list vlan-interface {
              description 'The config of static member in instance EVPN VPLS, w'
                        + 'hen with VLAN interface.'
                          ;
              key 'group-ip vlan-interface interface'
                  ;
              leaf group-ip {
                description 'Group IP address.'
                            ;
                type ncd:ipv4-address ;
              }
              leaf vlan-interface {
                description 'VLAN interface name.'
                            ;
                type ncd:ifname ;
              }
              leaf interface {
                description 'Interface name.'
                            ;
                type ncd:ifname ;
              }
            }
            list interface {
              description 'The config of static member in instance EVPN VPLS, s'
                        + 'upport interfaces except vlan-interface and static-t'
                        + 'unnel.'
                          ;
              key 'interface group-ip untag'
                  ;
              leaf group-ip {
                description 'Group IP address.'
                            ;
                type ncd:ipv4-address ;
              }
              leaf interface {
                description 'Interface name.'
                            ;
                type ncd:ifname ;
              }
              leaf untag {
                description 'Untag interface.'
                            ;
                type switch-type ;
              }
            }
            list static-tunnel {
              description 'The config of static member in instance EVPN VPLS, w'
                        + 'hen with static tunnel.'
                          ;
              key 'group-ip interface vni'
                  ;
              leaf group-ip {
                description 'Group IP address.'
                            ;
                type ncd:ipv4-address ;
              }
              leaf interface {
                description 'Interface name.'
                            ;
                type ncd:ifname ;
              }
              leaf vni {
                description 'VXLAN network ID.'
                            ;
                type uint32 {
                  range 1..16777215 ;
                }
              }
            }
          }
          container ndls {
            description 'The config of port not allowed to learn dynamic mroute'
                      + 'r in instance EVPN VPLS. The max-elements depends on t'
                      + 'he product.'
                        ;
            list vlan-interface {
              description 'The config of port not allowed to learn dynamic mrou'
                        + 'ter in instance EVPN VPLS, when with VLAN interface.'
                          ;
              key 'vlan-interface interface'
                  ;
              leaf vlan-interface {
                description 'VLAN interface name.'
                            ;
                type ncd:ifname ;
              }
              leaf interface {
                description 'Interface name.'
                            ;
                type ncd:ifname ;
              }
            }
            list interface {
              description 'The config of port not allowed to learn dynamic mrou'
                        + 'ter in instance EVPN VPLS, support interfaces except'
                        + ' vlan-interface and static-tunnel.'
                          ;
              key 'interface untag'
                  ;
              leaf interface {
                description 'Interface name.'
                            ;
                type ncd:ifname ;
              }
              leaf untag {
                description 'Untag interface.'
                            ;
                type switch-type ;
              }
            }
            list static-tunnel {
              description 'The config of port not allowed to learn dynamic mrou'
                        + 'ter in instance EVPN VPLS, when with static tunnel.'
                          ;
              key 'interface vni'
                  ;
              leaf interface {
                description 'Interface name.'
                            ;
                type ncd:ifname ;
              }
              leaf vni {
                description 'VXLAN network ID.'
                            ;
                type uint32 {
                  range 1..16777215 ;
                }
              }
            }
          }
        }
        ncd:revise-date 2018-06-13 ;
      }
    }
  }
  container state {
    config false ;
    description 'State model.'
                ;
    container igmp-snooping {
      description 'IGMP snooping state parameters.'
                  ;
      container vpls {
        // if-feature vpls ;
        description 'IGMP snooping VPLS information.'
                    ;
        list member {
          description 'The information of member in instance VPLS.'
                      ;
          key 'vpls-name group-ip source-ip interface-name'
              ;
          leaf vpls-name {
            description 'Submode instance Name of VPLS.'
                        ;
            type string {
              length 1..32 ;
            }
          }
          leaf group-ip {
            description 'Group IP address.'
                        ;
            type ncd:ipv4-address ;
          }
          leaf source-ip {
            description 'Source IP address.'
                        ;
            type ncd:ipv4-address ;
          }
          leaf interface-name {
            description 'Interface name of this member.'
                        ;
            type ncd:ifname ;
          }
          leaf instance-id {
            description 'Submode instance ID of VPLS.'
                        ;
            type uint32 ;
          }
          leaf state {
            description 'State of this member.'
                        ;
            type version-type ;
          }
          leaf mode {
            description 'Mode of this member.'
                        ;
            type mode-type ;
          }
          leaf remain-time {
            description 'Remain time of this member.'
                        ;
            type string {
              length 1..10 ;
            }
          }
          leaf present-time {
            description 'Present time of this member.'
                        ;
            type string {
              length 1..10 ;
            }
            ncd:revise-date 2018-02-12 ;
          }
          ncd:select vpls-name ;
          ncd:select 'vpls-name group-ip source-ip'
                     ;
          ncd:select 'vpls-name group-ip source-ip interface-name'
                     ;
        }
      }
      container vlan {
        // if-feature vlan ;
        list member {
          description 'The information of member in instance VLAN.'
                      ;
          key 'vlan-id group-ip source-ip interface-name'
              ;
          leaf vlan-id {
            description 'Submode instance ID of VLAN.'
                        ;
            type uint32 {
              range 1..4094 ;
            }
          }
          leaf group-ip {
            description 'Group IP address.'
                        ;
            type ncd:ipv4-address ;
          }
          leaf source-ip {
            description 'Source IP address.'
                        ;
            type ncd:ipv4-address ;
          }
          leaf interface-name {
            description 'Interface name of this member.'
                        ;
            type ncd:ifname ;
          }
          leaf state {
            description 'State of this member.'
                        ;
            type version-type ;
          }
          leaf mode {
            description 'Mode of this member.'
                        ;
            type mode-type ;
          }
          leaf remain-time {
            description 'Remain time of this member.'
                        ;
            type string {
              length 1..10 ;
            }
          }
          leaf present-time {
            description 'Present time of this member.'
                        ;
            type string {
              length 1..10 ;
            }
            ncd:revise-date 2018-02-12 ;
          }
          ncd:select vlan-id ;
          ncd:select 'vlan-id group-ip source-ip'
                     ;
          ncd:select 'vlan-id group-ip source-ip interface-name'
                     ;
        }
      }
      container vbui {
        // if-feature vbui ;
        list member {
          description 'The information of member in instance VBUI.'
                      ;
          key 'vbui-name group-ip source-ip interface-name'
              ;
          leaf vbui-name {
            description 'Submode instance Name of VBUI.'
                        ;
            type string {
              length 1..31 ;
            }
          }
          leaf group-ip {
            description 'Group IP address.'
                        ;
            type ncd:ipv4-address ;
          }
          leaf source-ip {
            description 'Source IP address.'
                        ;
            type ncd:ipv4-address ;
          }
          leaf interface-name {
            description 'Interface name of this member.'
                        ;
            type ncd:ifname ;
          }
          leaf instance-id {
            description 'Submode instance ID of VBUI.'
                        ;
            type uint32 ;
          }
          leaf state {
            description 'State of this member.'
                        ;
            type version-type ;
          }
          leaf mode {
            description 'Mode of this member.'
                        ;
            type mode-type ;
          }
          leaf remain-time {
            description 'Remain time of this member.'
                        ;
            type string {
              length 1..10 ;
            }
          }
          leaf present-time {
            description 'Present time of this member.'
                        ;
            type string {
              length 1..10 ;
            }
            ncd:revise-date 2019-12-05 ;
          }
          ncd:select vbui-name ;
          ncd:select 'vbui-name group-ip source-ip'
                     ;
          ncd:select 'vbui-name group-ip source-ip interface-name'
                     ;
        }
      }
      container vrf {
        // if-feature vrf ;
        list member {
          description 'The information of member in instance VRF.'
                      ;
          key 'vrf-name group-ip source-ip external-vlan-id internal-vlan-id in'
            + 'terface-name phy-interface-name'
              ;
          leaf vrf-name {
            description 'Submode instance Name of VRF.'
                        ;
            type string {
              length 0..32 ;
            }
          }
          leaf group-ip {
            description 'Group IP address.'
                        ;
            type ncd:ipv4-address ;
          }
          leaf source-ip {
            description 'Source IP address.'
                        ;
            type ncd:ipv4-address ;
          }
          leaf external-vlan-id {
            description 'External VLAN ID of this member.'
                        ;
            type uint32 {
              range 0..4094 ;
            }
          }
          leaf internal-vlan-id {
            description 'Internal VLAN ID of this member.'
                        ;
            type uint32 {
              range 0..4094 ;
            }
          }
          leaf interface-name {
            description 'Interface name of this member.'
                        ;
            type ncd:ifname ;
          }
          leaf phy-interface-name {
            description 'Physical interface name of this member.'
                        ;
            type ncd:ifname ;
          }
          leaf instance-id {
            description 'Submode instance ID of VRF.'
                        ;
            type uint32 ;
          }
          leaf state {
            description 'State of this member.'
                        ;
            type version-type ;
          }
          leaf mode {
            description 'Mode of this member.'
                        ;
            type mode-type ;
          }
          leaf remain-time {
            description 'Remain time of this member.'
                        ;
            type string {
              length 0..10 ;
            }
          }
          leaf present-time {
            description 'Present time of this member.'
                        ;
            type string {
              length 1..10 ;
            }
            ncd:revise-date 2019-12-05 ;
          }
          ncd:select vrf-name ;
          ncd:select 'vrf-name group-ip source-ip'
                     ;
          ncd:select 'vrf-name group-ip source-ip interface-name'
                     ;
        }
      }
      container ip-global {
        // if-feature ip-global ;
        description 'IGMP snooping IP-global information.'
                    ;
        list member {
          description 'The information of member in instance IP-GLOBAL.'
                      ;
          key 'group-ip source-ip external-vlan-id internal-vlan-id interface-n'
            + 'ame phy-interface-name'
              ;
          leaf group-ip {
            description 'Group IP address.'
                        ;
            type ncd:ipv4-address ;
          }
          leaf source-ip {
            description 'Source IP address.'
                        ;
            type ncd:ipv4-address ;
          }
          leaf external-vlan-id {
            description 'External VLAN ID of this member.'
                        ;
            type uint32 {
              range 0..4094 ;
            }
          }
          leaf internal-vlan-id {
            description 'Internal VLAN ID of this member.'
                        ;
            type uint32 {
              range 0..4094 ;
            }
          }
          leaf interface-name {
            description 'Interface name of this member.'
                        ;
            type ncd:ifname ;
          }
          leaf phy-interface-name {
            description 'Physical interface name of this member.'
                        ;
            type ncd:ifname ;
          }
          leaf state {
            description 'State of this member.'
                        ;
            type version-type ;
          }
          leaf mode {
            description 'Mode of this member.'
                        ;
            type mode-type ;
          }
          leaf remain-time {
            description 'Remain time of this member.'
                        ;
            type string {
              length 0..10 ;
            }
          }
          leaf present-time {
            description 'Present time of this member.'
                        ;
            type string {
              length 1..10 ;
            }
            ncd:revise-date 2018-02-12 ;
          }
          ncd:select 'group-ip source-ip'
                     ;
          ncd:select 'group-ip source-ip interface-name'
                     ;
        }
      }
      list mrouter {
        // if-feature general-state-mrouter ;
        description 'The information of IGMP multicast router.'
                    ;
        key 'vlan-id vpls-name interface-name'
            ;
        leaf vlan-id {
          description 'Submode instance ID of VLAN.'
                      ;
          type uint32 {
            range 0..4094 ;
          }
        }
        leaf vpls-name {
          description 'Submode instance Name of VPLS.'
                      ;
          type string {
            length 0..32 ;
          }
        }
        leaf interface-name {
          description 'Interface name of this mrouter.'
                      ;
          type ncd:ifname ;
        }
        leaf vpn-id {
          description 'Submode instance ID of VPLS.'
                      ;
          type uint32 {
            range 0..8000 ;
          }
        }
        leaf state {
          description 'State of this mrouter.'
                      ;
          type mode-type ;
        }
        leaf version {
          description 'Version of this mrouter.'
                      ;
          type version-type ;
        }
        leaf remain-time {
          description 'Remain time of this mrouter.'
                      ;
          type uint32 {
            range 0..65535 ;
          }
          units second ;
        }
        leaf querier-ip {
          description 'Querier IP address.'
                      ;
          type ncd:ipv4-address ;
          ncd:revise-date 2015-10-30 ;
        }
        leaf present-time {
          description 'Present time of this mrouter.'
                      ;
          type string {
            length 1..10 ;
          }
          ncd:revise-date 2018-02-12 ;
        }
        ncd:select 'vlan-id interface-name'
                   ;
        ncd:select 'vpls-name interface-name'
                   ;
      }
      container summary {
        description 'Show summary info of groups, members and routers.'
                    ;
        container group {
          description 'Show summary info of groups.'
                      ;
          container global {
            description 'Show global summary info of groups.'
                        ;
            leaf total {
              description 'Total groups number.'
                          ;
              type uint32 ;
            }
            leaf exist-host {
              description 'Groups Number with host.'
                          ;
              type uint32 ;
            }
            leaf cfg-drop {
              description 'Groups number configured as drop.'
                          ;
              type uint32 ;
            }
            leaf cfg-prejoin {
              description 'Groups number configured as prejoin.'
                          ;
              type uint32 ;
            }
            leaf cfg-max-host {
              description 'Groups number with max hosts limited.'
                          ;
              type uint32 ;
            }
            leaf source-specific {
              description 'Source-specific groups number.'
                          ;
              type uint32 ;
            }
            leaf anycast-specific {
              description 'Anycast-specific groups number.'
                          ;
              type uint32 ;
            }
          }
        }
        container member {
          description 'Show summary info of members.'
                      ;
          container global {
            description 'Show global summary info of members.'
                        ;
            leaf total {
              description 'Total members number.'
                          ;
              type uint32 ;
            }
            leaf dynamic {
              description 'Dynamic members number.'
                          ;
              type uint32 ;
            }
            leaf static {
              description 'Static members number.'
                          ;
              type uint32 ;
            }
          }
        }
        container mrouter {
          description 'Show summary info of routers.'
                      ;
          container global {
            description 'Show global summary info of routers.'
                        ;
            leaf total {
              description 'Total mrouter ports number.'
                          ;
              type uint32 ;
            }
            leaf dynamic {
              description 'Dynamic mrouter ports number.'
                          ;
              type uint32 ;
            }
            leaf static {
              description 'Static mrouter ports number.'
                          ;
              type uint32 ;
            }
          }
        }
      }
      container vxlan {
        // if-feature vxlan ;
        description 'IGMP snooping VXLAN information.'
                    ;
        list member {
          description 'The information of member in instance VXLAN.'
                      ;
          key 'vxlan-id group-ip source-ip interface-name external-vlan-id inte'
            + 'rnal-vlan-id'
              ;
          leaf vxlan-id {
            description 'Submode instance ID of VXLAN.'
                        ;
            type uint32 {
              range 1..16777215 ;
            }
          }
          leaf group-ip {
            description 'Group IP address.'
                        ;
            type ncd:ipv4-address ;
          }
          leaf source-ip {
            description 'Source IP address.'
                        ;
            type ncd:ipv4-address ;
          }
          leaf interface-name {
            description 'Interface name of this member.'
                        ;
            type ncd:ifname ;
          }
          leaf external-vlan-id {
            description 'External VLAN ID of this member.'
                        ;
            type uint32 {
              range 0..4094 ;
            }
          }
          leaf internal-vlan-id {
            description 'Internal VLAN ID of this member.'
                        ;
            type uint32 {
              range 0..4094 ;
            }
          }
          leaf state {
            description 'State of this member.'
                        ;
            type version-type ;
          }
          leaf mode {
            description 'Mode of this member.'
                        ;
            type mode-type ;
          }
          leaf remain-time {
            description 'Remain time of this member.'
                        ;
            type string {
              length 1..10 ;
            }
          }
          leaf present-time {
            description 'Present time of this member.'
                        ;
            type string {
              length 1..10 ;
            }
            ncd:revise-date 2019-12-05 ;
          }
          ncd:select vxlan-id ;
          ncd:select 'vxlan-id group-ip source-ip'
                     ;
          ncd:select 'vxlan-id group-ip source-ip interface-name'
                     ;
        }
        list mrouter {
          // if-feature vxlan ;
          description 'The information of IGMP multicast router.'
                      ;
          key 'vxlan-id interface-name external-vlan-id internal-vlan-id'
              ;
          leaf vxlan-id {
            description 'Submode instance ID of VXLAN.'
                        ;
            type uint32 {
              range 1..16777215 ;
            }
          }
          leaf interface-name {
            description 'Interface name of this mrouter.'
                        ;
            type ncd:ifname ;
          }
          leaf external-vlan-id {
            description 'External VLAN ID of this member.'
                        ;
            type uint32 {
              range 0..4094 ;
            }
          }
          leaf internal-vlan-id {
            description 'Internal VLAN ID of this member.'
                        ;
            type uint32 {
              range 0..4094 ;
            }
          }
          leaf state {
            description 'State of this mrouter.'
                        ;
            type mode-type ;
          }
          leaf version {
            description 'Version of this mrouter.'
                        ;
            type version-type ;
          }
          leaf remain-time {
            description 'Remain time of this mrouter.'
                        ;
            type uint32 {
              range 0..65535 ;
            }
            units second ;
          }
          leaf querier-ip {
            description 'Querier IP address.'
                        ;
            type ncd:ipv4-address ;
          }
          leaf present-time {
            description 'Present time of this mrouter.'
                        ;
            type string {
              length 1..10 ;
            }
            ncd:revise-date 2019-12-05 ;
          }
          ncd:select 'vxlan-id interface-name'
                     ;
        }
        ncd:revise-date 2017-05-23 ;
      }
      container ring-tree {
        // if-feature ring-tree ;
        description 'IGMP snooping Ring Tree information.'
                    ;
        list member {
          // if-feature ring-tree ;
          description 'The information of member in instance Ring Tree.'
                      ;
          key 'ring-tree-name group-ip source-ip interface-name'
              ;
          leaf ring-tree-name {
            description 'Submode instance name of Ring Tree.'
                        ;
            type string {
              length 1..32 ;
            }
          }
          leaf group-ip {
            description 'Group IP address.'
                        ;
            type ncd:ipv4-address ;
          }
          leaf source-ip {
            description 'Source IP address.'
                        ;
            type ncd:ipv4-address ;
          }
          leaf interface-name {
            description 'Interface name of this member.'
                        ;
            type ncd:ifname ;
          }
          leaf instance-id {
            description 'Submode instance ID of Ring Tree.'
                        ;
            type uint32 {
              range 1..65535 ;
            }
          }
          leaf state {
            description 'State of this member.'
                        ;
            type version-type ;
          }
          leaf mode {
            description 'Mode of this member.'
                        ;
            type mode-type ;
          }
          leaf remain-time {
            description 'Remain time of this member.'
                        ;
            type string {
              length 1..10 ;
            }
          }
          leaf present-time {
            description 'Present time of this member.'
                        ;
            type string {
              length 1..10 ;
            }
            ncd:revise-date 2019-12-05 ;
          }
          ncd:select ring-tree-name ;
          ncd:select 'ring-tree-name group-ip source-ip'
                     ;
          ncd:select 'ring-tree-name group-ip source-ip interface-name'
                     ;
        }
        list mrouter {
          // if-feature ring-tree ;
          description 'The information of IGMP multicast router.'
                      ;
          key 'ring-tree-name interface-name'
              ;
          leaf ring-tree-name {
            description 'Submode instance name of Ring Tree.'
                        ;
            type string {
              length 1..32 ;
            }
          }
          leaf interface-name {
            description 'Interface name of this mrouter.'
                        ;
            type ncd:ifname ;
          }
          leaf instance-id {
            description 'Submode instance ID of Ring Tree.'
                        ;
            type uint32 {
              range 1..65535 ;
            }
          }
          leaf state {
            description 'State of this mrouter.'
                        ;
            type mode-type ;
          }
          leaf version {
            description 'Version of this mrouter.'
                        ;
            type version-type ;
          }
          leaf remain-time {
            description 'Remain time of this mrouter.'
                        ;
            type uint32 {
              range 0..65535 ;
            }
            units second ;
          }
          leaf querier-ip {
            description 'Querier IP address.'
                        ;
            type ncd:ipv4-address ;
          }
          leaf present-time {
            description 'Present time of this mrouter.'
                        ;
            type string {
              length 1..10 ;
            }
            ncd:revise-date 2019-12-05 ;
          }
          ncd:select 'ring-tree-name interface-name'
                     ;
        }
        ncd:revise-date 2017-10-27 ;
      }
      container evpn-vpls {
        // if-feature evpn-vpls ;
        description 'IGMP snooping EVPN VPLS information.'
                    ;
        list member {
          description 'The information of member in instance EVPN VPLS.'
                      ;
          key 'evpn-vpls-name group-ip source-ip interface-name vni external-vl'
            + 'an-id internal-vlan-id'
              ;
          leaf evpn-vpls-name {
            description 'Submode instance Name of EVPN VPLS.'
                        ;
            type string {
              length 1..32 ;
            }
          }
          leaf group-ip {
            description 'Group IP address.'
                        ;
            type ncd:ipv4-address ;
          }
          leaf source-ip {
            description 'Source IP address.'
                        ;
            type ncd:ipv4-address ;
          }
          leaf interface-name {
            description 'Interface name of this member.'
                        ;
            type ncd:ifname ;
          }
          leaf vni {
            description 'VXLAN network ID.'
                        ;
            type uint32 {
              range 0..16777215 ;
            }
          }
          leaf external-vlan-id {
            description 'External VLAN ID of this member.'
                        ;
            type uint32 {
              range 0..4094 ;
            }
          }
          leaf internal-vlan-id {
            description 'Internal VLAN ID of this member.'
                        ;
            type uint32 {
              range 0..4094 ;
            }
          }
          leaf state {
            description 'State of this member.'
                        ;
            type version-type ;
          }
          leaf mode {
            description 'Mode of this member.'
                        ;
            type mode-type ;
          }
          leaf remain-time {
            description 'Remain time of this member.'
                        ;
            type string {
              length 1..10 ;
            }
          }
          leaf present-time {
            description 'Present time of this member.'
                        ;
            type string {
              length 1..10 ;
            }
          }
          ncd:select evpn-vpls-name ;
          ncd:select 'evpn-vpls-name group-ip source-ip'
                     ;
          ncd:select 'evpn-vpls-name group-ip source-ip interface-name'
                     ;
        }
        list mrouter {
          description 'The information of IGMP multicast router.'
                      ;
          key 'evpn-vpls-name interface-name vni external-vlan-id internal-vlan'
            + '-id'
              ;
          leaf evpn-vpls-name {
            description 'Submode instance Name of EVPN VPLS.'
                        ;
            type string {
              length 1..32 ;
            }
          }
          leaf interface-name {
            description 'Interface name of this mrouter.'
                        ;
            type ncd:ifname ;
          }
          leaf vni {
            description 'VXLAN network ID.'
                        ;
            type uint32 {
              range 0..16777215 ;
            }
          }
          leaf external-vlan-id {
            description 'External VLAN ID of this member.'
                        ;
            type uint32 {
              range 0..4094 ;
            }
          }
          leaf internal-vlan-id {
            description 'Internal VLAN ID of this member.'
                        ;
            type uint32 {
              range 0..4094 ;
            }
          }
          leaf state {
            description 'State of this mrouter.'
                        ;
            type mode-type ;
          }
          leaf version {
            description 'Version of this mrouter.'
                        ;
            type version-type ;
          }
          leaf querier-ip {
            description 'Querier IP address.'
                        ;
            type ncd:ipv4-address ;
          }
          leaf remain-time {
            description 'Remain time of this mrouter.'
                        ;
            type uint32 {
              range 0..65535 ;
            }
            units second ;
          }
          leaf present-time {
            description 'Present time of this mrouter.'
                        ;
            type string {
              length 1..10 ;
            }
          }
          ncd:select 'evpn-vpls-name interface-name'
                     ;
        }
        ncd:revise-date 2018-06-13 ;
      }
    }
  }
  container operation {
    config false ;
    description 'Command of IGMP snooping clear.'
                ;
    container igmp-snooping {
      description 'Clear IGMP snooping groups.'
                  ;
      container clear {
        description 'Clear IGMP snooping groups.'
                    ;
        container group {
          description 'Clear the specific group of the specific instance.'
                      ;
          presence group ;
          leaf group-ip {
            description 'Multicast group IP address.'
                        ;
            type ncd:ipv4-address ;
            mandatory true ;
          }
          leaf source-ip {
            description 'Source IP address.'
                        ;
            type ncd:ipv4-address ;
          }
          choice instance {
            description Instance. ;
            mandatory true ;
            case vlan {
              // if-feature vlan ;
              description 'Clear all groups of the specific VLAN instance.'
                          ;
              leaf vlan-id {
                description 'VLAN ID.'
                            ;
                type uint16 {
                  range 1..4094 ;
                }
              }
            }
            case vpls {
              // if-feature vpls ;
              description 'Clear all groups of the specific VPLS instance.'
                          ;
              leaf vpls-name {
                description 'VPLS name.'
                            ;
                type string {
                  length 1..32 ;
                }
              }
            }
            case vrf {
              // if-feature vrf ;
              description 'Clear all groups of the specific VRF instance.'
                          ;
              leaf vrf-name {
                description 'VRF name.'
                            ;
                type string {
                  length 0..32 ;
                }
              }
            }
            case ip-global {
              // if-feature ip-global ;
              description 'Clear all groups of the specific IP-global instance.'
                          ;
              leaf ip-global {
                description IP-global. ;
                type empty ;
              }
            }
            case vxlan {
              // if-feature vxlan ;
              description 'Clear all groups of the specific VXLAN instance.'
                          ;
              leaf vxlan-id {
                description 'VXLAN ID.'
                            ;
                type uint32 ;
              }
              ncd:revise-date 2017-05-23 ;
            }
            case ring-tree {
              // if-feature ring-tree ;
              description 'Clear all groups of the specific Ring Tree instance.'
                          ;
              leaf ring-tree-name {
                description 'Ring Tree name.'
                            ;
                type string {
                  length 1..32 ;
                }
              }
              ncd:revise-date 2017-10-27 ;
            }
            case evpn-vpls {
              // if-feature evpn-vpls ;
              description 'Clear all groups of the specific EVPN VPLS instance.'
                          ;
              leaf evpn-vpls-name {
                description 'EVPN VPLS name.'
                            ;
                type string {
                  length 1..32 ;
                }
              }
              ncd:revise-date 2018-06-13 ;
            }
          }
        }
        container groups {
          description 'Clear all groups of the specific instance.'
                      ;
          choice type {
            description 'Clear all groups of the specific instance.'
                        ;
            case vlan {
              // if-feature vlan ;
              description 'Clear all groups of the specific VLAN instance.'
                          ;
              leaf vlan-id {
                description 'VLAN ID.'
                            ;
                type uint16 {
                  range 1..4094 ;
                }
              }
            }
            case vpls {
              // if-feature vpls ;
              description 'Clear all groups of the specific VPLS instance.'
                          ;
              leaf vpls-name {
                description 'VPLS name.'
                            ;
                type string {
                  length 1..32 ;
                }
              }
            }
            case vrf {
              // if-feature vrf ;
              description 'Clear all groups of the specific VRF instance.'
                          ;
              leaf vrf-name {
                description 'VRF name.'
                            ;
                type string {
                  length 0..32 ;
                }
              }
            }
            case ip-global {
              // if-feature ip-global ;
              description 'Clear all groups of the specific IP-global instance.'
                          ;
              leaf ip-global {
                description IP-global. ;
                type empty ;
              }
            }
            case all {
              description 'Clear all groups.'
                          ;
              leaf all-groups {
                description 'All groups.'
                            ;
                type empty ;
              }
            }
            case vxlan {
              // if-feature vxlan ;
              description 'Clear all groups of the specific VXLAN instance.'
                          ;
              leaf vxlan-id {
                description 'VXLAN ID.'
                            ;
                type uint32 ;
              }
              ncd:revise-date 2017-05-23 ;
            }
            case ring-tree {
              // if-feature ring-tree ;
              description 'Clear all groups of the specific Ring Tree instance.'
                          ;
              leaf ring-tree-name {
                description 'Ring Tree name.'
                            ;
                type string {
                  length 1..32 ;
                }
              }
              ncd:revise-date 2017-10-27 ;
            }
            case evpn-vpls {
              // if-feature evpn-vpls ;
              description 'Clear all groups of the specific EVPN VPLS instance.'
                          ;
              leaf evpn-vpls-name {
                description 'EVPN VPLS name.'
                            ;
                type string {
                  length 1..32 ;
                }
              }
              ncd:revise-date 2018-06-13 ;
            }
          }
        }
      }
    }
  }
}
