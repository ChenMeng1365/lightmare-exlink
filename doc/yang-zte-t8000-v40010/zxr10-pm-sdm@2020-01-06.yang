module zxr10-pm-sdm {
  namespace 'http://www.zte.com.cn/zxr10/netconf/schema/rosng/pm-sdm'
            ;
  prefix zxr10-pm-sdm ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2020-01-06 {
    description 'Add show boot version number information command'
                ;
  }
  revision 2019-08-01 {
    description 'Add leaf af-node for contain ports.'
                ;
  }
  container state {
    config false ;
    leaf current-software {
      type string {
        length 1..160 ;
      }
    }
    container upgrade {
      container state {
        leaf rollback-software {
          type string {
            length 1..160 ;
          }
        }
        leaf upgrade-state {
          type enumeration {
            enum COMMIT {
              value 1 ;
            }
            enum ROLLBACK {
              value 2 ;
            }
            enum ACTIVATE {
              value 3 ;
            }
            enum COMPLETE {
              value 4 ;
            }
            enum FAIL {
              value 5 ;
            }
            enum ACTIVATE_COMPLETE {
              value 6 ;
            }
            enum ACTIVATE_FAIL {
              value 7 ;
            }
          }
        }
        leaf upgrade-time {
          type ncd:string-with-blank {
            length 1..32 ;
            pattern '[0-9]{4}\-[0-9]{2}\-[0-9]{2}T[0-9]{2}:[0-9]{2}:[0-9]{2}(\.'
                  + '[0-9]+)?Z[+-][0-9]{2}:[0-9]{2}'
                    ;
          }
        }
      }
    }
    container download {
      container state {
        leaf software-name {
          type string {
            length 1..160 ;
          }
        }
        leaf expected-duration {
          type string {
            length 1..32 ;
          }
        }
        leaf download-state {
          type enumeration {
            enum DOWNLOADING {
              value 0 ;
            }
            enum COMMIT {
              value 1 ;
            }
            enum ROLLBACK {
              value 2 ;
            }
            enum ACTIVATE {
              value 3 ;
            }
            enum COMPLETE {
              value 4 ;
            }
            enum FAIL {
              value 5 ;
            }
            enum ACTIVATE_COMPLETE {
              value 6 ;
            }
            enum ACTIVATE_FAIL {
              value 7 ;
            }
          }
        }
        leaf download-time {
          type ncd:string-with-blank {
            length 1..32 ;
            pattern '[0-9]{4}\-[0-9]{2}\-[0-9]{2}T[0-9]{2}:[0-9]{2}:[0-9]{2}(\.'
                  + '[0-9]+)?Z[+-][0-9]{2}:[0-9]{2}'
                    ;
          }
        }
      }
    }
    container firmware {
      container boot-versions {
        list boot-version {
          description 'show boot-firmware list'
                      ;
          key 'shelf slot cpu'
              ;
          leaf shelf {
            description 'shelf number'
                        ;
            type uint8 ;
          }
          leaf slot {
            description 'slot number'
                        ;
            type uint8 ;
          }
          leaf cpu {
            description 'cpu number'
                        ;
            type uint8 ;
          }
          leaf board-type {
            description 'board type'
                        ;
            type string ;
          }
          leaf board-id {
            description 'board id'
                        ;
            type uint32 ;
          }
          leaf firmware-type {
            description 'firmware type'
                        ;
            type string ;
          }
          leaf master-version {
            description 'master boot version number'
                        ;
            type string ;
          }
          leaf slave-version {
            description 'slave boot version number'
                        ;
            type string ;
          }
          ncd:select 'shelf slot cpu'
                     ;
        }
      }
      ncd:revise-date 2020-01-06 ;
    }
  }
  rpc software-operate {
    input {
      leaf software-operation {
        config false ;
        type enumeration {
          enum SWOP_DOWNLOAD {
            value 1 ;
          }
          enum SWOP_ACTIVATE {
            value 2 ;
          }
          enum SWOP_ROLLBACK {
            value 3 ;
          }
          enum SWOP_COMMIT {
            value 4 ;
          }
          enum SWOP_DELETE {
            value 5 ;
          }
          enum SWOP_CLEANUP {
            value 6 ;
          }
        }
      }
      leaf file-type {
        config false ;
        type enumeration {
          enum software {
            value 1 ;
          }
          enum startrun {
            value 2 ;
          }
        }
      }
      leaf operate-target {
        config false ;
        type string {
          length 1..180 ;
        }
      }
      choice server-info {
        config false ;
        case tftp {
          container tftp-server-info {
            leaf port {
              type uint32 ;
            }
            leaf ip-address {
              type string ;
            }
          }
        }
        case ftp {
          container ftp-server-info {
            leaf port {
              type uint32 ;
            }
            leaf user-name {
              type string {
                length 1..64 ;
              }
            }
            leaf user-password {
              type string {
                length 1..64 ;
              }
            }
            leaf ip-address {
              type string ;
            }
          }
        }
        case sftp {
          container sftp-server-info {
            leaf port {
              type uint32 ;
            }
            leaf user-name {
              type string {
                length 1..64 ;
              }
            }
            leaf user-password {
              type string {
                length 1..64 ;
              }
            }
            leaf ip-address {
              type string ;
            }
          }
        }
        case storage {
          container null ;
        }
      }
      leaf upgrade-type {
        config false ;
        type enumeration {
          enum issu {
            value 1 ;
          }
          enum parallel-reload {
            value 2 ;
          }
          enum reserve-standby {
            value 3 ;
          }
        }
      }
      leaf reboot-type {
        config false ;
        type enumeration {
          enum soft {
            value 1 ;
          }
          enum hard {
            value 2 ;
          }
        }
      }
      leaf vrf-name {
        type string ;
      }
    }
    output {
      leaf result {
        config false ;
        type string {
          length 1..32 ;
        }
      }
    }
  }
  notification event {
    container update {
      config false ;
      container software {
        container state {
          leaf current-software {
            type string {
              length 1..160 ;
            }
          }
        }
        container upgrade {
          container state {
            leaf rollback-software {
              type string {
                length 1..160 ;
              }
            }
            leaf upgrade-state {
              type enumeration {
                enum COMMIT {
                  value 1 ;
                }
                enum ROLLBACK {
                  value 2 ;
                }
                enum ACTIVATE {
                  value 3 ;
                }
                enum COMPLETE {
                  value 4 ;
                }
                enum FAIL {
                  value 5 ;
                }
                enum ACTIVATE_COMPLETE {
                  value 6 ;
                }
                enum ACTIVATE_FAIL {
                  value 7 ;
                }
              }
            }
            leaf upgrade-time {
              type ncd:string-with-blank {
                length 1..32 ;
                pattern '[0-9]{4}\-[0-9]{2}\-[0-9]{2}T[0-9]{2}:[0-9]{2}:[0-9]{2'
                      + '}(\.[0-9]+)?Z[+-][0-9]{2}:[0-9]{2}'
                        ;
              }
            }
          }
        }
        container download {
          container state {
            leaf software-name {
              type string {
                length 1..160 ;
              }
            }
            leaf expected-duration {
              type string {
                length 1..32 ;
              }
            }
            leaf download-state {
              type enumeration {
                enum DOWNLOADING {
                  value 0 ;
                }
                enum COMMIT {
                  value 1 ;
                }
                enum ROLLBACK {
                  value 2 ;
                }
                enum ACTIVATE {
                  value 3 ;
                }
                enum COMPLETE {
                  value 4 ;
                }
                enum FAIL {
                  value 5 ;
                }
                enum ACTIVATE_COMPLETE {
                  value 6 ;
                }
                enum ACTIVATE_FAIL {
                  value 7 ;
                }
              }
            }
            leaf download-time {
              type ncd:string-with-blank {
                length 1..32 ;
                pattern '[0-9]{4}\-[0-9]{2}\-[0-9]{2}T[0-9]{2}:[0-9]{2}:[0-9]{2'
                      + '}(\.[0-9]+)?Z[+-][0-9]{2}:[0-9]{2}'
                        ;
              }
            }
          }
        }
      }
    }
  }
}
