module zxr10-mpls-te {
  namespace 'http://www.zte.com.cn/zxr10/netconf/schema/rosng/mpls-te'
            ;
  prefix te ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf model for mpls-te.'
              ;
  revision 2021-02-25 {
    description '1.Add enum item of the leaf configuration/mpls-te/te-ecmp-grou'
              + 'ps/te-ecmp-group/load-share-policy.'
                ;
  }
  revision 2020-10-20 {
    description '1.Add the container configuration/mpls-te/dynamic-tunnel/tunne'
              + 'ls/tunnel/pce/slave-path.'
                ;
  }
  revision 2020-09-22 {
    description '1. add leaf /configuration/mpls-te/global-config/best-effort-c'
              + 'spf/exclude-overload'
                ;
  }
  revision 2020-08-19 {
    description '1.Add the leaf of configuration/mpls-te/bfd/interfaces/interfa'
              + 'ce/template-name'
                ;
  }
  revision 2020-06-13 {
    description '1.Add the choice of configuration/mpls-te/authentication/inter'
              + 'face/auth-key.'+"\n"
              + '2.delete default value configuration/mpls-te/authentication/in'
              + 'terface/key.'
                ;
  }
  revision 2020-04-23 {
    description '1.Add the choice of configuration/mpls-te/bfd/tunnels/tunnel/d'
              + 'etect-param'
                ;
  }
  revision 2020-04-20 {
    description '1.Delete the choice-case of the leaf /configuration/mpls-te/pa'
              + 'ssive-if/cross-domain/nbr-ospf-node-id and /configuration/mpls'
              + '-te/passive-if/cross-domain/nbr-isis-system-id.'
                ;
  }
  revision 2020-04-13 {
    description '1.Add container configuration/mpls-te/global-config/cspf-tie-b'
              + 'reaking.'
                ;
  }
  revision 2020-02-14 {
    description '1.Modify status deprecated configuration/mpls-te/dynamic-tunne'
              + 'l/tunnels/tunnel/pce-initiate.'+"\n"
              + '2.Modify status deprecated configuration/mpls-te/dynamic-tunne'
              + 'l/tunnels/tunnel/pce-control.'+"\n"
              + '3.Add choice configuration/mpls-te/dynamic-tunnel/tunnels/tunn'
              + 'el/pce.'
                ;
  }
  revision 2020-01-14 {
    description '1.Modify leaf /configuration/mpls-te/passive-if/cross-domain/n'
              + 'br-ospf-node-id.'+"\n"
              + '2.Modify leaf /configuration/mpls-te/passive-if/cross-domain/n'
              + 'br-isis-system-id.'
                ;
  }
  revision 2019-12-30 {
    description '1.Add a container state/mpls-te/local-acc-dynamic-tnnl-new.'
                ;
  }
  revision 2019-12-03 {
    description 'Add underflow container.Add underflow-limit,underflow-percent '
              + 'and underflow-bandwidth to the underflow container.'
                ;
  }
  revision 2019-11-21 {
    description '1.Modify status deprecated configuration/mpls-te/dynamic-tunne'
              + 'l/tunnels/tunnel/hsblsp-frr.'+"\n"
              + '2.Add container configuration/mpls-te/frr/tunnel/hsblsp-frr.'
                ;
  }
  revision 2019-10-28 {
    description '1.Increase the maximum of configuration/mpls-te/global-config/'
              + 'delay/delay_linkup.'
                ;
  }
  revision 2019-09-11 {
    description '1.Add the choice of configuration/mpls-te/dynamic-tunnel/tunne'
              + 'ls/tunnel/pce-control/control-address'
                ;
  }
  revision 2019-09-05 {
    description '1.Modify leaf /configuration/mpls-te/static-tunnels/tunnel/tri'
              + 'ple/ingress-tunnel-id.'
                ;
  }
  revision 2019-08-12 {
    description 'modify the value range of configuration/mpls-te/graceful-resta'
              + 'rt/recovery-time'
                ;
  }
  revision 2019-07-12 {
    description '1.Modify leaf /configuration/mpls-te/static-tunnels/tunnel/lsp'
              + 's/lsp/positive-attribute/in-label.'+"\n"
              + '2.Modify leaf /configuration/mpls-te/static-tunnels/tunnel/lsp'
              + 's/lsp/positive-attribute/out-label.'+"\n"
              + '3.Modify leaf /configuration/mpls-te/static-tunnels/tunnel/lsp'
              + 's/lsp/reverse-attribute/in-label.'+"\n"
              + '4.Modify leaf /configuration/mpls-te/static-tunnels/tunnel/lsp'
              + 's/lsp/reverse-attribute/out-label.'
                ;
  }
  revision 2019-07-01 {
    description '1.Add the choice of configuration/mpls-te/bfd/tunnels/tunnel/r'
              + 'everse-path'
                ;
  }
  revision 2019-06-13 {
    description '1.Modify leaf state/mpls-te/frr-protect/frr-protect-new/teTunn'
              + 'elProtType'+"\n"
              + '2.Add the container of configuration/mpls-te/te-interfaces/int'
              + 'erface/second-frr'
                ;
  }
  revision 2019-05-13 {
    description '1.Add ipv6 choice to /configuration/mpls-te/static-tunnels/tun'
              + 'nel/triple.'+"\n"
              + '2.Add ipv6 choice to /configuration/mpls-te/static-tunnels/tun'
              + 'nel/lsps/positive-attribute.'+"\n"
              + '3.Add ipv6 choice to /configuration/mpls-te/static-tunnels/tun'
              + 'nel/lsps/reverse-attribute.'
                ;
  }
  revision 2019-04-23 {
    description '1.Add choice /operation/clear/te/tunnel-type'
                ;
  }
  revision 2019-03-14 {
    description '1.Modify leaf /configuration/mpls-te/dynamic-tunnel/tunnels/gt'
              + 'unnel/bandwidth/bandwidth.'+"\n"
              + '2.Modify leaf /configuration/mpls-te/dynamic-tunnel/tunnels/gt'
              + 'unnel/bandwidth/cbs.'+"\n"
              + '3.Modify leaf /configuration/mpls-te/dynamic-tunnel/tunnels/gt'
              + 'unnel/bandwidth/eir.'+"\n"
              + '4.Modify leaf /configuration/mpls-te/dynamic-tunnel/tunnels/gt'
              + 'unnel/bandwidth/ebs.'+"\n"
              + '5.Modify leaf /configuration/mpls-te/static-tunnels/tunnel/lsp'
              + 's/positive-attribute/out-burst.'+"\n"
              + '6.Modify leaf /configuration/mpls-te/static-tunnels/tunnel/lsp'
              + 's/positive-attribute/out-peak.'+"\n"
              + '7.Modify leaf /configuration/mpls-te/static-tunnels/tunnel/lsp'
              + 's/positive-attribute/out-excess-burst.'+"\n"
              + '8.Modify leaf /configuration/mpls-te/static-tunnels/tunnel/lsp'
              + 's/reverse-attribute/out-burst.'+"\n"
              + '9.Modify leaf /configuration/mpls-te/static-tunnels/tunnel/lsp'
              + 's/reverse-attribute/out-peak.'+"\n"
              + '10.Modify leaf /configuration/mpls-te/static-tunnels/tunnel/ls'
              + 'ps/reverse-attribute/out-excess-burst.'+"\n"
              + '11.Modify leaf /configuration/mpls-te/static-gtunnels/gtunnel/'
              + 'bandwidth/bandwidth.'+"\n"
              + '12.Modify leaf /configuration/mpls-te/static-gtunnels/gtunnel/'
              + 'bandwidth/cbs.'+"\n"
              + '13.Modify leaf /configuration/mpls-te/static-gtunnels/gtunnel/'
              + 'bandwidth/eir.'+"\n"
              + '14.Modify leaf /configuration/mpls-te/static-gtunnels/gtunnel/'
              + 'bandwidth/ebs.'+"\n"
              + '15.Modify leaf /configuration/mpls-te/tnnl-rate-limit/tunnel/c'
              + 'ir.'+"\n"
              + '16.Modify leaf /configuration/mpls-te/tnnl-rate-limit/tunnel/c'
              + 'bs.'+"\n"
              + '17.Modify leaf /configuration/mpls-te/tnnl-rate-limit/tunnel/p'
              + 'ir.'+"\n"
              + '18.Modify leaf /configuration/mpls-te/tnnl-rate-limit/tunnel/p'
              + 'bs.'+"\n"
              + '19.Add description to /configuration/mpls-te/global-config/rou'
              + 'ter-id.'+"\n"
              + '20.Add description to /configuration/mpls-te/auto-bandwidth/tu'
              + 'nnels/tunnel/overflow.'
                ;
  }
  revision 2018-09-29 {
    description '1.Add the container of configuration/mpls-te/dynamic-tunnel/tu'
              + 'nels/tunnel/mainlsp-frr'+"\n"
              + '2.Add leaf configuration/mpls-te/dynamic-tunnel/tunels/tunnel/'
              + 'mainlsp-frr/block'
                ;
  }
  revision 2018-08-29 {
    description '1.Add leaf configuration/mpls-te/dynamic-tunnel/tunels/tunnel/'
              + 'pce-control/pce-control-addr'
                ;
  }
  revision 2018-08-28 {
    description '1.Modify the node:/configuration/mpls-te/global-config/cspf-pr'
              + 'eferred-igp/'+"\n"
              + '2.Add the node:/configuration/mpls-te/dynamic-tunnel/tunnels/t'
              + 'unnel/tunnel-preferred-igp'
                ;
  }
  revision 2018-08-27 {
    description '1.Add container configuration/mpls-te/dynamic-tunnel/tunels/tu'
              + 'nnel/pre-setup'
                ;
  }
  revision 2018-08-08 {
    description '1.Add leaf configuration/mpls-te/dynamic-tunnel/tunels/tunnel/'
              + 'protect/coexist'+"\n"
              + '2.Add leaf configuration/mpls-te/dynamic-tunnel/tunels/tunnel/'
              + 'protect/nest'+"\n"
              + '3.Add YangList[frr-protect-new] state/mpls-te/frr-protect/frr-'
              + 'protect-new'+"\n"
              + '4.Obsolete YangList[frr-protect] state/mpls-te/frr-protect/frr'
              + '-protect'
                ;
  }
  revision 2018-07-14 {
    description '1.Add the container of configuration/cac'
                ;
  }
  revision 2018-05-26 {
    description '1.Add the container of configuration/mpls-te/global-config/ent'
              + 'ropy-label'
                ;
  }
  revision 2018-05-14 {
    description '1.Add the container of configuration/mpls-te/global-config/ipv'
              + '6-router-id'
                ;
  }
  revision 2018-03-03 {
    description 'Add leaf configuration/mpls-te/frr/frr-topology/enable'
                ;
  }
  revision 2018-02-24 {
    description 'Add leaf configuration/mpls-te/global-config/best-effort-cspf/'
              + 'without-affinity-enable'
                ;
  }
  revision 2018-02-11 {
    description '1.Add the list of configuration/mpls-te/affinity/tunnels/affin'
              + 'ity-bit-frr'+"\n"
              + '2.Add the list of configuration/mpls-te/affinity/tunnels/affin'
              + 'ity-name-frr'
                ;
  }
  revision 2018-01-17 {
    description 'Add leaf configuration/mpls-te/global-config/delay/reactive-pr'
              + 'ecise'
                ;
  }
  revision 2018-01-10 {
    description 'Add configuration/mpls-te/dynamic-tunnel/tunnels/tunnel/ref-af'
              + 'finity'
                ;
  }
  revision 2017-11-30 {
    description '1.Add the container of configuration/mpls-te/affinity/affinity'
              + '-maps'+"\n"
              + '2.Add the list of configuration/mpls-te/affinity/tunnels/affin'
              + 'ity-name-hot'+"\n"
              + '3.Add the list of configuration/mpls-te/affinity/tunnels/affin'
              + 'ity-name-master'+"\n"
              + '4.Add the list of configuration/mpls-te/affinity/interfaces/af'
              + 'finity-name-interface'
                ;
  }
  revision 2017-11-28 {
    description 'Add the track-name leaf of configuration/mpls-te/static-gtunne'
              + 'ls/gtunnel.'
                ;
  }
  revision 2017-11-14 {
    description '1.Add the container of configuration/mpls-te/frr/frr-backup/'
                ;
  }
  revision 2017-10-19 {
    description '1.Add the leaf of configuration/mpls-te/graceful-restart/stand'
              + 'ard-recovery-path'+"\n"
              + '2.Add the container of configuration/mpls-te/graceful-restart/'
              + 'standard-nbr'+"\n"
              + '3.Add the container of configuration/mpls-te/global-config/sig'
              + 'nalling-tear'
                ;
  }
  revision 2017-10-14 {
    description '1.Add the perf-code of configuration/mpls-te/auto-bandwidth/tu'
              + 'nnels/tunnel/adjust-frequency '+"\n"
              + '2.Add the perf-code of configuration/mpls-te/auto-bandwidth/gl'
              + 'obal/sample-frequency'
                ;
  }
  revision 2017-09-18 {
    description '1.Add the container of configuration/mpls-te/global-config/del'
              + 'ay/delay-topo-change'
                ;
  }
  revision 2017-09-14 {
    description '1.Add enum item of the leaf /notification/dynamic-tunnel/tunne'
              + 'l/report-reasion'+"\n"
              + '                 2.obsolete node state/mpls-te/sr-tunnel'+"\n"
              + '                 3.obsolete node configuration/mpls-te/sr-expl'
              + '-path'+"\n"
              + '                 4.obsolete notification  sr-tunnel'+"\n"
              + '                 5.obsolete list configuration/mpls-te/dynamic'
              + '-tunnel/tunnels/tunnel/sr-path'+"\n"
              + '                 6.obsolete leaf configuration/mpls-te/dynamic'
              + '-tunnel/tunnels/tunnel/segment-routing'
                ;
  }
  revision 2017-09-04 {
    description '1.Add configuration/mpls-te/bfd/tunels/tunnel/reverse-tunnelid'
                ;
  }
  revision 2017-08-10 {
    description '1.Add the container of configuration/mpls-te/global-config/bin'
              + 'd-sid-allocate'
                ;
  }
  revision 2017-08-04 {
    description '1.Add spme leaf to /configuration/mpls-te/static-tunnels/tunne'
              + 'l.'
                ;
  }
  revision 2017-06-21 {
    description '1.Modify configuration/mpls-te/static-gtunnels/gtunnel/lsps/ls'
              + 'p/positive-in-attribute'+"\n"
              + '2.Modify configuration/mpls-te/static-gtunnels/gtunnel/lsps/ls'
              + 'p/positive-out-attribute'+"\n"
              + '3.Modify configuration/mpls-te/static-gtunnels/gtunnel/lsps/ls'
              + 'p/reverse-in-attribute'+"\n"
              + '4.Modify configuration/mpls-te/static-gtunnels/gtunnel/lsps/ls'
              + 'p/reverse-out-attribute'
                ;
  }
  revision 2017-04-25 {
    description '1.Add state/mpls-te/sr-tunnel'+"\n"
              + '2.Add the notification of sr-tunnel .'
                ;
  }
  revision 2017-03-31 {
    description '1.Add configuration/mpls-te/static-gtunnels'
                ;
  }
  revision 2016-12-27 {
    description '1.Add the leaf of configuration/mpls-te/explicit-path/name-bas'
              + 'ed/path-paras/path-para/hop-if-id'+"\n"
              + '2.Add the leaf of configuration/mpls-te/explicit-path/id-based'
              + '/path-paras/path-para/hop-if-id'+"\n"
              + '3.Add the list of configuration/mpls-te/dynamic-tunnel/tunnels'
              + '/gtunnel/path-option-list'+"\n"
              + '4.Add the container of configuration/mpls-te/dynamic-tunnel/tu'
              + 'nnels/gtunnel/bandwidth'+"\n"
              + '5.Add the container of configuration/mpls-te/dynamic-tunnel/tu'
              + 'nnels/gtunnel/rros'+"\n"
              + '6.Add the container of configuration/mpls-te/dynamic-tunnel/tu'
              + 'nnels/gtunnel/encoding-type'+"\n"
              + '7.Add the container of configuration/mpls-te/dynamic-tunnel/tu'
              + 'nnels/gtunnel/seg-protect-type'+"\n"
              + '8.Add the container of configuration/mpls-te/dynamic-tunnel/tu'
              + 'nnels/gtunnel/switching-type'+"\n"
              + '9.Add the container of configuration/mpls-te/dynamic-tunnel/tu'
              + 'nnels/gtunnel/g-pid'
                ;
  }
  revision 2016-12-09 {
    description '1.Add hard-pipe leaf to /configuration/mpls-te/static-tunnels/'
              + 'tunnel.'+"\n"
              + '2.Add hard-pipe container to /configuration/mpls-te/te-interfa'
              + 'ces/interface.'
                ;
  }
  revision 2016-09-12 {
    description '1.Add the list of configuration/mpls-te/affinity/tunnels/tunne'
              + 'l-mod-hot'
                ;
  }
  revision 2016-09-08 {
    description '1.Add default value of configuration/mpls-te/gtunnel-groups/gt'
              + 'unnel-group/min-bandwidth-to-activate'
                ;
  }
  revision 2016-09-01 {
    description '1.obsolete leaf node "configuration/mpls-te/sr-expl-path/name-'
              + 'based/path-paras/path-para/type"'+"\n"
              + '2.obsolete leaf node "configuration/mpls-te/sr-expl-path/name-'
              + 'based/path-paras/path-para/router-id"'+"\n"
              + '3.obsolete leaf node "configuration/mpls-te/sr-expl-path/name-'
              + 'based/path-paras/path-para/interface-ip"'+"\n"
              + '4.obsolete leaf node "configuration/mpls-te/sr-expl-path/name-'
              + 'based/path-paras/path-para/peer-router-id"'+"\n"
              + '5.obsolete leaf node "configuration/mpls-te/sr-expl-path/name-'
              + 'based/path-paras/path-para/peer-interface-ip"'+"\n"
              + '6.obsolete leaf node "configuration/mpls-te/sr-expl-path/id-ba'
              + 'sed/path-paras/path-para/type"'+"\n"
              + '7.obsolete leaf node "configuration/mpls-te/sr-expl-path/id-ba'
              + 'sed/path-paras/path-para/router-id"'+"\n"
              + '8.obsolete leaf node "configuration/mpls-te/sr-expl-path/id-ba'
              + 'sed/path-paras/path-para/interface-ip"'+"\n"
              + '9.obsolete leaf node "configuration/mpls-te/sr-expl-path/id-ba'
              + 'sed/path-paras/path-para/peer-router-id"'+"\n"
              + '10.obsolete leaf node "configuration/mpls-te/sr-expl-path/id-b'
              + 'ased/path-paras/path-para/peer-interface-ip"'+"\n"
              + '11.add container node "configuration/mpls-te/sr-expl-path/name'
              + '-based/path-paras/path-para/sr-path "and choice node "configur'
              + 'ation/mpls-te/sr-expl-path/name-based/path-paras/path-para/sr-'
              + 'path/sr-path-type"'+"\n"
              + '12.add case node "configuration/mpls-te/sr-expl-path/name-base'
              + 'd/path-paras/path-para/sr-path/sr-path-type/node"'+"\n"
              + '13.add leaf node "configuration/mpls-te/sr-expl-path/name-base'
              + 'd/path-paras/path-para/sr-path/sr-path-type/node/node-router-i'
              + 'd"'+"\n"
              + '14.add case node "configuration/mpls-te/sr-expl-path/name-base'
              + 'd/path-paras/path-para/sr-path/sr-path-type/adjacency"'+"\n"
              + '15.add leaf node "configuration/mpls-te/sr-expl-path/name-base'
              + 'd/path-paras/path-para/sr-path/sr-path-type/adjacency/router-i'
              + 'd","configuration/mpls-te/sr-expl-path/name-based/path-paras/p'
              + 'ath-para/sr-path/sr-path-type/adjacency/interface-ip","configu'
              + 'ration/mpls-te/sr-expl-path/name-based/path-paras/path-para/sr'
              + '-path/sr-path-type/adjacency/peer-router-id" and "configuratio'
              + 'n/mpls-te/sr-expl-path/name-based/path-paras/path-para/sr-path'
              + '/sr-path-type/adjacency/peer-interface-ip".'+"\n"
              + '16.add container node "configuration/mpls-te/sr-expl-path/id-b'
              + 'ased/path-paras/path-para/sr-path " and choice node "configura'
              + 'tion/mpls-te/sr-expl-path/id-based/path-paras/path-para/sr-pat'
              + 'h/sr-path-type"'+"\n"
              + '17.add case node "configuration/mpls-te/sr-expl-path/id-based/'
              + 'path-paras/path-para/sr-path/sr-path-type/node"'+"\n"
              + '18.add leaf node "configuration/mpls-te/sr-expl-path/id-based/'
              + 'path-paras/path-para/sr-path/sr-path-type/node/node-router-id"'
              + ''+"\n"
              + '19.add case node "configuration/mpls-te/sr-expl-path/id-based/'
              + 'path-paras/path-para/sr-path/sr-path-type/adjacency"'+"\n"
              + '20.add leaf node "configuration/mpls-te/sr-expl-path/id-based/'
              + 'path-paras/path-para/sr-path/sr-path-type/adjacency/router-id"'
              + ',"configuration/mpls-te/sr-expl-path/id-based/path-paras/path-'
              + 'para/sr-path/sr-path-type/adjacency/interface-ip","configurati'
              + 'on/mpls-te/sr-expl-path/id-based/path-paras/path-para/sr-path/'
              + 'sr-path-type/adjacency/peer-router-id" and "configuration/mpls'
              + '-te/sr-expl-path/id-based/path-paras/path-para/sr-path/sr-path'
              + '-type/adjacency/peer-interface-ip".'
                ;
  }
  revision 2016-07-29 {
    description '1.Add configuration/mpls-te/dynamic-tunnel/tunnels/gtunnel'+"\n"
              + '2.Add configuration/mpls-te/access-tunnel/gtunnel'
                ;
  }
  revision 2016-07-28 {
    description 'Change the range of "configuration/mpls-te/sr-expl-path/name-b'
              + 'ased/path-paras/path-para/index" from 1-5 to 1-255.'+"\n"
              + 'Change the range of "configuration/mpls-te/sr-expl-path/id-bas'
              + 'ed/path-paras/path-para/index" from 1-5 to 1-255.'
                ;
  }
  revision 2016-07-22 {
    description '1.Add configuration/mpls-te/gtunnel-groups'+"\n"
              + '                 2.Add state/mpls-te/gtunnel-groups'
                ;
  }
  revision 2016-06-30 {
    description 'Add configuration/mpls-te/dynamic-tunnel/tunnels/tunnel/segmen'
              + 't-routing'+"\n"
              + 'Add configuration/mpls-te/dynamic-tunnel/tunnels/tunnel/sr-pat'
              + 'h'+"\n"
              + 'Add configuration/mpls-te/sr-expl-path'
                ;
  }
  revision 2016-03-09 {
    description '1.Add configuration/mpls-te/global-config/pce-compute'+"\n"
              + '  Add configuration/mpls-te/global-config/pce-compute/pce-comp'
              + 'ute-enable'
                ;
  }
  revision 2016-02-01 {
    description '1.Obsolete configuration/mpls-te/dynamic-tunnel/tunnels/tunnel'
              + '/pce-init'+"\n"
              + '2.Add configuration/mpls-te/dynamic-tunnel/tunnels/tunnel/pce-'
              + 'initiate'+"\n"
              + '  Add configuration/mpls-te/dynamic-tunnel/tunnels/tunnel/pce-'
              + 'initiate/pce-init-enable'
                ;
  }
  revision 2016-01-06 {
    description '1. Add the leaf of /configuration/mpls-te/authentication/inter'
              + 'face/keychain.'+"\n"
              + '2. Add the leaf of /configuration/mpls-te/authentication/inter'
              + 'face/mode.'
                ;
  }
  revision 2015-12-28 {
    description '1.add configuration/mpls-te/dynamic-tunnel/tunnels/tunnel/pce-'
              + 'control.'+"\n"
              + '2.add configuration/mpls-te/dynamic-tunnel/tunnels/tunnel/pce-'
              + 'control/pce-control-enable.'
                ;
  }
  revision 2015-11-03 {
    description '1.Add bandwidth-utilization leaf to state/mpls-te/dynamic-tunn'
              + 'el/tunnel.'+"\n"
              + '2.Add bandwidth-utilization-in leaf to state/mpls-te/dynamic-t'
              + 'unnel/tunnel.'+"\n"
              + '3.Add bandwidth-utilization leaf to state/mpls-te/static-tunne'
              + 'l/tunnel.'+"\n"
              + '4.Add state/mpls-te/local-acc-dynamic-tnnl container.'+"\n"
              + '5.Modify the range of /configuration/mpls-te/tnnl-rate-limit/t'
              + 'unnel/cir.'+"\n"
              + '6.Add the perf-code of /configuration/mpls-te/tnnl-rate-limit/'
              + 'tunnel/cir.'+"\n"
              + '7.Add the perf-code of /configuration/mpls-te/tnnl-rate-limit/'
              + 'tunnel/cbs.'+"\n"
              + '8.Add the perf-code of /configuration/mpls-te/tnnl-rate-limit/'
              + 'tunnel/pir.'+"\n"
              + '9.Add the perf-code of /configuration/mpls-te/tnnl-rate-limit/'
              + 'tunnel/pbs.'
                ;
  }
  revision 2015-10-21 {
    description '1. Add /configuration/mpls-te/global-config/metric-ability con'
              + 'tainer.'+"\n"
              + '2. Add /configuration/mpls-te/dynamic-tunnel/none-null'+"\n"
              + '3. Modify unit from s to second.'
                ;
  }
  revision 2015-09-11 {
    description '1.Add the leaf of /operation/manual-reopt/tunnel-id and  /oper'
              + 'ation/manual-reopt/all.'
                ;
  }
  revision 2015-08-12 {
    description '1. Remove /configuration/mpls-te/passive-if/cross-domain/nbr-o'
              + 'spf-node-id regular express.'+"\n"
              + '2. Add /configuration/mpls-te/global-config/cspf-preferred-igp'
              + ' container.'+"\n"
              + '3. Add /configuration/mpls-te/bfd/tunnels/active-lsp-bfd list.'
              + ''+"\n"
              + '4. Add /configuration/mpls-te/global-config/next-hop-routing c'
              + 'ontainer.'+"\n"
              + '5. Add /configuration/mpls-te/global-config/best-effort-cspf c'
              + 'ontainer..'+"\n"
              + '6. Add /configuration/mpls-te/dynamic-tunnel/tunnels/tunnel/wi'
              + 'thout-cspf container.'
                ;
  }
  revision 2015-07-10 {
    description '1.Add the leaf of /configuration/mpls-te/auto-route/forwarding'
              + '-adjacency/tunnel/ipv6 and  /configuration/mpls-te/auto-route/'
              + 'short-cut/tunnel/ipv6'+"\n"
              + '    2.Add configuration/mpls-te/dynamic-tunnel/tunnels/tunnel/'
              + 'pce-init.'
                ;
  }
  revision 2015-06-04 {
    description '1.Add eir leaf to mpls-te/ds-te/if-bandwidthes/if-bandwidth.'+"\n"
              + '2.obselete /configuration/mpls-te/affinity/tunnels/tunnel list'
              + '.'+"\n"
              + '3.add /configuration/mpls-te/affinity/tunnels/tunnel-mod list.'
                ;
  }
  revision 2015-06-03 {
    description '1.Modify  /configuration/mpls-te/tnnl-policy-class.'+"\n"
              + '2.Add the enumeration type of /dynamic-tunnel/tunnel/hsb-statu'
              + 's and /state/mpls-te/dynamic-tunnel/tunnel/hsb-status.'
                ;
  }
  revision 2015-05-20 {
    description '1.add /configuration/mpls-te/static-tunnel/tunnel/bandwidth-ut'
              + 'ilization.'
                ;
  }
  revision 2015-04-15 {
    description 'Modify the sequence of /configuration/mpls-te/tnnl-rate-limit '
              + 'and /configuration/mpls-te/static-tunnels.'
                ;
  }
  revision 2015-03-27 {
    description '1.obselete /configuration/mpls-te/dynamic-tunnel/tunnels/tunne'
              + 'l/policy-class'+"\n"
              + '2.obselete /configuration/mpls-te/access-tunnel/tunnel/policy.'
              + ''+"\n"
              + '3.obselete /configuration/mpls-te/static-tunnels/tunnel/policy'
              + '.'+"\n"
              + '4.add /configuration/mpls-te/tnnl-policy-class.'+"\n"
              + '5.modify the minimum-member leaf of /configuration/mpls-te/te-'
              + 'ecmp-groups/te-ecmp-group.'
                ;
  }
  revision 2015-03-16 {
    description '1.add configuration/mpls-te/dynamic-tunnel/tunnels/tunnel/ref_'
              + 'hsb.'
                ;
  }
  revision 2015-03-03 {
    description '1.reset the range of pir in tnnl-rate-limit.'+"\n"
              + '2.reset the range of out-peak and out-excess-burst in positive'
              + '-attribute.'+"\n"
              + '3.reset the range of out-peak,out-burst and out-excess-burst i'
              + 'n reverse-attribute.'
                ;
  }
  revision 2015-02-27 {
    description '1.Modify the key of affinity leaf /configuration/mpls-te/affin'
              + 'ity/tunnels/tunnel.'+"\n"
              + '2.Add the notification of dynamic-tunnel and history-path.'
                ;
  }
  revision 2015-02-10 {
    description '1.Modify the te-ecmp-group list of configuration/mpls-te/te-ec'
              + 'mp-groups.'+"\n"
              + '2.Modify the group-id leaf of configuration/mpls-te/te-ecmp-gr'
              + 'oups/te-ecmp-group. '+"\n"
              + '3.Modify the hop-type leaf of configuration/mpls-te/explicit-p'
              + 'ath\name-based/path-paras/path-para.'+"\n"
              + '4.Modify the hop-attr leaf of configuration/mpls-te/explicit-p'
              + 'ath\name-based/path-paras/path-para.'+"\n"
              + '5.Modify the hop-type leaf of configuration/mpls-te/explicit-p'
              + 'ath/id-based/path-paras/path-para.'+"\n"
              + '6.Modify the hop-attr leaf of configuration/mpls-te/explicit-p'
              + 'ath/id-based/path-paras/path-para.'+"\n"
              + '7.Add speed-blind leaf to mpls-te/ds-te/if-bandwidthes/if-band'
              + 'width.'+"\n"
              + '8.Modify the value /mpls-te/access-tunnel/tunnel/triple/ingres'
              + 's-tunnel-id.'+"\n"
              + '9.Modify the value /mpls-te/static-tunnels/tunnel/triple/ingre'
              + 'ss-tunnel-id.'
                ;
  }
  revision 2015-01-26 {
    description '1. Modify interval of retransmit signalling message leaf /conf'
              + 'iguration/mpls-te/global-config/retran-config/interval.'
                ;
  }
  revision 2015-01-07 {
    description '1.Add flow-statistics leaf to mpls-te/dynamic-tunnel/tunnels/t'
              + 'unnel.'+"\n"
              + '2.Add flow-statistics leaf to mpls-te/access-tunnel/tunnel.'+"\n"
              + '3.Add flow-statistics leaf to mpls-te/static-tunnels/tunnel.'+"\n"
              + '4.Add ultralimit-discard leaf to mpls-te/dynamic-tunnel/tunnel'
              + 's/tunnel.'+"\n"
              + '5.Add ultralimit-discard leaf to mpls-te/access-tunnel/tunnel.'
              + ''+"\n"
              + '6.Add ultralimit-discard leaf to mpls-te/static-tunnels/tunnel'
              + '.'
                ;
  }
  revision 2014-12-18 {
    description 'Modify the minimum-member leaf of configuration/mpls-te/te-ecm'
              + 'p-groups/te-ecmp-group.'
                ;
  }
  revision 2014-11-28 {
    description '1.Add the container of frr-protect.'
                ;
  }
  revision 2014-11-20 {
    description 'Add the e2e-protect container of configuration/mpls-te/dynamic'
              + '-tunnel/tunnels/tunnel.'+"\n"
              + 'Add the minimum-member leaf of configuration/mpls-te/te-ecmp-g'
              + 'roups/te-ecmp-group.'+"\n"
              + 'Add the update-delay leaf of configuration/mpls-te/te-ecmp-gro'
              + 'ups/te-ecmp-group.'
                ;
  }
  revision 2014-11-07 {
    description '1.Add the leaf of state/mpls-te/dynamic-tunnel/tunnel/ingress-'
              + 'id'+"\n"
              + '2.Add the leaf of state/mpls-te/dynamic-tunnel/tunnel/egress-i'
              + 'd.'
                ;
  }
  revision 2014-10-28 {
    description '1. Add enable leaf to mpls-te/gs-config/global.'+"\n"
              + '2. Add enable leaf and name leaf to mpls-te/gs-config/interfac'
              + 'es/interface.'
                ;
  }
  revision 2014-10-16 {
    description '1.Modify the description of state/mpls-te/history-path/hispath'
              + '/lsprole.'
                ;
  }
  revision 2014-10-10 {
    description 'Add the escape-path leaf of configuration/mpls-te/dynamic-tunn'
              + 'el/tunnels/tunnel.'
                ;
  }
  revision 2014-09-19 {
    description '1.Modify the value range of configuration/mpls-te/global-confi'
              + 'g/delay/delay_switch_over'+"\n"
              + '2.Modify the select of state/mpls-te/dynamic-tunnel/tunnel-cho'
              + 'p,tnnl-ar-hop,state/mpls-te/pathoption-addition.'
                ;
  }
  revision 2014-09-13 {
    description '1.Add the container of state/mpls-te/history-path.'
                ;
  }
  revision 2014-08-18 {
    description '1.delete the value range of configuration/mpls-te/dynamic-tunn'
              + 'el/tunnels/tunnel/hot-lsp-frr leaf.'+"\n"
              + '2.add the value range and type of configuration/mpls-te/dynami'
              + 'c-tunnel/tunnels/tunnel/hsblsp-frr leaf, and add its reset val'
              + 'ue.'
                ;
  }
  revision 2014-07-14 {
    description '1.Modify the value range of configuration/mpls-te/explicit-pat'
              + 'h\name-based\name;'+"\n"
              + '2.Modify the value range of configuration/mpls-te/dynamic-tunn'
              + 'el/tunnels/tunnel/path-option-list/explicit-name/explicit-path'
              + '-name;'+"\n"
              + '3.Modify the value range of configuration/mpls-te/hotstandby/t'
              + 'unnel/explicit-name/path-name;'+"\n"
              + '4.Modify the value range of configuration/mpls-te/static-tunne'
              + 'ls/tunnel/track-name;'+"\n"
              + '5.Modify the value range of state/mpls-te/remote-tunnel/tunnel'
              + '/in-interface;'+"\n"
              + '6.Modify the value range of state/mpls-te/remote-tunnel/tunnel'
              + '/out-interface.'
                ;
  }
  revision 2014-06-11 {
    description '1.Modify the value range of configuration/mpls-te/auto-bandwid'
              + 'th/tunnels/tunnel/adjust-enable leaf.'+"\n"
              + '2.Modify the value range and type of configuration/mpls-te/gra'
              + 'ceful-restart/enable leaf, and add its reset value.'
                ;
  }
  revision 2014-05-23 {
    description '1.Add backup-bw leaf to mpls-te/dynamic-tunnel/tunnels/tunnel.'
                ;
  }
  revision 2014-05-16 {
    description '1.modify the mandatory of addr-type and hop-type.'
                ;
  }
  revision 2014-05-08 {
    description '1.add the type of oper-status.'
                ;
  }
  revision 2014-04-02 {
    description 'Add ovreflow container.Move overflow-limit,overflow-percent an'
              + 'd overflow-bandwidth to the ovreflow container.'+"\n"
              + 'Delete the default value and add the reset value of adjust-max'
              + '-value.'
                ;
  }
  revision 2014-03-24 {
    description '1. Move setup-priority and holding priority to priority contai'
              + 'ner.'+"\n"
              + '2. Add default value to ds-te/model/value,access-tunnel/tunnel'
              + '/activation.'+"\n"
              + '3. Add reset value to static-tunnel/tunnel/lsps/positive(rever'
              + 'se)-attribute next-hop share-tunnel pre-hop.'+"\n"
              + '4. Add convergence-ratio container.'+"\n"
              + '5. Add tunnel-bind.'+"\n"
              + '6. Add pathoption list,add egress tunnel,modify dynamic_tunnel'
              + ' list,modify tnnl-ar-hop.'
                ;
  }
  revision 2014-03-07 {
    description '1. Add performCode to ingress-tunnel-id and bfd.'+"\n"
              + '2. Add interface filter number to static tunnel name.'+"\n"
              + '3. Add frr-promotion unit.'+"\n"
              + '4. Add maximum instance number if-bandwidthes.'+"\n"
              + '5. Add maximum instance number of affinity.'+"\n"
              + '6. Modify protect-type Mandatory.'+"\n"
              + '7. Add dynamic case to hotstandby path type.'+"\n"
              + '8. Add default value to policy class.'
                ;
  }
  revision 2014-03-05 {
    description '1.add the range of bandwidth and delete performance of bandwid'
              + 'th in dynamic-tunnel and static-tunnel.'+"\n"
              + '2.add reset value and delete default value of cbs, eir and ebs'
              + ' in dynamic-tunnel.'+"\n"
              + '3.add the range of cir and pir in tnnl-rate-limit.'+"\n"
              + '4.add the reset value of inlabel and outlabel in positive-attr'
              + 'ibute and reverse-attribute.'+"\n"
              + '5.modify the range of ar-relative-metric.'+"\n"
              + '6.modify the description of tunnel list.'+"\n"
              + '7.modify the name of remote tunnel.'+"\n"
              + '8.Add dscp container.'
                ;
  }
  revision 2014-02-18 {
    description '1.remove filter of retran-config.'+"\n"
              + '2.add the invalid value of interval and frequency.'+"\n"
              + '3.add the range of explicit-path id.'+"\n"
              + '4.modify ar-enable wrong value.'
                ;
  }
  revision 2014-02-15 {
    description '1.add sd container.'
                ;
  }
  revision 2014-01-23 {
    description 'Add the activation of dynamic tunnel. Modify the sequence of r'
              + 'ole-type and triple. Modify the  scope of the inlabel and outl'
              + 'abel. Delete the default value and default performance of out-'
              + 'bandwidth leaf.'
                ;
  }
  revision 2014-01-15 {
    description 'Add te-trunk container.'+"\n"
              + 'Move soft-preempt container from mpls-te to dynamic-tunnel.'+"\n"
              + 'Remove resv-style and alias-name container.'+"\n"
              + 'Add filter to router-id and tunnel-destination.'
                ;
  }
  revision 2014-01-08 {
    description 'Add container affinity and frr-promotion.'+"\n"
              + 'Add the filter of invalid address and delete default value.'+"\n"
              + 'Add the UnactiveTime,delay_switch_over,delay_reactive,delay_li'
              + 'nkup,crankback.'
                ;
  }
  revision 2013-12-31 {
    description 'modify te-metric range and add sample-enable reset value.'+"\n"
              + 'modify description of refresh-interval/restart-time/recovery-t'
              + 'ime of graceful-restart function.'+"\n"
              + 'modify description of srlg of interface.'+"\n"
              + 'Add container for auto-bandwidth and ds-te.'+"\n"
              + 'Add filter for policy-class of static-tunnel.'
                ;
  }
  revision 2013-12-26 {
    description 'Add performance and interface filter. Add filter in policy-cla'
              + 'ss of access-tunnel.'
                ;
  }
  revision 2013-12-11 {
    description 'add resv-style,bw-protect,alias-name,soft-preemption,te-ecmp-g'
              + 'roups,limit-hop-num,hop-prior,reopt-hsb-lsp to model.'+"\n"
              + 'modify retran-config/enable configuration value.'
                ;
  }
  revision 2013-12-05 {
    description 'Modify srlg container to add one-to-one, facility, auto-backup'
              + ' and hotstandby type.'
                ;
  }
  revision 2013-11-25 {
    description 'add regular expression to admin-weight tunnel name.'+"\n"
              + 'add reset default value 0 to frr facility and one2one.'
                ;
  }
  revision 2013-11-10 {
    description 'Change the type of model from unit32 to enumeration, the type '
              + 'of percent from unit32 to unit8, the range of tunnel bfd enabl'
              + 'e and policy list of dynamic-tunnel and access-tunnel.'
                ;
  }
  revision 2013-09-24 {
    description 'Add the static tunnel model, see called "static-tunnels" of co'
              + 'ntainer.'
                ;
  }
  revision 2013-09-18 {
    description 'Add filter, change some choice to single container and modify '
              + 'some testing mistakes.'
                ;
  }
  revision 2013-08-01 {
    description 'Initial version.'
                ;
  }
  container configuration {
    description 'The branch of configuration model.'
                ;
    container cac {
      description 'The configuration of CAC.'
                  ;
      leaf cac-enable {
        description 'The global switch of CAC.'
                    ;
        type enumeration {
          enum disabled {
            value 0 ;
          }
          enum enabled {
            value 1 ;
          }
        }
        default enabled ;
      }
      ncd:revise-date 2018-07-14 ;
    }
    container mpls-te {
      description 'The configuration of MPLS TE.'
                  ;
      leaf te-enable {
        description 'The global switch of TE.'
                    ;
        type enumeration {
          enum disabled {
            value 0 ;
          }
          enum enabled {
            value 1 ;
          }
        }
        default disabled ;
      }
      container global-config {
        description 'TE global common configuration. Include refresh configurat'
                  + 'ion, retran and srefresh congiguration, explicit none cong'
                  + 'iguration and resv confirm congiguration.'
                    ;
        presence 'global configuration'
                 ;
        container refresh-config {
          description 'The signalling packet containing path and resv refresh c'
                    + 'onfiguration.'
                      ;
          leaf interval {
            description 'Configuration of time interval for sending refresh mes'
                      + 'sage, range: from 5000 to 65535000,'+"\n"
                      + 'units: ms, default value is 30000 ms.'
                        ;
            type uint32 {
              range 5000..65535000 ;
            }
            units ms ;
            default 30000 ;
          }
          leaf misses {
            description 'Configuration of miss number for refresh message, rang'
                      + 'e: from 2 to 10, default value is 4.'
                        ;
            type uint32 {
              range 2..10 ;
            }
            default 4 ;
          }
        }
        container retran-config {
          description 'The retransmit configuration.'
                      ;
          leaf enable {
            description 'The switch of retransmit. Ref-reduction-enable is depe'
                      + 'nd on retran-config enable.'
                        ;
            type empty ;
          }
          leaf interval {
            description 'The interval of retransmit signalling message, range: '
                      + 'from 500 to 60000, unit: ms, default value: 1000 ms.'
                        ;
            type uint32 {
              range 500..60000 ;
            }
            units ms ;
            default 1000 ;
          }
          leaf limit {
            description 'The limit of signalling message retransmit, range: fro'
                      + 'm 2 to 10, default value: 3.'
                        ;
            type uint32 {
              range 2..10 ;
            }
            default 3 ;
          }
          leaf ref-reduction-enable {
            description 'Enable summary refresh function, default value is disa'
                      + 'bled.'+"\n"
                      + 'Ref-reduction-enable is depend on retran-config enable'
                      + '.'
                        ;
            type enumeration {
              enum disabled {
                value 0 ;
              }
              enum enabled {
                value 1 ;
              }
            }
            default disabled ;
          }
        }
        container explicit-none {
          description 'The egress label management. The default label is implic'
                    + 'it-null.'
                      ;
          leaf explicit-null {
            description 'When this attribute is configured, it indicates that t'
                      + 'he label of egress node is explicit-null.'
                        ;
            type boolean ;
            default false ;
          }
          leaf none-null {
            description 'When this attribute is configured, it indicates that t'
                      + 'he label of egress node is none-null.'
                        ;
            type boolean ;
            default false ;
          }
        }
        container sd-config {
          description 'Configuration of SD.'
                      ;
          leaf enable {
            description 'The switch of sd. default value is disabled.'
                        ;
            type enumeration {
              enum disabled {
                value 0 ;
              }
              enum enabled {
                value 1 ;
              }
            }
            default disabled ;
          }
          leaf interval {
            description 'The interval of sd alarm, range: from 10 to 30, unit: '
                      + 's, default value: 10 s.'
                        ;
            type int16 {
              range 10..30 ;
            }
            units second ;
            default 10 ;
          }
        }
        container resv-confirm {
          description 'The resv confirm.'
                      ;
          leaf enable {
            description 'Enable resv confirm function, default value is disable'
                      + 'd.'+"\n"
                      + 'It is configured on egress.'
                        ;
            type enumeration {
              enum disabled {
                value 0 ;
              }
              enum enabled {
                value 1 ;
              }
            }
            default disabled ;
          }
        }
        container router-id {
          description 'Configuration of router-id.'
                      ;
          leaf route-id {
            description 'The TE route ID configuration. Must config router id b'
                      + 'efore any other configuration under dynamic-tunnl node'
                      + ' and ensure that router id is reachable in route.'
                        ;
            type ncd:ipv4-address {
              pattern '([1-9]|[1-9][0-9]|1[0-9][0-9]|2[0-4][0-9]|25[0-5])(.([0-'
                    + '9]|[1-9][0-9]|1[0-9][0-9]|2[0-4][0-9]|25[0-5])){3}'
                      ;
            }
          }
        }
        container ipv6-router-id {
          leaf ipv6-router-id {
            description 'The TE ipv6 route ID configuration. Must config ipv6 r'
                      + 'outer id before any other configuration about SRv6 tun'
                      + 'nel and ensure that ipv6 router id is reachable in rou'
                      + 'te.'
                        ;
            type ncd:ipv6-address ;
          }
          ncd:revise-date 2018-05-14 ;
        }
        container tnnl-unact-time {
          description 'Tunnel reconstruction interval regularly.'
                      ;
          leaf interval {
            description 'Tunnel reconstruction interval regularly.'
                        ;
            type uint32 {
              range 30..300 ;
            }
            units second ;
          }
        }
        container delay {
          description 'Static TE delay function of management object.'
                      ;
          leaf delay_switch_over {
            description 'Time delay back cut.'
                        ;
            type uint32 {
              range 0..90 ;
            }
            units second ;
            default 0 ;
          }
          leaf delay_reactive {
            description 'Delay reactive time.'
                        ;
            type uint32 {
              range 0..30 ;
            }
            units second ;
            default 10 ;
          }
          leaf reactive-precise {
            description 'Delay reactive precise time.'
                        ;
            type uint8 {
              range 1..9 {
                description 'reactive precise time(100ms)'
                            ;
              }
            }
            units 100ms ;
            ncd:revise-date 2018-01-17 ;
          }
          leaf delay_linkup {
            description 'The linkup of time delay response.'
                        ;
            type uint32 {
              range 0..120 ;
            }
            units second ;
            default 0 ;
          }
          leaf delay-topo-change {
            description 'Topology-change delay time(default:5s)'
                        ;
            type uint32 {
              range 0..30 ;
            }
            units second ;
            default 5 ;
            ncd:revise-date 2017-09-18 ;
          }
        }
        container cspf-preferred-igp {
          presence 'cspf preferred igp'
                   ;
          choice preferred-igp-type {
            case ospf-preferred {
              leaf preferred-igp-ospf {
                description 'Specify OSPF for CSPF routing to use prior.'
                            ;
                type enumeration {
                  enum ospf {
                    value 1 ;
                  }
                }
                mandatory true ;
              }
              container ospf-process {
                choice ospf-process-config {
                  case ospf-process-configed {
                    leaf ospf-process-id {
                      description 'OSPF process ID'
                                  ;
                      type uint32 {
                        range 1..65535 ;
                      }
                      mandatory true ;
                    }
                    container ospf-area {
                      choice ospf-area-config {
                        case ospf-area-configed {
                          leaf ospf-area-id {
                            description 'OSPF area ID'
                                        ;
                            type ncd:ipv4-address ;
                            mandatory true ;
                          }
                        }
                      }
                    }
                  }
                }
              }
            }
            case isis-preferred {
              leaf preferred-igp-isis {
                description 'Specify ISIS for CSPF routing to use prior.'
                            ;
                type enumeration {
                  enum isis {
                    value 2 ;
                  }
                }
                mandatory true ;
              }
              container isis-process {
                choice isis-process-config {
                  case isis-process-configed {
                    leaf isis-process-id {
                      description 'ISIS process ID'
                                  ;
                      type uint32 {
                        range 0..65535 ;
                      }
                      mandatory true ;
                    }
                    container isis-level {
                      choice isis-level-configed {
                        case isis-level1-configed {
                          leaf isis-level-1 {
                            type enumeration {
                              enum level-1 {
                                value 1 ;
                              }
                            }
                            mandatory true ;
                          }
                        }
                        case isis-level2-configed {
                          leaf isis-level-2 {
                            description 'ISIS level-2'
                                        ;
                            type enumeration {
                              enum level-2 {
                                value 2 ;
                              }
                            }
                            mandatory true ;
                          }
                        }
                      }
                    }
                  }
                }
              }
            }
            ncd:revise-date 2018-08-28 ;
          }
          ncd:revise-date 2015-08-12 ;
        }
        container next-hop-routing {
          description 'Build path ERO without CSPF.'
                      ;
          presence 'next hop routing'
                   ;
          leaf without-cspf-enable {
            description 'Build path ERO without CSPF.'
                        ;
            type empty ;
          }
          ncd:revise-date 2015-08-12 ;
        }
        container best-effort-cspf {
          description 'Enable best-effort CSPF requirement,such as without band'
                    + 'width,without affinity.'
                      ;
          presence 'best effort cspf'
                   ;
          leaf without-bw-enable {
            description 'Enable best-effort CSPF without bandwidth requirement.'
                        ;
            type empty ;
          }
          leaf without-affinity-enable {
            description 'Enable best-effort CSPF without affinity requirement.'
                        ;
            type enumeration {
              enum disabled {
                value 0 ;
              }
              enum enabled {
                value 1 ;
              }
            }
            default disabled ;
            ncd:revise-date 2018-02-24 ;
          }
          leaf exclude-overload {
            description 'Config CSPF exclude overload nodes.'
                        ;
            type enumeration {
              enum disabled {
                value 0 ;
              }
              enum enabled {
                value 1 ;
              }
            }
            default disabled ;
            ncd:revise-date 2020-09-22 ;
          }
          ncd:revise-date 2015-08-12 ;
        }
        container metric-ability {
          leaf metric-ability {
            description 'Configure administrative-weight implicit-ability.'
                        ;
            type enumeration {
              enum disabled {
                value 0 ;
              }
              enum enabled {
                value 1 ;
              }
            }
            default enabled ;
          }
          ncd:revise-date 2015-10-21 ;
        }
        container pce-compute {
          leaf pce-compute-enable {
            description 'Enable path of tunnel to be computed by PCE. Default v'
                      + 'alue is disabled.'
                        ;
            type enumeration {
              enum disabled {
                value 0 ;
              }
              enum enabled {
                value 1 ;
              }
            }
            default disabled ;
          }
          ncd:revise-date 2016-03-09 ;
        }
        container bind-sid-allocate {
          leaf bind-sid-allocate {
            description 'When this attribute is configured, allocate bind-sid f'
                      + 'or tunnel.'
                        ;
            type enumeration {
              enum disabled {
                value 0 ;
              }
              enum enabled {
                value 1 ;
              }
            }
            default disabled ;
          }
          ncd:revise-date 2017-08-10 ;
        }
        container signalling-tear {
          description 'Signalling tear.'
                      ;
          leaf trigger-by-bfd {
            description 'Enable signalling of tearing trigerred by BFD down.'
                        ;
            type enumeration {
              enum disabled {
                value 0 ;
              }
              enum enabled {
                value 1 ;
              }
            }
            default disabled ;
          }
          ncd:revise-date 2017-10-19 ;
        }
        container entropy-label {
          description 'Configure entropy label capability.'
                      ;
          leaf entropy-label-capability {
            description 'Configure entropy label capability.The default value i'
                      + 's controlled by the parameters of performance.'
                        ;
            type enumeration {
              enum disabled {
                value 0 ;
              }
              enum enabled {
                value 1 ;
              }
            }
          }
          ncd:revise-date 2018-05-26 ;
        }
        container cspf-tie-breaking {
          leaf tie-breaking-method {
            description 'Specify tie-breaking method for CSPF.'
                        ;
            type enumeration {
              enum least-fill {
                value 1 ;
                description 'Preferred path with largest available BW ratio.'
                            ;
              }
              enum most-fill {
                value 2 ;
                description 'Preferred path with smallest available BW ratio.'
                            ;
              }
              enum disabled {
                value 0 ;
              }
            }
            default disabled ;
          }
          ncd:revise-date 2020-04-13 ;
        }
      }
      container explicit-path {
        description 'Configuration of explicit path.'
                    ;
        presence 'Configuration of explicit-path'
                 ;
        list name-based {
          description 'The explicit path name list.'
                      ;
          min-elements 0 ;
          max-elements 8192 ;
          key name ;
          leaf name {
            description 'The explicit path name.'
                        ;
            type string {
              length 1..64 ;
            }
          }
          container path-paras {
            description 'Every explicit-path contains 32 hops.'
                        ;
            list path-para {
              description 'Explicit path address information.'
                          ;
              max-elements 131072 ;
              key index ;
              leaf index {
                description 'The explicit path index.'
                            ;
                type uint8 {
                  range 1..64 ;
                }
              }
              leaf hop-ip {
                description 'Hop IP.'
                            ;
                type ncd:ipv4-address ;
                mandatory true ;
              }
              leaf hop-if-id {
                description 'The if-id of unnumbered interface'
                            ;
                type ncd:ipv4-address {
                  pattern '([1-9]|[1-9][0-9]|1[0-9][0-9]|2[0-4][0-9]|25[0-5])(.'
                        + '([0-9]|[1-9][0-9]|1[0-9][0-9]|2[0-4][0-9]|25[0-5])){'
                        + '3}'
                          ;
                }
                ncd:revise-date 2016-12-27 ;
              }
              leaf hop-type {
                description 'The hop type.'
                            ;
                type enumeration {
                  enum include {
                    value 1 ;
                  }
                  enum exclude {
                    value 2 ;
                  }
                  enum avoid {
                    value 3 ;
                  }
                }
                mandatory true ;
              }
              leaf hop-attr {
                description 'The hop attribute. If hop type is include route, c'
                          + 'an configure strict route and loose route. If hop '
                          + 'type is exclude route, can configure exclude inter'
                          + 'face and exclude node.'+"\n"
                          + 'If hop type is avoid route, can configure avoid in'
                          + 'terface and avoid node.'
                            ;
                type enumeration {
                  enum strict-route {
                    value 1 ;
                  }
                  enum loose-route {
                    value 2 ;
                  }
                  enum exclude-intf {
                    value 3 ;
                  }
                  enum exclude-node {
                    value 4 ;
                  }
                  enum avoid-intf {
                    value 15 ;
                  }
                  enum avoid-node {
                    value 16 ;
                  }
                }
                mandatory true ;
              }
            }
          }
        }
        list id-based {
          description 'The explicit path ID list.'
                      ;
          min-elements 0 ;
          max-elements 8192 ;
          key id ;
          leaf id {
            description 'The explicit path ID.'
                        ;
            type uint16 {
              range 1..65535 ;
            }
          }
          container path-paras {
            description 'Every explicit-path contains 32 hops.'
                        ;
            list path-para {
              description 'Explicit path address information.'
                          ;
              max-elements 131072 ;
              key index ;
              leaf index {
                description 'Explicit path index.'
                            ;
                type uint8 {
                  range 1..64 ;
                }
              }
              leaf hop-ip {
                description 'Hop IP.'
                            ;
                type ncd:ipv4-address ;
                mandatory true ;
              }
              leaf hop-if-id {
                description 'The if-id of unnumbered interface'
                            ;
                type ncd:ipv4-address {
                  pattern '([1-9]|[1-9][0-9]|1[0-9][0-9]|2[0-4][0-9]|25[0-5])(.'
                        + '([0-9]|[1-9][0-9]|1[0-9][0-9]|2[0-4][0-9]|25[0-5])){'
                        + '3}'
                          ;
                }
                ncd:revise-date 2016-12-27 ;
              }
              leaf hop-type {
                description 'The hop type. Include include route and exclude ro'
                          + 'ute.'
                            ;
                type enumeration {
                  enum include {
                    value 1 ;
                  }
                  enum exclude {
                    value 2 ;
                  }
                  enum avoid {
                    value 3 ;
                  }
                }
                mandatory true ;
              }
              leaf hop-attr {
                description 'The hop attribute. If hop type is include route, c'
                          + 'an configure strict route and loose route. If hop '
                          + 'type is exclude route, can configure exclude inter'
                          + 'face and exclude node.'+"\n"
                          + 'If hop type is avoid route, can configure avoid in'
                          + 'terface and avoid node.'
                            ;
                type enumeration {
                  enum strict-route {
                    value 1 ;
                  }
                  enum loose-route {
                    value 2 ;
                  }
                  enum exclude-intf {
                    value 3 ;
                  }
                  enum exclude-node {
                    value 4 ;
                  }
                  enum avoid-intf {
                    value 15 ;
                  }
                  enum avoid-node {
                    value 16 ;
                  }
                }
                mandatory true ;
              }
            }
          }
        }
      }
      container sr-expl-path {
        status obsolete {
          ncd:revise-date 2017-09-14 ;
        }
        description 'Configuration of sr explicit path.'
                    ;
        presence 'Configuration of sr explicit-path'
                 ;
        list name-based {
          description 'The explicit path name list'
                      ;
          min-elements 0 ;
          max-elements 8192 ;
          key name ;
          leaf name {
            description 'The sr path name.'
                        ;
            type string {
              length 1..64 ;
            }
          }
          container path-paras {
            description 'Every sr explicit-path contains 16 hops.'
                        ;
            list path-para {
              description 'Explicit path address information.'
                          ;
              max-elements 131072 ;
              key index ;
              leaf index {
                description 'The explicit path index.'
                            ;
                type uint8 {
                  range 1..255 ;
                }
              }
              leaf type {
                status obsolete {
                  ncd:revise-date 2016-09-01 ;
                }
                description 'The hop type.'
                            ;
                type enumeration {
                  enum node {
                    value 1 ;
                  }
                  enum adjacency {
                    value 2 ;
                  }
                }
                mandatory true ;
              }
              leaf router-id {
                status obsolete {
                  ncd:revise-date 2016-09-01 ;
                }
                description 'Hop IP.'
                            ;
                type ncd:ipv4-address ;
                mandatory true ;
              }
              leaf interface-ip {
                status obsolete {
                  ncd:revise-date 2016-09-01 ;
                }
                description 'The hop attribute. If hop type is include route, c'
                          + 'an configure strict route and loose route. If hop '
                          + 'type is exclude route, can configure exclude inter'
                          + 'face and exclude node.'+"\n"
                          + 'If hop type is avoid route, can configure avoid in'
                          + 'terface and avoid node.'
                            ;
                type ncd:ipv4-address ;
                default 0.0.0.0 ;
              }
              leaf peer-router-id {
                status obsolete {
                  ncd:revise-date 2016-09-01 ;
                }
                description 'Hop IP.'
                            ;
                type ncd:ipv4-address ;
                default 0.0.0.0 ;
              }
              leaf peer-interface-ip {
                status obsolete {
                  ncd:revise-date 2016-09-01 ;
                }
                description 'The hop attribute. If hop type is include route, c'
                          + 'an configure strict route and loose route. If hop '
                          + 'type is exclude route, can configure exclude inter'
                          + 'face and exclude node.'+"\n"
                          + 'If hop type is avoid route, can configure avoid in'
                          + 'terface and avoid node.'
                            ;
                type ncd:ipv4-address ;
                default 0.0.0.0 ;
              }
              container sr-path {
                choice sr-path-type {
                  description 'SR path type.'
                              ;
                  mandatory true ;
                  case node {
                    description 'node type'
                                ;
                    leaf node-router-id {
                      description 'The router id of node.'
                                  ;
                      type ncd:ipv4-address ;
                      mandatory true ;
                    }
                  }
                  case adjacency {
                    description 'adjacency type.'
                                ;
                    leaf router-id {
                      description 'The router id of local node.'
                                  ;
                      type ncd:ipv4-address ;
                      mandatory true ;
                    }
                    leaf interface-ip {
                      description 'The interface ip of local node.'
                                  ;
                      type ncd:ipv4-address ;
                      mandatory true ;
                    }
                    leaf peer-router-id {
                      description 'The router id of peer node.'
                                  ;
                      type ncd:ipv4-address ;
                      mandatory true ;
                    }
                    leaf peer-interface-ip {
                      description 'The interface ip of peer node.'
                                  ;
                      type ncd:ipv4-address ;
                      mandatory true ;
                    }
                  }
                }
                ncd:revise-date 2016-09-01 ;
              }
            }
          }
        }
        list id-based {
          description 'The explicit path ID list.'
                      ;
          min-elements 0 ;
          max-elements 8192 ;
          key id ;
          leaf id {
            description 'The explicit path ID.'
                        ;
            type uint16 {
              range 1..65535 ;
            }
          }
          container path-paras {
            description 'Every explicit-path contains 16 hops.'
                        ;
            list path-para {
              description 'Explicit path address information.'
                          ;
              max-elements 131072 ;
              key index ;
              leaf index {
                description 'Explicit path index.'
                            ;
                type uint8 {
                  range 1..255 ;
                }
              }
              leaf type {
                status obsolete {
                  ncd:revise-date 2016-09-01 ;
                }
                description 'The hop type. Include include route and exclude ro'
                          + 'ute.'
                            ;
                type enumeration {
                  enum node {
                    value 1 ;
                  }
                  enum adjacency {
                    value 2 ;
                  }
                }
                mandatory true ;
              }
              leaf router-id {
                status obsolete {
                  ncd:revise-date 2016-09-01 ;
                }
                description 'Hop IP.'
                            ;
                type ncd:ipv4-address ;
                mandatory true ;
              }
              leaf interface-ip {
                status obsolete {
                  ncd:revise-date 2016-09-01 ;
                }
                description 'The hop attribute. If hop type is include route, c'
                          + 'an configure strict route and loose route. If hop '
                          + 'type is exclude route, can configure exclude inter'
                          + 'face and exclude node.'+"\n"
                          + 'If hop type is avoid route, can configure avoid in'
                          + 'terface and avoid node.'
                            ;
                type ncd:ipv4-address ;
                default 0.0.0.0 ;
              }
              leaf peer-router-id {
                status obsolete {
                  ncd:revise-date 2016-09-01 ;
                }
                description 'The hop attribute. If hop type is include route, c'
                          + 'an configure strict route and loose route. If hop '
                          + 'type is exclude route, can configure exclude inter'
                          + 'face and exclude node.'+"\n"
                          + 'If hop type is avoid route, can configure avoid in'
                          + 'terface and avoid node.'
                            ;
                type ncd:ipv4-address ;
                default 0.0.0.0 ;
              }
              leaf peer-interface-ip {
                status obsolete {
                  ncd:revise-date 2016-09-01 ;
                }
                description 'The hop attribute. If hop type is include route, c'
                          + 'an configure strict route and loose route. If hop '
                          + 'type is exclude route, can configure exclude inter'
                          + 'face and exclude node.'+"\n"
                          + 'If hop type is avoid route, can configure avoid in'
                          + 'terface and avoid node.'
                            ;
                type ncd:ipv4-address ;
                default 0.0.0.0 ;
              }
              container sr-path {
                description 'SR path'
                            ;
                choice sr-path-type {
                  description 'SR path type.'
                              ;
                  mandatory true ;
                  case node {
                    description 'node type.'
                                ;
                    leaf node-router-id {
                      description 'The router id of node.'
                                  ;
                      type ncd:ipv4-address ;
                      mandatory true ;
                    }
                  }
                  case adjacency {
                    description 'adjacency type.'
                                ;
                    leaf router-id {
                      description 'The router id of local node.'
                                  ;
                      type ncd:ipv4-address ;
                      mandatory true ;
                    }
                    leaf interface-ip {
                      description 'The interface ip of local node.'
                                  ;
                      type ncd:ipv4-address ;
                      mandatory true ;
                    }
                    leaf peer-router-id {
                      description 'The router id of peer node.'
                                  ;
                      type ncd:ipv4-address ;
                      mandatory true ;
                    }
                    leaf peer-interface-ip {
                      description 'The interface ip of peer node.'
                                  ;
                      type ncd:ipv4-address ;
                      mandatory true ;
                    }
                  }
                }
                ncd:revise-date 2016-09-01 ;
              }
            }
          }
        }
        ncd:revise-date 2016-06-30 ;
      }
      container te-interfaces {
        description 'Enable interface to join in TE.All of the interface config'
                  + 'uration depend on TE interface.'
                    ;
        presence 'configuration of te-interface'
                 ;
        list interface {
          description 'TE interface list.'
                      ;
          max-elements 255 ;
          key name ;
          leaf name {
            description 'Interface name.'
                        ;
            type ncd:ifname ;
          }
          leaf dscp {
            description 'DSCP value of TE interface, range: 0-63.'
                        ;
            type uint8 {
              range 0..63 ;
            }
          }
          container convergence-ratio {
            description 'Interface convergence ratio.'
                        ;
            leaf convergence-ratio-value {
              description 'Interface convergence ratio value.'
                          ;
              type uint8 {
                range 1..100 ;
              }
              default 100 ;
            }
          }
          container hard-pipe {
            description 'Interface hard pipe.'
                        ;
            presence 'Configure hard pipe.'
                     ;
            leaf mode {
              description 'Interface hard pipe mode.'
                          ;
              type enumeration {
                enum share-mode {
                  value 1 ;
                }
                enum exclusive-mode {
                  value 2 ;
                }
              }
              mandatory true ;
            }
            leaf bandwidth {
              description 'Interface hard pipe bandwidth.'
                          ;
              type uint32 {
                range 1..4294967295 ;
              }
              units kbps ;
              mandatory true ;
            }
            ncd:revise-date 2016-12-09 ;
          }
          container second-frr {
            description 'Configure of second frr'
                        ;
            presence 'Configure second fast reroute.'
                     ;
            leaf enable {
              description 'Configure of second frr'
                          ;
              type empty ;
              mandatory true ;
            }
            ncd:revise-date 2019-06-13 ;
          }
        }
      }
      container dynamic-tunnel {
        description 'The dynamic tunnel.'
                    ;
        presence 'configurationg of dynamic-tunnel'
                 ;
        container reoptimize {
          description 'The global configuration of reoptimization.'
                      ;
          presence 'Enable TECP reoptimize frequency.'
                   ;
          leaf frequency {
            description 'The tunnels reoptimize timer frequency in global mode.'
                      + ' Configure tnnl-reoptimize enable node to specify whic'
                      + 'h tunnel uses reoptimize function.'
                        ;
            type int32 {
              range 30..604800 ;
            }
            units second ;
          }
          leaf event {
            description 'Specify which event can triger reoptimize.'
                        ;
            type uint8 {
              range 0..1 {
                description 'linkup(1), none(0).'
                            ;
              }
            }
            default 0 ;
          }
          leaf loose-node-enable {
            description 'Configuration of loose node reoptimize.'
                        ;
            type enumeration {
              enum disabled {
                value 0 ;
              }
              enum enabled {
                value 1 ;
              }
            }
            default disabled ;
          }
        }
        container crankback {
          description 'Set the crankback retry count limit and information life'
                    + ' cycle.'
                      ;
          leaf limit_count {
            description 'Set the crankback retry count limit.'
                        ;
            type uint8 {
              range 1..10 ;
            }
            default 5 ;
          }
          leaf ttl_value {
            description 'Set the crankback information life cycle.'
                        ;
            type uint16 {
              range 30..300 ;
            }
            default 60 ;
          }
        }
        container tunnels {
          description 'Dynamic Tunnel Configuration.'
                      ;
          list gtunnel {
            description 'The gmpls tunnel configuration list.'
                        ;
            max-elements 131070 ;
            key name ;
            leaf name {
              description 'The gmpls tunnel name.'
                          ;
              type string {
                length 11..31 ;
                pattern 'te_gtunnel[0-9]{1,22}'
                        ;
              }
            }
            leaf destination {
              description 'The gmpls tunnel destination.'
                          ;
              type ncd:ipv4-address {
                pattern '([1-9]|[1-9][0-9]|1[0-9][0-9]|2[0-4][0-9]|25[0-5])(.(['
                      + '0-9]|[1-9][0-9]|1[0-9][0-9]|2[0-4][0-9]|25[0-5])){3}'
                        ;
              }
            }
            leaf alias-name {
              description 'Configuration of gmpls tunnel alias name.'
                          ;
              type string {
                length 1..63 ;
              }
            }
            list path-option-list {
              description 'Gtunnel path option configuration.'
                          ;
              max-elements 786420 ;
              key number ;
              leaf number {
                description 'Path option number which the specified gtunnel is '
                          + 'used.'
                            ;
                type uint8 {
                  range 1..16 ;
                }
              }
              choice path-class {
                description 'Path Selection Type.'
                            ;
                mandatory true ;
                case dynamic {
                  description 'Dynamic Path Selection.'
                              ;
                  leaf dynamic {
                    description 'The path type is dynamic.'
                                ;
                    type empty ;
                    mandatory true ;
                  }
                  ncd:revise-date 2020-02-14 ;
                }
                case explicit-name {
                  description 'Based on the name of the explicit path selection.'
                              ;
                  leaf explicit-path-name {
                    description 'The related explicit path name.'
                                ;
                    type string {
                      length 1..64 ;
                    }
                    mandatory true ;
                  }
                }
                case expilict-id {
                  description 'Id-based explicit path selection.'
                              ;
                  leaf explicit-path-id {
                    description 'The related explicit path ID.'
                                ;
                    type uint16 {
                      range 1..65535 ;
                    }
                    mandatory true ;
                  }
                }
              }
              ncd:revise-date 2016-12-27 ;
            }
            container pce-initiate {
              description 'The pce initiate function of dynamic gmpls tunnel.'
                          ;
              leaf pce-init-enable {
                description 'Enable PCE init of gmpls tunnel.'
                            ;
                type enumeration {
                  enum disabled {
                    value 0 ;
                  }
                  enum enabled {
                    value 1 ;
                  }
                }
                default disabled ;
              }
            }
            container bandwidth {
              description 'The gtunnel bandwidth.'
                          ;
              presence 'Gtunnel bandwidth allocation.'
                       ;
              leaf bandwidth {
                description 'The gtunnel bandwidth configuration.'
                            ;
                type uint32 {
                  range 1..4294967295 {
                    description 'The minimum value may be greater than 1, and t'
                              + 'he maximum value may be less than 4294967295, '
                              + 'depending on the system.'
                                ;
                  }
                }
                units kbps ;
                mandatory true ;
              }
              leaf cbs {
                description 'The gtunnel CBS.'
                            ;
                type uint32 {
                  range 1..4294967295 {
                    description 'The minimum value may be greater than 1, and t'
                              + 'he maximum value may be less than 4294967295, '
                              + 'depending on the system.'
                                ;
                  }
                }
                units byte ;
              }
              leaf eir {
                description 'The gtunnel EIR.'
                            ;
                type uint32 {
                  range 1..4294967295 {
                    description 'The minimum value may be greater than 1, and t'
                              + 'he maximum value may be less than 4294967295, '
                              + 'depending on the system.'
                                ;
                  }
                }
                units kbps ;
              }
              leaf ebs {
                description 'The gtunnel EBS.'
                            ;
                type uint32 {
                  range 1..4294967295 {
                    description 'The minimum value may be greater than 1, and t'
                              + 'he maximum value may be less than 4294967295, '
                              + 'depending on the system.'
                                ;
                  }
                }
                units byte ;
              }
              ncd:revise-date 2016-12-27 ;
            }
            container rros {
              description 'The RRO function of gtunnel.'
                          ;
              leaf rro-enable {
                description 'If this object is true, then it enables the Record'
                          + 'Route.'
                            ;
                type enumeration {
                  enum disabled {
                    value 0 ;
                  }
                  enum enabled {
                    value 1 ;
                  }
                }
                default disabled ;
              }
              ncd:revise-date 2016-12-27 ;
            }
            container encoding-type {
              description 'Gtunnel encoding-type configuration.'
                          ;
              choice type {
                description 'type selection.'
                            ;
                case ethernet {
                  description 'Ethernet encoding-type selection.'
                              ;
                  leaf ethernet {
                    description 'Enable ethernet encoding-type.'
                                ;
                    type empty ;
                  }
                }
                case line {
                  description 'Line encoding-type selection.'
                              ;
                  leaf line {
                    description 'Enable line encoding-type.'
                                ;
                    type empty ;
                  }
                }
              }
              ncd:revise-date 2016-12-27 ;
            }
            container seg-protect-type {
              description 'Gtunnel segment-protection-type configuration.'
                          ;
              choice type {
                description 'Gtunnel segment-protection-type.'
                            ;
                case sbr {
                  description 'Sbr segment-protection-type selection.'
                              ;
                  leaf sbr {
                    description 'Enable sbr segment-protection-type.'
                                ;
                    type empty ;
                  }
                }
                case sncp {
                  description 'Sncp segment-protection-type selection.'
                              ;
                  leaf sncp {
                    description 'Enable sncp segment-protection-type.'
                                ;
                    type empty ;
                  }
                }
              }
              ncd:revise-date 2016-12-27 ;
            }
            container switching-type {
              description 'Gtunnel switching-type configuration.'
                          ;
              choice type {
                description 'Gtunnel switching-type.'
                            ;
                case evpl {
                  description 'Evpl switching-type selection.'
                              ;
                  leaf evpl {
                    description 'Enable evpl switching-type.'
                                ;
                    type empty ;
                  }
                }
                case dcsc {
                  description 'Dcsc switching-type selection.'
                              ;
                  leaf dcsc {
                    description 'Enable dcsc switching-type.'
                                ;
                    type empty ;
                  }
                }
              }
              ncd:revise-date 2016-12-27 ;
            }
            container g-pid {
              description 'Gtunnel g-pid configuration.'
                          ;
              choice type {
                description 'Gtunnel g-pid type.'
                            ;
                case eth-phy {
                  description 'eth_phy g-pid type selection.'
                              ;
                  leaf eth-phy {
                    description 'Enable eth_phy g-pid.'
                                ;
                    type empty ;
                  }
                }
              }
              ncd:revise-date 2016-12-27 ;
            }
            ncd:revise-date 2016-07-29 ;
          }
          list tunnel {
            description 'The dynamic tunnel configuration list.'
                        ;
            max-elements 131070 ;
            key name ;
            leaf name {
              description 'The tunnel name.'
                          ;
              type string {
                length 10..31 ;
                pattern 'te_tunnel[0-9]{1,22}'
                        ;
              }
            }
            leaf destination {
              description 'The tunnel destination.'
                          ;
              type ncd:ipv4-address {
                pattern '([1-9]|[1-9][0-9]|1[0-9][0-9]|2[0-4][0-9]|25[0-5])(.(['
                      + '0-9]|[1-9][0-9]|1[0-9][0-9]|2[0-4][0-9]|25[0-5])){3}'
                        ;
              }
            }
            leaf reoptimize {
              description 'Specify MPLS tunnel whether to open the timing re-op'
                        + 'timization.'
                          ;
              type enumeration {
                enum disabled {
                  value 0 ;
                }
                enum enabled {
                  value 1 ;
                }
              }
              default disabled ;
            }
            leaf limit-hop-num {
              description 'The maximum value of hops.'
                          ;
              type uint8 {
                range 0..32 ;
              }
              default 0 ;
            }
            leaf hop-prior {
              description 'Enable the minimum hop priority function of a tunnel.'
                          ;
              type enumeration {
                enum enabled {
                  value 1 ;
                }
                enum disabled {
                  value 2 ;
                }
              }
              default disabled ;
            }
            leaf reopt-hsb-lsp {
              description 'Enable hsb-lsp auto-reoptimize.'
                          ;
              type enumeration {
                enum disabled {
                  value 0 ;
                }
                enum enabled {
                  value 1 ;
                }
              }
              default disabled ;
            }
            leaf activation {
              description 'The activation of dynamic tunnel enable.'
                          ;
              type enumeration {
                enum disabled {
                  value 0 ;
                }
                enum enabled {
                  value 1 ;
                }
              }
              default enabled ;
            }
            leaf crankback {
              description 'Tunnel crankback features enabled.'
                          ;
              type enumeration {
                enum disabled {
                  value 0 ;
                }
                enum end-to-end {
                  value 1 ;
                }
              }
              default disabled ;
            }
            leaf resv-style {
              description 'Configure resv-style in tunnel mode.'+"\n"
                        + 'You must noticed that ff style is confilct to frr co'
                        + 'nfiguration.If frr has been configured first in tunn'
                        + 'el mode,ff style can not be configured.If ff style h'
                        + 'as been configured,frr can not be configured.'
                          ;
              type enumeration {
                enum se {
                  value 1 ;
                  description 'se(Shared Explicit).'
                              ;
                }
                enum ff {
                  value 2 ;
                  description 'ff(Fixed Filter).'
                              ;
                }
              }
              default se ;
            }
            leaf alias-name {
              description 'Configuration of tunnel alias name.'
                          ;
              type string {
                length 1..63 ;
              }
            }
            leaf track-name {
              description 'Configuration of tunnel track name,use for BFD detec'
                        + 'tion.'
                          ;
              type string {
                length 1..31 ;
              }
            }
            leaf soft-preemption-enable {
              description 'Enable soft-preemption in tunnel mode,and this tunne'
                        + 'l will be teared after the specifc time named timeou'
                        + 't configured under timeout container.'
                          ;
              type enumeration {
                enum disabled {
                  value 0 ;
                }
                enum enabled {
                  value 1 ;
                }
              }
              default disabled ;
            }
            leaf escape-path {
              description 'Enable the escape path function of a tunnel.'
                          ;
              type enumeration {
                enum disabled {
                  value 0 ;
                }
                enum enabled {
                  value 1 ;
                }
              }
              default disabled ;
            }
            leaf ultralimit-discard {
              description 'Tunnel ultralimit outbound discard enabled.'
                          ;
              type enumeration {
                enum disabled {
                  value 1 ;
                }
                enum enabled {
                  value 2 ;
                }
              }
              default disabled ;
            }
            leaf flow-statistics {
              description 'The switch of dynamic tunnel flow statistics.'
                          ;
              type enumeration {
                enum disabled {
                  value 0 ;
                }
                enum enabled {
                  value 1 ;
                }
              }
              default disabled ;
            }
            leaf ref_hsb {
              description 'Enable backup path of a tunnel.'
                          ;
              type enumeration {
                enum disabled {
                  value 0 ;
                }
                enum enabled {
                  value 1 ;
                }
              }
              default disabled ;
            }
            leaf pce-init {
              status obsolete {
                ncd:revise-date 2016-02-01 ;
              }
              description 'Enable PCE init of a tunnel.'
                          ;
              type enumeration {
                enum disabled {
                  value 0 ;
                }
                enum enabled {
                  value 1 ;
                }
              }
              default disabled ;
              ncd:revise-date 2015-07-10 ;
            }
            list path-option-list {
              description 'Tunnel path option configuration.'
                          ;
              max-elements 786420 ;
              key number ;
              leaf number {
                description 'Path option number which the specified tunnel is u'
                          + 'sed.'
                            ;
                type uint8 {
                  range 1..16 ;
                }
              }
              choice path-class {
                description 'Path Selection Type.'
                            ;
                mandatory true ;
                case dynamic {
                  description 'Dynamic Path Selection.'
                              ;
                  leaf dynamic {
                    description 'The path type is dynamic.'
                                ;
                    type empty ;
                    mandatory true ;
                  }
                }
                case explicit-name {
                  description 'Based on the name of the explicit path selection.'
                              ;
                  leaf explicit-path-name {
                    description 'The related explicit path name.'
                                ;
                    type string {
                      length 1..64 ;
                    }
                    mandatory true ;
                  }
                }
                case expilict-id {
                  description 'Id-based explicit path selection.'
                              ;
                  leaf explicit-path-id {
                    description 'The related explicit path ID.'
                                ;
                    type uint16 {
                      range 1..65535 ;
                    }
                    mandatory true ;
                  }
                }
              }
              leaf lockdown {
                description 'Lockdown switch is turned on.'
                            ;
                type boolean ;
                default false ;
              }
            }
            container binary-tunnel {
              description 'Bidirectional Tunnel Setting.'
                          ;
              leaf co-route {
                description 'The binary tunnel enable or disable.'
                            ;
                type enumeration {
                  enum disabled {
                    value 0 ;
                  }
                  enum enabled {
                    value 1 ;
                  }
                }
                default disabled ;
              }
            }
            container policy-class {
              status obsolete {
                ncd:revise-date 2015-06-03 ;
              }
              description 'The tunnel policy class.'
                          ;
              leaf class {
                description 'The tunnel policy class configuration. From 0 to 7'
                          + ' represent normal configuration. Ingress and Egres'
                          + 's of co-tunnel uses 255 as its default value.'
                            ;
                type uint8 {
                  range '0..7 | 255'
                        {
                    description '0-7 represent normal configuration. Ingress an'
                              + 'd Egress of co-tunnel uses 255 as its default '
                              + 'value.'
                                ;
                  }
                }
                default 255 ;
              }
            }
            container bandwidth {
              description 'The tunnel bandwidth.'
                          ;
              presence 'Tunnel bandwidth allocation.'
                       ;
              leaf bandwidth {
                description 'The tunnel bandwidth configuration.'
                            ;
                type uint32 {
                  range 0..4294967295 ;
                }
                units kbps ;
                mandatory true ;
              }
              leaf cbs {
                description 'The tunnel CBS.'
                            ;
                type uint32 {
                  range 1..4294967295 ;
                }
                units byte ;
              }
              leaf eir {
                description 'The tunnel EIR.'
                            ;
                type uint32 {
                  range 1..4294967295 ;
                }
                units kbps ;
              }
              leaf ebs {
                description 'The tunnel EBS.'
                            ;
                type uint32 {
                  range 1..4294967295 ;
                }
                units byte ;
              }
            }
            container ct-bandwidths {
              description 'Tunnel classtype and its request bandwidth. It is ex'
                        + 'clusive with common bandwidth and tunnel-rate-limit.'
                          ;
              list ct-bandwidth {
                description 'Tunnel classtype and its request bandwidth.'
                            ;
                key class-type ;
                leaf class-type {
                  description 'The configuration of class type.'
                              ;
                  type uint8 {
                    range 0..7 ;
                  }
                }
                leaf bandwidth {
                  description 'The bandwidth of class type.'
                              ;
                  type uint32 {
                    range 1..4294967295 ;
                  }
                  mandatory true ;
                }
              }
            }
            container rros {
              description 'The RRO function of dynamic tunnel.'
                          ;
              leaf rro-enable {
                description 'If this object is true, then it enables the Record'
                          + 'Route. Before to configure FRR or hotstandby, plea'
                          + 'se ensure that this leaf node is enabled.'
                            ;
                type enumeration {
                  enum disabled {
                    value 0 ;
                  }
                  enum enabled {
                    value 1 ;
                  }
                }
                default disabled ;
              }
            }
            container priority {
              description 'Configuration of tunnel priority.'
                          ;
              presence 'priority of this tunnel'
                       ;
              leaf setup-priority {
                description "The tunnel setup priority.This attribute can't be "
                          + "higher than the holding-priority.0 is the highest "
                          + "priority and 7 is the lowest priority."
                            ;
                type uint16 {
                  range 0..7 ;
                }
                mandatory true ;
              }
              leaf holding-priority {
                description 'The tunnel holding priority.The tunnel of lower ho'
                          + 'lding-priority will be preempted by the tunnel of '
                          + 'higher setup-priority.0 is the highest priority an'
                          + 'd 7 is the lowest priority.'
                            ;
                type uint16 {
                  range 0..7 ;
                }
                mandatory true ;
              }
            }
            container tunnel-bind {
              description 'The associated dynamic tunnel bind function.'
                          ;
              presence 'Configure bound tunnel.'
                       ;
              leaf associated-tunnel-id {
                description 'The associated tunnel id which is the tunnel id of'
                          + ' access tunnel. This function can only be configur'
                          + 'ed at ingress node.This attribute is determined by'
                          + ' product.'
                            ;
                type uint32 {
                  range 1..131072 ;
                }
                mandatory true ;
              }
            }
            leaf backup-bw {
              description 'The backup tunnel bandwidth configuration.'
                          ;
              type uint32 {
                range 1..4294967295 ;
              }
              units kbps ;
            }
            container hsblsp-frr {
              status deprecated ;
              description 'To indicate that hotstandby lsp whether enable FRR o'
                        + 'r not.'
                          ;
              leaf hsblsp-frr {
                status deprecated ;
                description 'To indicate that hotstandby lsp whether enable FRR'
                          + ' or not.'
                            ;
                type enumeration {
                  enum disabled {
                    value 0 ;
                  }
                  enum enabled {
                    value 1 ;
                  }
                }
                default disabled ;
              }
            }
            container mainlsp-frr {
              description 'Configuration-set about main LSP FRR'
                          ;
              leaf block {
                description 'To indicate that main lsp whether block FRR or not.'
                            ;
                type enumeration {
                  enum disabled {
                    value 0 ;
                  }
                  enum enabled {
                    value 1 ;
                  }
                }
                default disabled ;
              }
              ncd:revise-date 2018-09-29 ;
            }
            container e2e-protect {
              description 'Tunnel E2E-protect configuration.'
                          ;
              presence e2e-protect ;
              leaf e2e {
                description 'Enable the E2E-protect of a tunnel.'
                            ;
                type enumeration {
                  enum disabled {
                    value 0 ;
                  }
                  enum enabled {
                    value 1 ;
                  }
                }
                mandatory true ;
              }
            }
            container without-cspf {
              description 'Build path ERO without CSPF.'
                          ;
              presence 'without cspf'
                       ;
              leaf enable {
                description 'Build path ERO without CSPF.'
                            ;
                type empty ;
              }
              ncd:revise-date 2015-08-12 ;
            }
            container pce-control {
              status deprecated ;
              description 'The pce control function of dynamic tunnel.'
                          ;
              presence 'pce control of dynamic tunnel'
                       ;
              leaf pce-control-enable {
                status deprecated ;
                description 'Enable PCE control of a tunnel.'
                            ;
                type enumeration {
                  enum disabled {
                    value 0 ;
                  }
                  enum enabled {
                    value 1 ;
                  }
                }
                default disabled ;
              }
              choice control-address {
                status deprecated ;
                description 'Control address.'
                            ;
                case ipv4 {
                  status deprecated ;
                  description 'Configration ipv4 type of the pce-control.'
                              ;
                  leaf pce-control-addr {
                    status deprecated ;
                    description 'Pce control address.'
                                ;
                    type ncd:ipv4-address {
                      pattern '([1-9]|[1-9][0-9]|1[0-9][0-9]|2[0-4][0-9]|25[0-5'
                            + '])(.([0-9]|[1-9][0-9]|1[0-9][0-9]|2[0-4][0-9]|25'
                            + '[0-5])){3}'
                              ;
                    }
                  }
                  ncd:revise-date 2018-08-29 ;
                }
                case ipv6 {
                  status deprecated ;
                  description 'Configration ipv4 type of the pce-control.'
                              ;
                  leaf pce-control-ipv6-addr {
                    status deprecated ;
                    description 'Pce control ipv6 address.'
                                ;
                    type ncd:ipv6-address ;
                  }
                  ncd:revise-date 2019-09-11 ;
                }
                ncd:revise-date 2018-08-29 ;
              }
              ncd:revise-date 2015-12-28 ;
            }
            container pce-initiate {
              status deprecated ;
              description 'The pce initiate function of dynamic tunnel.'
                          ;
              presence 'pce initiate of dynamic tunnel'
                       ;
              leaf pce-init-enable {
                status deprecated ;
                description 'Enable PCE init of a tunnel.'
                            ;
                type enumeration {
                  enum disabled {
                    value 0 ;
                  }
                  enum enabled {
                    value 1 ;
                  }
                }
                default disabled ;
              }
              ncd:revise-date 2016-02-01 ;
            }
            container pce {
              description 'configuration of pce.'
                          ;
              container slave-name {
                description 'Configuration of tunnel slave name.'
                            ;
                leaf slave-name {
                  description 'Configuration of tunnel slave name.'
                              ;
                  type string {
                    length 1..63 ;
                  }
                }
                ncd:revise-date 2020-10-20 ;
              }
              choice pce-type {
                description 'Pce Selection Type.'
                            ;
                case pce-control {
                  description 'The pce control function of dynamic tunnel.'
                              ;
                  container pce-control {
                    description 'The pce control function of dynamic tunnel.'
                                ;
                    presence 'pce control of dynamic tunnel'
                             ;
                    leaf pce-control-enable {
                      description 'Enable PCE control of a tunnel.'
                                  ;
                      type empty ;
                    }
                    choice control-address {
                      description 'Control address.'
                                  ;
                      case ipv4 {
                        description 'Configration ipv4 type of the pce-control.'
                                    ;
                        leaf pce-control-addr {
                          description 'Pce control address.'
                                      ;
                          type ncd:ipv4-address {
                            pattern '([1-9]|[1-9][0-9]|1[0-9][0-9]|2[0-4][0-9]|'
                                  + '25[0-5])(.([0-9]|[1-9][0-9]|1[0-9][0-9]|2['
                                  + '0-4][0-9]|25[0-5])){3}'
                                    ;
                          }
                        }
                      }
                      case ipv6 {
                        description 'Configration ipv4 type of the pce-control.'
                                    ;
                        leaf pce-control-ipv6-addr {
                          description 'Pce control ipv6 address.'
                                      ;
                          type ncd:ipv6-address ;
                        }
                      }
                    }
                  }
                }
                case pce-initiate {
                  description 'The pce initiate function of dynamic tunnel.'
                              ;
                  container pce-init {
                    description 'The pce initiate function of dynamic tunnel.'
                                ;
                    leaf pce-init-enable {
                      description 'Enable PCE init of a tunnel.'
                                  ;
                      type empty ;
                    }
                  }
                }
              }
              ncd:revise-date 2020-02-14 ;
            }
            leaf segment-routing {
              status obsolete {
                ncd:revise-date 2017-09-14 ;
              }
              description 'Enable segment routing of a tunnel.'
                          ;
              type enumeration {
                enum disabled {
                  value 0 ;
                }
                enum enabled {
                  value 1 ;
                }
              }
              default disabled ;
              ncd:revise-date 2016-06-30 ;
            }
            list sr-path {
              status obsolete {
                ncd:revise-date 2017-09-14 ;
              }
              description 'Tunnel sr path configuration.'
                          ;
              max-elements 786420 ;
              key role ;
              leaf role {
                description 'sr path role.'
                            ;
                type enumeration {
                  enum master {
                    value 1 ;
                  }
                  enum slave {
                    value 2 ;
                  }
                }
              }
              choice sr-path-type {
                description 'Path Selection Type.'
                            ;
                mandatory true ;
                case srpath-name {
                  description 'Based on the name of the sr path selection.'
                              ;
                  leaf name {
                    description 'The sr path name.'
                                ;
                    type string {
                      length 1..64 ;
                    }
                    mandatory true ;
                  }
                }
                case srpath-id {
                  description 'Based on the id of the sr path selection.'
                              ;
                  leaf id {
                    description 'The sr path ID.'
                                ;
                    type uint16 {
                      range 1..65535 ;
                    }
                    mandatory true ;
                  }
                }
              }
              ncd:revise-date 2016-06-30 ;
            }
            container ref-affinity {
              description 'FRR backup tunnel reference main path affinity confi'
                        + 'guration.'
                          ;
              leaf ref-main-affinity {
                description 'Enable FRR backup tunnel reference main path affin'
                          + 'ity'
                            ;
                type enumeration {
                  enum disabled {
                    value 0 ;
                  }
                  enum enabled {
                    value 1 ;
                  }
                }
                default disabled ;
              }
              ncd:revise-date 2018-01-10 ;
            }
            container protect {
              description 'Tunnel protect configuration.'
                          ;
              presence 'protect of dynamic tunnel'
                       ;
              leaf coexist {
                description 'Enable protect coexist of a tunnel.'
                            ;
                type enumeration {
                  enum disabled {
                    value 0 ;
                  }
                  enum enabled {
                    value 1 ;
                  }
                }
                default disabled ;
              }
              leaf nest {
                description 'Enable protect coexist of a tunnel.'
                            ;
                type enumeration {
                  enum disabled {
                    value 0 ;
                  }
                  enum enabled {
                    value 1 ;
                  }
                }
                default disabled ;
              }
              ncd:revise-date 2018-08-08 ;
            }
            container tunnel-preferred-igp {
              presence 'tunnel preferred igp'
                       ;
              list tnnl-preferred-igp {
                description 'preferred IGP of the tunnel.'
                            ;
                key role ;
                leaf role {
                  description 'role of the tunnel: main or hot-standby.'
                              ;
                  type enumeration {
                    enum main {
                      value 1 ;
                      description 'main lsp'
                                  ;
                    }
                    enum hsb {
                      value 2 ;
                      description 'hot-standby lsp'
                                  ;
                    }
                  }
                }
                choice tnnl-preferred-igp-type {
                  case tnnl-ospf-preferred {
                    leaf tnnl-preferred-ospf {
                      description 'Specify OSPF for CSPF routing to use prior.'
                                  ;
                      type enumeration {
                        enum ospf {
                          value 1 ;
                        }
                      }
                      mandatory true ;
                    }
                    container tnnl-ospf-process {
                      choice tnnl-ospf-process-config {
                        case tnnl-ospf-process-configed {
                          leaf tnnl-ospf-process-id {
                            description 'OSPF process ID'
                                        ;
                            type uint32 {
                              range 1..65535 ;
                            }
                            mandatory true ;
                          }
                          container tnnl-ospf-area {
                            choice tnnl-ospf-area-config {
                              case tnnl-ospf-area-configed {
                                leaf tnnl-ospf-area-id {
                                  description 'OSPF area ID'
                                              ;
                                  type ncd:ipv4-address ;
                                  mandatory true ;
                                }
                              }
                            }
                          }
                        }
                      }
                    }
                  }
                  case tnnl-isis-preferred {
                    leaf tnnl-preferred-isis {
                      description 'Specify ISIS for CSPF routing to use prior.'
                                  ;
                      type enumeration {
                        enum isis {
                          value 2 ;
                        }
                      }
                      mandatory true ;
                    }
                    container tnnl-isis-process {
                      choice tnnl-isis-process-config {
                        case tnnl-isis-process-configed {
                          leaf tnnl-isis-process-id {
                            description 'ISIS process ID'
                                        ;
                            type uint32 {
                              range 0..65535 ;
                            }
                            mandatory true ;
                          }
                          container tnnl-isis-level {
                            choice tnnl-isis-level-configed {
                              case tnnl-isis-level1-configed {
                                leaf tnnl-isis-level-1 {
                                  type enumeration {
                                    enum level-1 {
                                      value 1 ;
                                    }
                                  }
                                  mandatory true ;
                                }
                              }
                              case tnnl-isis-level2-configed {
                                leaf tnnl-isis-level-2 {
                                  description 'ISIS level-2'
                                              ;
                                  type enumeration {
                                    enum level-2 {
                                      value 2 ;
                                    }
                                  }
                                  mandatory true ;
                                }
                              }
                            }
                          }
                        }
                      }
                    }
                  }
                }
              }
              ncd:revise-date 2018-09-29 ;
            }
            container pre-setup {
              description 'Tunnel pre-setup LSP configuration.'
                          ;
              choice path-class {
                description 'Path Selection Type.'
                            ;
                case dynamic {
                  description 'Dynamic Path Selection.'
                              ;
                  leaf dynamic {
                    description 'The path type is dynamic.'
                                ;
                    type empty ;
                    mandatory true ;
                  }
                }
                case explicit-name {
                  description 'Based on the name of the explicit path selection.'
                              ;
                  leaf explicit-path-name {
                    description 'The related explicit path name.'
                                ;
                    type string {
                      length 1..64 ;
                    }
                    mandatory true ;
                  }
                }
                case expilict-id {
                  description 'Id-based explicit path selection.'
                              ;
                  leaf explicit-path-id {
                    description 'The related explicit path ID.'
                                ;
                    type uint16 {
                      range 1..65535 ;
                    }
                    mandatory true ;
                  }
                }
              }
              ncd:revise-date 2018-08-27 ;
            }
          }
        }
        container admin-weight {
          description 'Configuration of admin weight.'
                      ;
          container if-based {
            description 'Configuration of admin-weight for the specified interf'
                      + 'ace.'
                        ;
            list interface {
              description 'An interface weight management.'
                          ;
              max-elements 255 ;
              key name ;
              leaf name {
                description 'Interface name.'
                            ;
                type ncd:ifname ;
              }
              leaf te-metric {
                description 'The configuration of metric for a mpls te interfac'
                          + 'e.'
                            ;
                type uint32 {
                  range 1..65535 ;
                }
              }
            }
          }
          container tunnel-based {
            description 'Configuration of admin-weight for the specified Tunnel.'
                        ;
            list tunnel {
              description 'The weight of a tunnel management.'
                          ;
              min-elements 0 ;
              max-elements 131070 ;
              key name ;
              leaf name {
                description 'Tunnel name.'
                            ;
                type ncd:ifname ;
              }
              leaf te-metric {
                description 'The Configuration of traffic-eng metric for Tunnel.'
                            ;
                type uint32 {
                  range 1..4294967295 ;
                }
                mandatory true ;
              }
            }
          }
        }
        container wtr {
          leaf cleanup-delay-time {
            description 'Configuration of clean up delay time.'
                        ;
            type int16 {
              range 0..600 ;
            }
            units second ;
            default 15 ;
          }
          leaf installation-delay-time {
            description 'Configuration of installation delay time.'
                        ;
            type int16 {
              range 0..600 ;
            }
            units second ;
            default 10 ;
          }
        }
        container soft-preemption {
          description 'Configuration of soft preemption.'
                      ;
          presence 'configuration of soft preemption'
                   ;
          container timeout {
            leaf timeout {
              description 'Configure soft-preemption keep-alive time.'
                          ;
              type int16 {
                range 1..300 {
                  description 'unit is second.'
                              ;
                }
              }
              units second ;
              default 30 ;
            }
          }
        }
        container none-null {
          description 'The egress label management for support none null label.'
                      ;
          presence 'configure none-null label'
                   ;
          list advertise-none-null {
            description 'The configuration of egress for support none null labe'
                      + 'l.'
                        ;
            key tunnel-name ;
            leaf tunnel-name {
              description 'Tunnel name.'
                          ;
              type ncd:ifname ;
            }
            leaf enable {
              description 'The none-null label for egress enable.'
                          ;
              type empty ;
            }
          }
          ncd:revise-date 2015-10-21 ;
        }
      }
      container ds-te {
        description 'The configuration of DS-TE.'
                    ;
        presence 'configure ds-te'
                 ;
        container model {
          description 'The bandwidth resv model.'
                      ;
          leaf value {
            description 'The bandwidth resv model.The te-class and BC bandwidth'
                      + ' which depend on DS-TE model can only be configurated '
                      + 'at MAM,RDM or EXTEND-MAM model.'
                        ;
            type enumeration {
              enum RDM {
                value 0 ;
              }
              enum MAM {
                value 1 ;
              }
              enum MPLS-TE {
                value 2 ;
              }
              enum EXTEND-MAM {
                value 254 ;
              }
              enum NONE-TE {
                value 255 ;
              }
            }
            default MPLS-TE ;
          }
        }
        container te-classes {
          description 'Te-class configuration.'
                      ;
          list te-class {
            description "Te-class configuration.If the class-type and priority "
                      + "of tunnel don't match the te-class,the tunnel path com"
                      + "pute can't be success."
                        ;
            min-elements 0 ;
            max-elements 8 ;
            key class-id ;
            leaf class-id {
              description 'TE class ID. Range is 0-7.'
                          ;
              type uint8 {
                range 0..7 ;
              }
            }
            leaf type {
              description 'TE class type. Range is 0-7.'
                          ;
              type uint8 {
                range 0..7 ;
              }
              mandatory true ;
            }
            leaf priority {
              description 'TE class priority. Range is 0-7.'
                          ;
              type uint8 {
                range 0..7 ;
              }
              mandatory true ;
            }
          }
        }
        container if-bandwidthes {
          description 'The configuration of interface bandwidth.'
                      ;
          list if-bandwidth {
            description 'The configuration of interface bandwidth.'
                        ;
            max-elements 510 ;
            key 'name reserve-tunnel-type'
                ;
            leaf name {
              description 'Interface name.'
                          ;
              type ncd:ifname ;
            }
            leaf reserve-tunnel-type {
              description 'The reserve type of tunnel.'
                          ;
              type enumeration {
                enum dynamic {
                  value 1 ;
                }
                enum static {
                  value 2 ;
                }
              }
            }
            leaf bandwidth {
              description 'Interface total resv bandwidth.'
                          ;
              type uint32 {
                range 1..4294967295 ;
              }
              units kbps ;
              mandatory true ;
            }
            leaf bc0 {
              description "BC0 bandwidth.The sum of BC bandwidth can't be large"
                        + "r thaninterface bandwidth."
                          ;
              type uint32 {
                range 0..4294967295 ;
              }
              units kbps ;
              default 0 ;
            }
            leaf bc1 {
              description "BC1 bandwidth.The sum of BC bandwidth can't be large"
                        + "r thaninterface bandwidth."
                          ;
              type uint32 {
                range 0..4294967295 ;
              }
              units kbps ;
              default 0 ;
            }
            leaf bc2 {
              description "BC2 bandwidth.The sum of BC bandwidth can't be large"
                        + "r thaninterface bandwidth."
                          ;
              type uint32 {
                range 0..4294967295 ;
              }
              units kbps ;
              default 0 ;
            }
            leaf bc3 {
              description "BC3 bandwidth.The sum of BC bandwidth can't be large"
                        + "r thaninterface bandwidth."
                          ;
              type uint32 {
                range 0..4294967295 ;
              }
              units kbps ;
              default 0 ;
            }
            leaf bc4 {
              description "BC4 bandwidth.The sum of BC bandwidth can't be large"
                        + "r thaninterface bandwidth."
                          ;
              type uint32 {
                range 0..4294967295 ;
              }
              units kbps ;
              default 0 ;
            }
            leaf bc5 {
              description "BC5 bandwidth.The sum of BC bandwidth can't be large"
                        + "r thaninterface bandwidth."
                          ;
              type uint32 {
                range 0..4294967295 ;
              }
              units kbps ;
              default 0 ;
            }
            leaf bc6 {
              description "BC6 bandwidth.The sum of BC bandwidth can't be large"
                        + "r thaninterface bandwidth."
                          ;
              type uint32 {
                range 0..4294967295 ;
              }
              units kbps ;
              default 0 ;
            }
            leaf bc7 {
              description "BC7 bandwidth.The sum of BC bandwidth can't be large"
                        + "r thaninterface bandwidth."
                          ;
              type uint32 {
                range 0..4294967295 ;
              }
              units kbps ;
              default 0 ;
            }
            leaf per-flow-bw {
              description "The per flow bandwidth.The bandwidth of any bypassed"
                        + " tunnel of this interface can't be larger than this "
                        + "attribute.This attribute can't be larger than interf"
                        + "ace total bandwidth."
                          ;
              type uint32 {
                range 0..4294967295 ;
              }
              units kbps ;
              default 0 ;
            }
            leaf percent {
              description "The bandwidth occupied ratio.The dynamic percentage "
                        + "of interface speed and the static percentage of inte"
                        + "rface speed can't be over 100 percent."
                          ;
              type uint8 {
                range 0..100 ;
              }
              default 40 ;
            }
            leaf speed-blind {
              description 'To deternmine wether or not the reserved bandwidth o'
                        + 'f tunnel can overpass the interface speed.'
                          ;
              type enumeration {
                enum enabled {
                  value 1 ;
                }
                enum disabled {
                  value 2 ;
                }
              }
              default disabled ;
            }
            leaf eir {
              description 'TE interface excess information rate.'
                          ;
              type uint32 {
                range 0..4294967295 ;
              }
              units kbps ;
              default 0 ;
              ncd:revise-date 2015-06-04 ;
            }
            ncd:select 'name reserve-tunnel-type'
                       ;
          }
        }
      }
      container passive-if {
        description 'The configuration of passive interface.Traffic engineering'
                  + ' flood the interface information to IGP-TE for OSPF path c'
                  + 'ompute at inter-area condition.'
                    ;
        presence 'configuration of passive-if'
                 ;
        list cross-domain {
          description 'Passive interface list.'
                      ;
          max-elements 2550 ;
          key 'if-name nbr-route-id'
              ;
          leaf if-name {
            description 'Interface name.'
                        ;
            type ncd:ifname ;
          }
          leaf nbr-route-id {
            description 'The neighbor route ID.'
                        ;
            type ncd:ipv4-address ;
          }
          leaf nbr-if-addr {
            description 'Neighbor interface address.'
                        ;
            type ncd:ipv4-address {
              pattern '([1-9]|[1-9][0-9]|1[0-9][0-9]|2[0-4][0-9]|25[0-5])(.([0-'
                    + '9]|[1-9][0-9]|1[0-9][0-9]|2[0-4][0-9]|25[0-5])){3}'
                      {
                description 'To filter the invalid address.'
                            ;
              }
            }
          }
          leaf nbr-ospf-node-id {
            description 'Neighbor OSPF node ID.'
                        ;
            type ncd:ipv4-address-none-zero ;
          }
          leaf nbr-isis-system-id {
            description 'Neighbor ISIS system ID.'
                        ;
            type ncd:mac-address ;
            default 00:00:00:00:00:00 ;
          }
          ncd:select 'if-name nbr-route-id'
                     ;
        }
      }
      container bfd {
        description 'Configuration of BFD.'
                    ;
        presence 'configuration of bfd'
                 ;
        container interfaces {
          description 'TE BFD interface configuration.'
                      ;
          list interface {
            description 'The interface BFD list.'
                        ;
            min-elements 0 ;
            max-elements 100 ;
            key name ;
            leaf name {
              description 'Interface name.'
                          ;
              type ncd:ifname ;
            }
            leaf enable {
              description 'The interface BFD enable.'
                          ;
              type enumeration {
                enum disabled {
                  value 0 ;
                }
                enum enabled {
                  value 1 ;
                }
              }
              mandatory true ;
            }
            leaf template-name {
              description 'The intf bfd template name.'
                          ;
              type string {
                length 1..31 ;
              }
              ncd:revise-date 2020-08-19 ;
            }
          }
        }
        container tunnels {
          description 'BFD tunnel settings.'
                      ;
          list tunnel {
            description 'BFD is set in a tunnel.'
                        ;
            max-elements 100 ;
            key 'name enable'
                ;
            leaf name {
              description 'Tunnel name.'
                          ;
              type ncd:ifname ;
            }
            leaf enable {
              description 'The tunnel BFD enable.This attribute depend on the t'
                        + 'unnel role and direction-type.'
                          ;
              type enumeration {
                enum master {
                  value 1 ;
                }
                enum slave {
                  value 2 ;
                }
              }
            }
            choice detect-param {
              description 'Detect param.'
                          ;
              mandatory true ;
              case template {
                description 'Bfd template name.'
                            ;
                leaf template-name {
                  description 'The tunnel bfd template name.'
                              ;
                  type string {
                    length 1..31 ;
                  }
                  mandatory true ;
                }
                ncd:revise-date 2020-04-23 ;
              }
              case detect-params {
                description 'Detect params.'
                            ;
                leaf min-tx-interval {
                  description 'The tunnel BFD min transmit interval.'
                              ;
                  type uint32 {
                    range 3..990 ;
                  }
                  units ms ;
                  mandatory true ;
                }
                leaf min-rx-interval {
                  description 'The tunnel BFD min receive interval.'
                              ;
                  type uint32 {
                    range 3..990 ;
                  }
                  units ms ;
                  mandatory true ;
                }
                leaf detect-multiple {
                  description 'The tunnel BFD detecting multiple.'
                              ;
                  type uint16 {
                    range 3..50 ;
                  }
                  mandatory true ;
                }
              }
            }
            choice reverse-path {
              description 'Reverse path.'
                          ;
              case reverse-tunnel {
                description 'Selection reverse tunnel.'
                            ;
                leaf reverse-tunnelid {
                  description 'The tunnel bfd associatd reverse tunnelid.'
                              ;
                  type uint16 {
                    range 1..65535 {
                      description 'The tunnel bfd reverse tunnel id range'
                                  ;
                    }
                  }
                }
                ncd:revise-date 2017-09-04 ;
              }
              case ld-rd {
                description 'Local and Remote discriminator for BFD.'
                            ;
                container ld-rd {
                  description 'Local and Remote discriminator for BFD.'
                              ;
                  presence 'Local and Remote discriminator for BFD.'
                           ;
                  leaf ld {
                    description 'Local discriminator for BFD.'
                                ;
                    type uint32 {
                      range 1..2048 ;
                    }
                    mandatory true ;
                  }
                  leaf rd {
                    description 'Remote discriminator for BFD.'
                                ;
                    type uint32 {
                      range 1..4294967295 ;
                    }
                    mandatory true ;
                  }
                }
                ncd:revise-date 2019-07-01 ;
              }
              ncd:revise-date 2017-09-04 ;
            }
            ncd:select 'name enable'
                       ;
          }
        }
        container tunnels-active-lsp {
          description 'Active lsp BFD tunnel settings.'
                      ;
          presence 'tunnels active lsp'
                   ;
          list active-lsp-bfd {
            description 'BFD is set in a active lsp.'
                        ;
            key tunnel-name ;
            leaf tunnel-name {
              description 'Tunnel name.'
                          ;
              type ncd:ifname ;
            }
            leaf enable {
              description 'The tunnel Active-lsp bfd enable.'
                          ;
              type empty ;
            }
          }
          ncd:revise-date 2015-08-12 ;
        }
      }
      container access-tunnel {
        description 'The access tunnel,it is related with ingress tunnel.'
                    ;
        presence 'configuration of access-tunnel'
                 ;
        list gtunnel {
          description 'The gmpls access tunnel list.'
                      ;
          max-elements 131070 ;
          key name ;
          leaf name {
            description 'The gmpls tunnel name.'
                        ;
            type ncd:ifname ;
          }
          container role-type {
            description 'The gmpls access tunnel role and direction type.'
                        ;
            presence 'Configure tunnel role and type.'
                     ;
            leaf role {
              description 'The gmpls access tunnel role.'
                          ;
              type enumeration {
                enum transitNode {
                  value 2 ;
                }
                enum egressNode {
                  value 3 ;
                }
              }
              mandatory true ;
            }
            leaf direction-type {
              description 'The gmpls access tunnel direction type.'
                          ;
              type enumeration {
                enum unidirectional {
                  value 1 ;
                }
                enum bidirectional {
                  value 2 ;
                }
              }
              mandatory true ;
            }
          }
          container triple {
            description 'The gmpls access tunnel triple elements.'
                        ;
            presence 'Configure tunnel triple.'
                     ;
            leaf ingress-tunnel-id {
              description 'The ingress gmpls tunnel ID,it is used to locate ing'
                        + 'ress gmpls tunnel.'
                          ;
              type uint32 {
                range 1..65535 ;
              }
              mandatory true ;
            }
            leaf ingress-lsr-id {
              description 'The ingress route ID.'
                          ;
              type ncd:ipv4-address ;
              mandatory true ;
            }
            leaf egress-lsr-id {
              description 'The egress route ID.'
                          ;
              type ncd:ipv4-address ;
              mandatory true ;
            }
          }
          ncd:revise-date 2016-07-29 ;
        }
        list tunnel {
          description 'The access tunnel list.'
                      ;
          max-elements 131070 ;
          key name ;
          leaf name {
            description 'The tunnel name.'
                        ;
            type ncd:ifname ;
          }
          leaf activation {
            description 'The activation of access-tunnel.Only the egress node o'
                      + 'f bidirectional access-tunnel can configure this attri'
                      + 'bute.'
                        ;
            type enumeration {
              enum disabled {
                value 0 ;
              }
              enum enabled {
                value 1 ;
              }
              enum invalid {
                value 2 ;
              }
            }
            default enabled ;
          }
          leaf ultralimit-discard {
            description 'Tunnel ultralimit outbound discard enabled.'
                        ;
            type enumeration {
              enum disabled {
                value 1 ;
              }
              enum enabled {
                value 2 ;
              }
            }
            default disabled ;
          }
          leaf flow-statistics {
            description 'The switch of access tunnel flow statistics.'
                        ;
            type enumeration {
              enum disabled {
                value 0 ;
              }
              enum enabled {
                value 1 ;
              }
            }
            default disabled ;
          }
          container role-type {
            description 'The tunnel role and direction type.'
                        ;
            presence 'Configure tunnel role and type.'
                     ;
            leaf role {
              description 'The access tunnel role.'
                          ;
              type enumeration {
                enum transitNode {
                  value 2 ;
                }
                enum egressNode {
                  value 3 ;
                }
              }
              mandatory true ;
            }
            leaf direction-type {
              description 'The access tunnel direction type.'
                          ;
              type enumeration {
                enum unidirectional {
                  value 1 ;
                }
                enum bidirectional {
                  value 2 ;
                }
              }
              mandatory true ;
            }
          }
          container triple {
            description 'The tunnel triple elements.'
                        ;
            presence 'Configure tunnel triple.'
                     ;
            leaf ingress-tunnel-id {
              description 'The ingress tunnel ID,it is used to locate ingress t'
                        + 'unnel.'
                          ;
              type uint32 {
                range 1..65535 ;
              }
              mandatory true ;
            }
            leaf ingress-lsr-id {
              description 'The ingress route ID.'
                          ;
              type ncd:ipv4-address ;
              mandatory true ;
            }
            leaf egress-lsr-id {
              description 'The egress route ID.'
                          ;
              type ncd:ipv4-address ;
              mandatory true ;
            }
          }
          container policy {
            status obsolete {
              ncd:revise-date 2015-06-03 ;
            }
            description 'The tunnel policy class.'
                        ;
            leaf policy-class {
              description 'The access tunnel policy class.It depend on directio'
                        + 'n-type and role,and only the bidirectional egress tu'
                        + 'nnel can configure this attribute.'
                          ;
              type uint8 {
                range '0..7 | 255'
                      {
                  description '0-7 represent normal configuration. Ingress and '
                            + 'Egress of co-tunnel uses 255 as its default valu'
                            + 'e.'
                              ;
                }
              }
            }
          }
        }
      }
      container graceful-restart {
        description 'Configuration of Graceful-restart.Graceful-restart and frr'
                  + '-hello are mutual exclusion.'
                    ;
        presence 'The graceful-restart configuration for RSVP.'
                 ;
        leaf enable {
          description 'Enable graceful restart and graceful-restart hello funct'
                    + 'ion, before to enable this node, please ensure that frr '
                    + 'hello is disabled for frr hello conflict to graceful-res'
                    + 'tart hello.'
                      ;
          type empty ;
        }
        leaf refresh-interval {
          description 'Graceful-restart hello refresh interval time, range 1000'
                    + '~30000 (ms), default value is 10000(ms).'
                      ;
          type uint32 {
            range 1000..30000 ;
          }
          units ms ;
          default 10000 ;
        }
        leaf refresh-misses {
          description 'Miss number of Graceful-restart hello, range: 4-10, defa'
                    + 'ult value is 4.'
                      ;
          type uint8 {
            range 4..10 ;
          }
          default 4 ;
        }
        leaf restart-time {
          description 'Restart time interval of Graceful-restart for this node,'
                    + ' range: 120000-600000(ms), default value is 120000(ms).'
                      ;
          type uint32 {
            range 120000..600000 ;
          }
          units ms ;
          default 120000 ;
        }
        leaf recovery-time {
          description 'Recovery time interval of Graceful-restart for this node'
                    + ', range:120000~7200000 (ms), default value is 120000 (ms'
                    + ').'
                      ;
          type uint32 {
            range 120000..7200000 ;
          }
          units ms ;
          default 120000 ;
        }
        leaf node-hello-enable {
          description 'If this object is true, then it enables the Node Hello.I'
                    + 't depends graceful-restart enable.'
                      ;
          type enumeration {
            enum disabled {
              value 0 ;
            }
            enum enabled {
              value 1 ;
            }
          }
          default disabled ;
        }
        leaf extend-recovery-path {
          description 'If this object is true, then it enables the Gr Extend Re'
                    + 'covery Path. The node will send recovery-path with priva'
                    + 'te ero to all neighbours.'
                      ;
          type enumeration {
            enum disabled {
              value 0 ;
            }
            enum enabled {
              value 1 ;
            }
          }
          default disabled ;
        }
        list extend-nbr-rid-list {
          min-elements 0 ;
          max-elements 32 ;
          key extend-nbr-rid ;
          leaf extend-nbr-rid {
            description 'This leaf node specifies neighbor router id which reco'
                      + 'very path with private ero will be sent to. The maxium'
                      + ' number of neighbour address is 32.'
                        ;
            type ncd:ipv4-address ;
          }
        }
        leaf standard-recovery-path {
          description 'If this object is true, then it enables the GR Standard '
                    + 'Recovery Path. The node will send standard recovery-path'
                    + ' to all neighbours.'
                      ;
          type enumeration {
            enum disabled {
              value 0 ;
            }
            enum enabled {
              value 1 ;
            }
          }
          default disabled ;
          ncd:revise-date 2017-10-19 ;
        }
        container standard-nbr {
          description 'Configuration of neighbour router id which standard reco'
                    + 'very path will be sent to.'
                      ;
          presence 'configuration of standard-nbr-rid'
                   ;
          list standard-nbr-rid-list {
            description 'The list of neighbour router id which standard recover'
                      + 'y path will be sent to.'
                        ;
            max-elements 32 ;
            key standard-nbr-rid ;
            leaf standard-nbr-rid {
              description 'This leaf node specifies neighbor router id which st'
                        + 'andard recovery path will be sent to. The maxium num'
                        + 'ber of neighbour address is 32.'
                          ;
              type ncd:ipv4-address ;
            }
          }
          ncd:revise-date 2017-10-19 ;
        }
      }
      container authentication {
        description 'Configuration authentication for the specified interface.'
                    ;
        presence 'configuration of authentication'
                 ;
        list interface {
          description 'Interface list.'
                      ;
          max-elements 255 ;
          key name ;
          leaf name {
            description 'The name of this interface.'
                        ;
            type ncd:ifname ;
          }
          leaf enable {
            description 'If this interface enables RSVP cryptographic authentic'
                      + 'ation, this value is true, otherwise it is false. Defa'
                      + 'ult value of this node is disabled.'
                        ;
            type enumeration {
              enum disabled {
                value 0 ;
              }
              enum enabled {
                value 1 ;
              }
            }
            default disabled ;
          }
          leaf type {
            description 'Specifies the type of authentication algorithm on this'
                      + ' interface. Default value is md5.'
                        ;
            type enumeration {
              enum md5 {
                value 1 ;
              }
              enum sha {
                value 2 ;
              }
            }
            default md5 ;
          }
          choice auth-key {
            description 'Authentication key.'
                        ;
            case plaintext {
              description 'Authentication plaintext key.'
                          ;
              leaf key {
                description 'Specifies shared secret key for all neighbors on t'
                          + 'his interface.'
                            ;
                type string {
                  length 8..40 ;
                }
              }
            }
            case ciphertext {
              description 'Authentication ciphertext key.'
                          ;
              leaf encrypt-key {
                description 'Specifies shared secret key for all neighbors on t'
                          + 'his interface.'
                            ;
                type string {
                  length 56..108 ;
                }
              }
              ncd:revise-date 2020-06-13 ;
            }
          }
          leaf keychain {
            description 'Specifies keychain for all neighbors on this interface.'
                        ;
            type string {
              length 1..31 ;
            }
            ncd:revise-date 2016-01-06 ;
          }
          leaf mode {
            description 'Specifies the mode of authentication on this interface'
                      + '. Default value is key.'
                        ;
            type enumeration {
              enum key {
                value 1 ;
              }
              enum keychain {
                value 2 ;
              }
            }
            default key ;
            ncd:revise-date 2016-01-06 ;
          }
          leaf window-size {
            description 'Specifies received window size for authenticated messa'
                      + 'ges on this interface. Range: from 1 to 64, default va'
                      + 'lue: 32.'
                        ;
            type uint8 {
              range 1..64 ;
            }
            default 32 ;
          }
          leaf challage-enable {
            description 'If this interface as a receiver to perform challenge/r'
                      + 'esponse handshake with new'+"\n"
                      + 'RSVP neighbors enables rsvp authentication challenge, '
                      + 'this value is enabled,otherwise it is disabled.'
                        ;
            type enumeration {
              enum disabled {
                value 0 ;
              }
              enum enabled {
                value 1 ;
              }
            }
            default disabled ;
          }
          leaf challage-imp-enable {
            description 'If this interface as a sender  to perform challenge/re'
                      + 'sponse handshake with new'+"\n"
                      + 'RSVP neighbors enables rsvp authentication challenge i'
                      + 'mp,this value is enabled, otherwise it is disabled.'
                        ;
            type enumeration {
              enum disabled {
                value 0 ;
              }
              enum enabled {
                value 1 ;
              }
            }
            default disabled ;
          }
        }
      }
      container frr {
        description 'Configuration of fast reroute. The function depend on rro-'
                  + 'enable.'
                    ;
        presence 'configuration of frr'
                 ;
        list tunnel {
          description 'Tunnel list.'
                      ;
          min-elements 0 ;
          max-elements 131070 ;
          key name ;
          leaf name {
            description 'The tunnel name.'
                        ;
            type ncd:ifname ;
          }
          choice protect-type {
            description 'To assign protect type of FRR, including facility and '
                      + 'one-to-one.'
                        ;
            mandatory true ;
            case facility {
              leaf facility {
                description 'If this tunnel enables facility FRR,this value is '
                          + 'true, otherwise it is false. This configureation i'
                          + 's depend on rro-enable.'
                            ;
                type empty ;
              }
            }
            case one2one {
              leaf one2one {
                description 'If this tunnel enables detour FRR,this value is tr'
                          + 'ue,otherwise, it is false. This Configuration is d'
                          + 'epend on rro-enable.'
                            ;
                type empty ;
              }
            }
          }
          leaf bw-protect {
            description 'Configuration of bandwidth protection.You must configu'
                      + 're FRR protection method before configuring FRR bandwi'
                      + 'dth protection.'
                        ;
            type enumeration {
              enum disabled {
                value 0 ;
                description 'Disabled bw-protect.'
                            ;
              }
              enum enabled {
                value 1 ;
                description 'Enable bw-protect.'
                            ;
              }
            }
            default disabled ;
          }
          container hsblsp-frr {
            description 'To indicate that hotstandby lsp whether enable FRR or '
                      + 'not.'
                        ;
            leaf hsblsp-frr {
              description 'To indicate that hotstandby lsp whether enable FRR o'
                        + 'r not.'
                          ;
              type enumeration {
                enum disabled {
                  value 0 ;
                }
                enum enabled {
                  value 1 ;
                }
              }
              default disabled ;
            }
            ncd:revise-date 2019-11-21 ;
          }
        }
        container interface {
          container manual-backup-tunnels {
            description 'It conflicts to auto-backup-tunnels. A interface can b'
                      + 'e configured one type of backup tunnel.'
                        ;
            list manual-backup-tunnel {
              description 'List of interfaces configured manual backup tunnel.'
                          ;
              max-elements 131070 ;
              key 'intf-name tunnel-id'
                  ;
              leaf intf-name {
                description 'Interface name.'
                            ;
                type ncd:ifname ;
              }
              leaf tunnel-id {
                description 'Configure a MPLSTE backup TE tunnel for this inter'
                          + 'face. The maximum number of MPLSTE backup TE tunne'
                          + 'l configured on this interface is 16. Please ensur'
                          + 'e that the MPLSTE backup TE tunnel does not use th'
                          + 'is interface as its output interface.'
                            ;
                type uint32 {
                  range 1..65535 ;
                }
              }
            }
          }
          container auto-backup-tunnels {
            description 'It conflicts to manual-backup-tunnels. A interface can'
                      + ' be configured one type of backup tunnel.'
                        ;
            list auto-backup-tunnel {
              description 'List of interface configured auto backup tunnel.'
                          ;
              max-elements 65535 ;
              key intf-name ;
              leaf intf-name {
                type ncd:ifname ;
              }
              leaf nhop-only {
                description 'If this object is true, then it only requires LINK'
                          + '_PROTECT by autobackup tunnel.'
                            ;
                type enumeration {
                  enum disabled {
                    value 0 ;
                  }
                  enum enabled {
                    value 1 ;
                  }
                }
                default disabled ;
              }
              leaf auto-backup-enable {
                description 'If this object is true, then it prefers NODE_PROTE'
                          + 'CT to LINK_PROTECT by autobackup tunnel.'
                            ;
                type enumeration {
                  enum disabled {
                    value 0 ;
                  }
                  enum enabled {
                    value 1 ;
                  }
                }
                default disabled ;
              }
            }
          }
        }
        container auto-backup-tnnl-id-range {
          description 'The auto backup tunnel ID scope.'
                      ;
          leaf min {
            description 'The auto backup min tunnel ID depend on product specif'
                      + 'ication.'
                        ;
            type uint32 ;
            default 64512 ;
          }
          leaf max {
            description 'The auto backup max tunnel ID depend on product specif'
                      + 'ication.'
                        ;
            type uint32 ;
            default 65535 ;
          }
        }
        container frr-hello {
          description 'Graceful-restart and frr-hello are mutual exclusion.'
                      ;
          leaf frr-hello-enable {
            description 'Enables or disables hello message in global mode which'
                      + ' is defined in RFC3209.  This leaf node is conflict to'
                      + ' graceful-restart enable. Before configure this leaf n'
                      + 'ode,please make sure that graceful-restart is disabled'
                      + ' and configure frr hello at specified interface.'
                        ;
            type enumeration {
              enum disabled {
                value 0 ;
              }
              enum enabled {
                value 1 ;
              }
            }
            default disabled ;
          }
          list interface {
            description 'Interface list.'
                        ;
            max-elements 255 ;
            key name ;
            leaf name {
              description 'Interface name.'
                          ;
              type ncd:ifname ;
            }
            leaf enable {
              description 'If this object is enabled, then the interface hello '
                        + 'refresh is enable. Before this configure, please mak'
                        + 'e sure that frr-hello-enable is enabled.'
                          ;
              type enumeration {
                enum disabled {
                  value 0 ;
                }
                enum enabled {
                  value 1 ;
                }
              }
              default disabled ;
            }
            leaf refresh-interval {
              description 'Configuration of hello refresh interval (1000-30000 '
                        + 'ms) on interface.'
                          ;
              type uint32 {
                range 1000..30000 ;
              }
              units ms ;
              default 10000 ;
            }
            leaf refresh-misses {
              description 'Configuration of hello refresh misses (4..10) on int'
                        + 'erface.'
                          ;
              type uint8 {
                range 4..10 ;
              }
              default 4 ;
            }
          }
        }
        container frr-promotion {
          presence 'frr promotion configuration'
                   ;
          leaf timer-en {
            description 'Enable timer for frr promotion.'
                        ;
            type enumeration {
              enum disabled {
                value 0 ;
                description 'disable frr promotion.'
                            ;
              }
              enum enabled {
                value 1 ;
                description 'enable frr promotion.'
                            ;
              }
            }
            default disabled ;
          }
          leaf timer-interval {
            description 'Configuration of seconds between promotions.'
                        ;
            type uint32 {
              range 60..604800 ;
            }
            units second ;
            default 300 ;
          }
        }
        container frr-backup {
          description 'The configuration of frr backup-path.'
                      ;
          leaf selection-delay-time {
            description 'Configuration of frr backup-path selection-delay-time'
                        ;
            type uint16 {
              range 5..90 ;
            }
            units second ;
            default 30 ;
          }
          ncd:revise-date 2017-11-14 ;
        }
        container frr-topology {
          leaf enable {
            description 'Enable the function of fast-reroute response topology-'
                      + 'change.'
                        ;
            type enumeration {
              enum disabled {
                value 0 ;
              }
              enum enabled {
                value 1 ;
              }
            }
            default disabled ;
          }
          ncd:revise-date 2018-03-03 ;
        }
      }
      container auto-bandwidth {
        description 'The configuration of auto bandwidth adjustment.'
                    ;
        presence 'For auto bandwidth adjustment.'
                 ;
        container global {
          description 'The global configuration of auto-bandwidth.'
                      ;
          presence 'The global configuration.'
                   ;
          leaf sample-enable {
            description 'The global switch of sample.'
                        ;
            type enumeration {
              enum disabled {
                value 0 ;
              }
              enum enabled {
                value 1 ;
              }
            }
            mandatory true ;
          }
          leaf sample-frequency {
            description 'Auto bandwidth adjustment timer frequency 60~604800 (s'
                      + ').'
                        ;
            type uint32 {
              range 10..604800 ;
            }
            units second ;
            default 300 ;
          }
        }
        container tunnels {
          description 'The tunnel configuration of auto-bandwidth.'
                      ;
          presence 'The tunnel configuration.'
                   ;
          list tunnel {
            description 'The configuration list.'
                        ;
            min-elements 0 ;
            max-elements 131070 ;
            key name ;
            leaf name {
              description 'The tunnel name.'
                          ;
              type ncd:ifname ;
            }
            leaf adjust-enable {
              description 'The adjust switch of tunnel ABW.'
                          ;
              type enumeration {
                enum enabled {
                  value 1 ;
                }
              }
              mandatory true ;
            }
            leaf adjust-frequency {
              description 'Adjust frequence of this tunnel.This attribute depen'
                        + 'd on adjust-enable.'
                          ;
              type uint32 {
                range 60..604800 ;
              }
              units second ;
              default 86400 ;
            }
            leaf adjust-max-value {
              description 'Maximum bandwidth of adjustment.This attribute depen'
                        + 'd on adjust-enable.'
                          ;
              type uint32 {
                range 1..4294967295 ;
              }
              units kbps ;
            }
            leaf adjust-min-value {
              description 'Minimum bandwidth of adjustment.This attribute depen'
                        + 'd on adjust-max-value.'
                          ;
              type uint32 {
                range 0..4294967295 ;
              }
              units kbps ;
              default 0 ;
            }
            leaf adjust-multiple {
              description 'The mutiple of adjustment.This attribute depend on a'
                        + 'djust-enable.'
                          ;
              type uint16 {
                range 50..100 ;
              }
              default 100 ;
            }
            leaf collect-bandwidth {
              description "The collection bandwidth switch.If this attribute is"
                        + " setup,the tunnel just sample bandwidth and don't ad"
                        + "just bandwidth."
                          ;
              type uint8 {
                range 0..1 ;
              }
              default 0 ;
            }
            container overflow {
              description 'The tunnel configuration of auto-bandwidth overflow '
                        + 'adjustment.'
                          ;
              presence 'overflow configuration'
                       ;
              leaf overflow-limit {
                description 'The bandwidth overflow limits.When the overflow ti'
                          + 'me of sampled bandwidth is over the configurated l'
                          + 'imit during adjustment period,the tunnel will trig'
                          + 'ger a bandwidth adjustment.'
                            ;
                type uint16 {
                  range 1..10 ;
                }
                mandatory true ;
              }
              leaf overflow-percent {
                description 'Bandwidth change percent to trigger an overflow.'
                            ;
                type uint32 {
                  range 1..100 ;
                }
                mandatory true ;
              }
              leaf overflow-bandwidth {
                description 'The value of overflow bandwidth.When the sampled b'
                          + 'andwidth is over this value,the overflow will be t'
                          + 'riggered.'
                            ;
                type uint32 {
                  range 10..4294967295 ;
                }
                units kbps ;
                default 10 ;
              }
            }
            container underflow {
              description 'Configures the tunnel underflow detection.'
                          ;
              presence 'underflow configuration'
                       ;
              leaf underflow-limit {
                description 'Configures the number of consecutive collection in'
                          + 'tervals that exceeds the threshold. The bandwidth '
                          + 'underflow triggers an early tunnel bandwidth updat'
                          + 'e.'
                            ;
                type uint16 {
                  range 1..10 ;
                }
                mandatory true ;
              }
              leaf underflow-percent {
                description 'Bandwidth change percent to trigger an underflow.'
                            ;
                type uint32 {
                  range 1..100 ;
                }
                mandatory true ;
              }
              leaf underflow-bandwidth {
                description 'Configures the bandwidth change value in kbps to t'
                          + 'rigger an underflow.'
                            ;
                type uint32 {
                  range 10..4294967295 ;
                }
                units kbps ;
                default 10 ;
              }
              ncd:revise-date 2019-12-03 ;
            }
          }
        }
      }
      container auto-route {
        description 'Auto route of TE tunnel.'
                    ;
        container forwarding-adjacency {
          description 'The forwarding-adjacency function. This function is excl'
                    + 'usive with short-cut.'
                      ;
          list tunnel {
            description 'Forwarding-adjacency list.'
                        ;
            min-elements 0 ;
            max-elements 131070 ;
            key name ;
            leaf name {
              description 'The tunnel name.'
                          ;
              type ncd:ifname ;
            }
            leaf fa-enable {
              description 'Forwarding-adjacency enable.This attribute depend on'
                        + ' the tunnel role and direction-type,it just can be c'
                        + 'onfigured at ingress or bidirectional egress.'
                          ;
              type enumeration {
                enum disabled {
                  value 0 ;
                }
                enum enabled {
                  value 1 ;
                }
              }
              default disabled ;
            }
            leaf fa-holdtime {
              description 'Forwarding-adjacency holdtime.'
                          ;
              type uint32 {
                range 0..4294967295 ;
              }
              default 0 ;
            }
            leaf fa-ipv6 {
              description 'Forwarding-adjacency ipv6.'
                          ;
              type enumeration {
                enum disabled {
                  value 0 ;
                }
                enum enabled {
                  value 1 ;
                }
              }
              default disabled ;
              ncd:revise-date 2015-07-10 ;
            }
          }
        }
        container short-cut {
          description 'The short-cut function. This function is exclusive with '
                    + 'forwarding-adjacency.'
                      ;
          list tunnel {
            description 'The tunnel AR list.'
                        ;
            min-elements 0 ;
            max-elements 131070 ;
            key name ;
            leaf name {
              description 'The tunnel name.'
                          ;
              type ncd:ifname ;
            }
            leaf ar-enable {
              description 'The tunnel auto route switch.This attribute depend o'
                        + 'n the tunnel role.It just can be confitured at ingre'
                        + 'ss.'
                          ;
              type enumeration {
                enum disabled {
                  value 0 ;
                }
                enum enabled {
                  value 1 ;
                }
              }
              default disabled ;
            }
            leaf ar-metric-type {
              description 'Auto route metric type.'
                          ;
              type enumeration {
                enum igp {
                  value 0 ;
                }
                enum defaulAbsolute {
                  value 1 ;
                }
                enum absolute {
                  value 2 ;
                }
                enum relative {
                  value 3 ;
                }
              }
              default igp ;
            }
            leaf ar-relative-metric {
              description 'The relative metric of AR,it is relative to IGP metr'
                        + 'ic.'
                          ;
              type int32 {
                range -10..10 ;
              }
              default 0 ;
            }
            leaf ar-absolute-metric {
              description 'The absolute metric of AR.'
                          ;
              type uint32 {
                range 0..4294967295 ;
              }
              default 0 ;
            }
            leaf ar-ipv6 {
              description 'auto route ipv6.'
                          ;
              type enumeration {
                enum disabled {
                  value 0 ;
                }
                enum enabled {
                  value 1 ;
                }
              }
              default disabled ;
              ncd:revise-date 2015-07-10 ;
            }
          }
        }
      }
      container srlg {
        description 'Configuration of srlg.'
                    ;
        container one-to-one {
          description 'The one-to-one type of srlg. The enable and mode should '
                    + 'configure together.'
                      ;
          leaf enable {
            description 'One-to-one type enable.'
                        ;
            type enumeration {
              enum disabled {
                value 0 ;
              }
              enum enabled {
                value 1 ;
              }
            }
            default disabled ;
          }
          leaf mode {
            description 'The mode of one-to-one type.'
                        ;
            type enumeration {
              enum none {
                value 0 ;
              }
              enum force {
                value 1 ;
              }
              enum prefer {
                value 2 ;
              }
            }
            default none ;
          }
        }
        container facility {
          description 'The facility type of srlg. The enable and mode should co'
                    + 'nfigure together.'
                      ;
          leaf enable {
            description 'Facility type enable.'
                        ;
            type enumeration {
              enum disabled {
                value 0 ;
              }
              enum enabled {
                value 1 ;
              }
            }
            default disabled ;
          }
          leaf mode {
            description 'The mode of facility type.'
                        ;
            type enumeration {
              enum none {
                value 0 ;
              }
              enum force {
                value 1 ;
              }
              enum prefer {
                value 2 ;
              }
            }
            default none ;
          }
        }
        container auto-backup {
          description 'The auto-backup type of srlg. The enable and mode should'
                    + ' configure together.'
                      ;
          leaf enable {
            description 'Auto-backup type enable.'
                        ;
            type enumeration {
              enum disabled {
                value 0 ;
              }
              enum enabled {
                value 1 ;
              }
            }
            default disabled ;
          }
          leaf mode {
            description 'The mode of auto-backup type.'
                        ;
            type enumeration {
              enum none {
                value 0 ;
              }
              enum force {
                value 1 ;
              }
              enum prefer {
                value 2 ;
              }
            }
            default none ;
          }
        }
        container hotstandby {
          description 'The hotstandy type of srlg. The enable and mode should c'
                    + 'onfigure together.'
                      ;
          leaf enable {
            description 'Auto-backup type enable.'
                        ;
            type enumeration {
              enum disabled {
                value 0 ;
              }
              enum enabled {
                value 1 ;
              }
            }
            default disabled ;
          }
          leaf mode {
            description 'The mode of hotstandby type.'
                        ;
            type enumeration {
              enum none {
                value 0 ;
              }
              enum force {
                value 1 ;
              }
              enum prefer {
                value 2 ;
              }
            }
            default none ;
          }
        }
        list interface {
          description 'Interface list for SRLG.'
                      ;
          max-elements 765 ;
          key 'name value'
              ;
          leaf name {
            description 'Interface name.'
                        ;
            type ncd:ifname ;
          }
          leaf value {
            description 'Configure SRLG value on specified interface. Every TE '
                      + 'interface can configure 3 SRLG value. The value range '
                      + 'from 0 to 4294967295.'
                        ;
            type uint32 {
              range 0..4294967295 ;
            }
          }
          ncd:select 'name value'
                     ;
        }
      }
      container hotstandby {
        description 'The configuration of hotstandby.This function depend on rr'
                  + 'o-enable.'
                    ;
        presence 'configuration of hotstandby'
                 ;
        list tunnel {
          description 'The tunnel configuration of hotstandby function.'
                      ;
          max-elements 131070 ;
          key 'name path-option-id'
              ;
          leaf name {
            description 'The tunnel name.'
                        ;
            type ncd:ifname ;
          }
          leaf path-option-id {
            description 'The attribute is the path-option which is protected.'
                        ;
            type uint8 {
              range 1..16 ;
            }
          }
          choice pathtype {
            description 'To assign path type of backup lsp. Three types.'
                        ;
            mandatory true ;
            case dynamic {
              description 'Dynamic Path Selection.'
                          ;
              leaf dynamic {
                description 'The path type is dynamic.'
                            ;
                type empty ;
                mandatory true ;
              }
              leaf prefer {
                description "If this attribute is configured, the backup path o"
                          + "nly can't be completely duplicated with primary pa"
                          + "th, otherwise the backup path must be different fr"
                          + "om primary path."
                            ;
                type boolean ;
                default false ;
              }
            }
            case explicit-id {
              description 'Id-based explicit path selection.'
                          ;
              leaf path-id {
                description 'The configured explicit path ID.'
                            ;
                type uint16 {
                  range 1..65535 ;
                }
                mandatory true ;
              }
              leaf id-exclude {
                description 'This attribute can be used to indicate whether bac'
                          + 'kup path need exclude primary path strictly.'
                            ;
                type boolean ;
                default false ;
              }
            }
            case explicit-name {
              description 'Based on the name of the explicit path selection.'
                          ;
              leaf path-name {
                description 'The configured explicit path name.'
                            ;
                type string {
                  length 1..64 ;
                }
                mandatory true ;
              }
              leaf name-exclude {
                description 'This attribute can be used to indicate whether bac'
                          + 'kup path need exclude primary path strictly.'
                            ;
                type boolean ;
                default false ;
              }
            }
          }
        }
      }
      container static-tunnels {
        description 'The configuration of static tunnel.'
                    ;
        presence 'configuration of static tunnel'
                 ;
        list tunnel {
          description 'The static tunnel list.'
                      ;
          max-elements 131070 ;
          key name ;
          leaf name {
            description 'The tunnel name.'
                        ;
            type ncd:ifname ;
          }
          leaf activation {
            description 'The activation of static tunnel enable.'
                        ;
            type enumeration {
              enum disabled {
                value 0 ;
              }
              enum enabled {
                value 1 ;
              }
            }
            default enabled ;
          }
          leaf sd {
            description 'The switch of static tunnel sd.'
                        ;
            type enumeration {
              enum enabled {
                value 1 ;
              }
              enum disabled {
                value 2 ;
              }
            }
            default disabled ;
          }
          leaf performance-switch {
            description 'The switch of static tunnel performance statistics.'
                        ;
            type enumeration {
              enum off {
                value 0 ;
              }
              enum on {
                value 1 ;
              }
            }
            default off ;
          }
          leaf track-name {
            description 'The track name.'
                        ;
            type string {
              length 1..31 ;
            }
          }
          leaf ultralimit-discard {
            description 'Tunnel ultralimit outbound discard enabled.'
                        ;
            type enumeration {
              enum disabled {
                value 1 ;
              }
              enum enabled {
                value 2 ;
              }
            }
            default disabled ;
          }
          leaf flow-statistics {
            description 'The switch of static tunnel flow statistics.'
                        ;
            type enumeration {
              enum disabled {
                value 0 ;
              }
              enum enabled {
                value 1 ;
              }
            }
            default disabled ;
          }
          leaf hard-pipe {
            description 'The switch of static tunnel hard pipe.'
                        ;
            type enumeration {
              enum disabled {
                value 0 ;
              }
              enum enabled {
                value 1 ;
              }
            }
            default disabled ;
            ncd:revise-date 2016-12-09 ;
          }
          leaf spme {
            description 'The switch of static tunnel SPME.'
                        ;
            type enumeration {
              enum disabled {
                value 0 ;
              }
              enum enabled {
                value 1 ;
              }
            }
            default disabled ;
            ncd:revise-date 2017-08-04 ;
          }
          container role-type {
            description 'The tunnel role and direction type.'
                        ;
            presence 'Configure tunnel role and type.'
                     ;
            leaf role {
              description 'The static tunnel role including ingress,transit and'
                        + ' egress.'
                          ;
              type enumeration {
                enum ingressNode {
                  value 1 ;
                }
                enum transitNode {
                  value 2 ;
                }
                enum egressNode {
                  value 3 ;
                }
              }
              mandatory true ;
            }
            leaf direction-type {
              description 'The static tunnel direction type including unidirect'
                        + 'ional and bidirectional.'
                          ;
              type enumeration {
                enum unidirectional {
                  value 1 ;
                }
                enum bidirectional {
                  value 2 ;
                }
              }
              mandatory true ;
            }
          }
          container triple {
            description 'The tunnel triple elements.'
                        ;
            presence 'Configure tunnel triple.'
                     ;
            leaf ingress-tunnel-id {
              description 'The ingress tunnel ID,it is used to locate ingress t'
                        + 'unnel. This attribute is determined by product.'
                          ;
              type uint32 {
                range 1..264192 ;
              }
              mandatory true ;
            }
            choice ip-type {
              description 'The type of triple elements address.'
                          ;
              mandatory true ;
              case ipv4 {
                description 'IPv4 address.'
                            ;
                leaf ingress-id {
                  description 'The ingress route ID.'
                              ;
                  type ncd:ipv4-address ;
                  mandatory true ;
                }
                leaf egress-id {
                  description 'The egress route ID.'
                              ;
                  type ncd:ipv4-address ;
                  mandatory true ;
                }
              }
              case ipv6 {
                description 'IPv6 address.'
                            ;
                container ipv6 {
                  description 'The IPv6 address elements.'
                              ;
                  leaf ingress-ipv6-id {
                    description 'The ingress IPv6 route ID.'
                                ;
                    type ncd:ipv6-address ;
                    mandatory true ;
                  }
                  leaf egress-ipv6-id {
                    description 'The egress IPv6 route ID.'
                                ;
                    type ncd:ipv6-address ;
                    mandatory true ;
                  }
                }
                ncd:revise-date 2019-05-13 ;
              }
            }
          }
          container policy {
            status obsolete {
              ncd:revise-date 2015-06-03 ;
            }
            description 'The static tunnel policy class.This attribute depend o'
                      + 'n the tunnel role and direction-type,it just can be co'
                      + 'nfigured at ingress or bidirectional egress.'
                        ;
            leaf class {
              description 'The tunnel policy class configuration. From 0 to 7 r'
                        + 'epresent normal configuration. Ingress and egress of'
                        + ' co-tunnel use 255 as its default value.'
                          ;
              type uint8 {
                range '0..7 | 255'
                      ;
              }
            }
          }
          container tunnel-bind {
            description 'The associated static tunnel bind function.'
                        ;
            presence 'Configure bound tunnel.'
                     ;
            leaf associated-tunnel-id {
              description 'The associated tunnel id which is the tunnel id of a'
                        + 'ccess tunnel. This function can only be configured a'
                        + 't ingress node.This attribute is determined by produ'
                        + 'ct.'
                          ;
              type uint32 {
                range 1..131072 ;
              }
              mandatory true ;
            }
          }
          container lsps {
            description 'The configured lsp of static tunnel.'
                        ;
            list lsp {
              description 'Lsp list.'
                          ;
              max-elements 1 ;
              key 'tunnel-id lsp-id'
                  ;
              leaf tunnel-id {
                description 'The tunnel ID. This attribute is determined by pro'
                          + 'duct.'
                            ;
                type uint32 {
                  range 1..131072 ;
                }
              }
              leaf lsp-id {
                description "The tunnel's lsp ID."
                            ;
                type uint16 {
                  range 1..65535 ;
                }
              }
              container positive-attribute {
                description 'The configuration of positive out-section and in-s'
                          + 'ection.'
                            ;
                leaf inport {
                  description 'The positive in-port.This attribute must be conf'
                            + 'igured with inlabel at the same time.'
                              ;
                  type ncd:ifname ;
                }
                leaf inlabel {
                  description 'The positive in-label. This attribute must be co'
                            + 'nfigured with inport at the same time.'
                              ;
                  type uint32 {
                    range '0 | 2 | 3 | 16..1048575'
                          ;
                  }
                }
                leaf outport {
                  description 'The positive out-port.This attribute must be con'
                            + 'figured with outlabel at the same time.'
                              ;
                  type ncd:ifname ;
                }
                leaf outlabel {
                  description 'The positive out-label.This attribute must be co'
                            + 'nfigured with outport at the same time.'
                              ;
                  type uint32 {
                    range '0 | 2 | 3 | 16..1048575'
                          ;
                  }
                }
                choice next-hop-choice {
                  description 'The positive next-hop chocie.'
                              ;
                  case ipv4 {
                    description 'The positive IPv4 next-hop type.'
                                ;
                    leaf next-hop {
                      description 'The positive IPv4 next-hop address.'
                                  ;
                      type ncd:ipv4-address {
                        pattern '([1-9]|[1-9][0-9]|1[0-9][0-9]|2[0-4][0-9]|25[0'
                              + '-5])(.([0-9]|[1-9][0-9]|1[0-9][0-9]|2[0-4][0-9'
                              + ']|25[0-5])){3}'
                                ;
                      }
                    }
                  }
                  case ipv6 {
                    description 'The positive IPv6 next-hop type.'
                                ;
                    leaf next-hop-ipv6 {
                      description 'The positive IPv6 next-hop address.'
                                  ;
                      type ncd:ipv6-address ;
                    }
                    ncd:revise-date 2019-05-13 ;
                  }
                }
                leaf out-bandwidth {
                  description 'The positive out bandwidth which is exclusive wi'
                            + 'th ct-bandwidth.  The min, max and default value'
                            + ' of this attribute are determined by product.'
                              ;
                  type uint32 {
                    range 0..4294967295 ;
                  }
                  units kbps ;
                  default 0 ;
                }
                leaf out-burst {
                  description 'The burst of out bandwidth. This attribute must '
                            + 'be configure after out-bandwidth.  The min, max '
                            + 'and default value of this attribute are determin'
                            + 'ed by product.'
                              ;
                  type uint32 {
                    range 1..4294967295 {
                      description 'The minimum value may be greater than 1, and'
                                + ' the maximum value may be less than 42949672'
                                + '95, depending on the system.'
                                  ;
                    }
                  }
                  units byte ;
                }
                leaf out-peak {
                  description "The peak of out bandwidth. This attribute can't "
                            + "be less than out-bandwidth.This attribute must b"
                            + "e configure afterout-bandwidth.  The min, max an"
                            + "d default value of this attribute are determined"
                            + " by product."
                              ;
                  type uint32 {
                    range 1..4294967295 {
                      description 'The minimum value may be greater than 1, and'
                                + ' the maximum value may be less than 42949672'
                                + '95, depending on the system.'
                                  ;
                    }
                  }
                  units kpbs ;
                }
                leaf out-excess-burst {
                  description 'The excess-burst of out bandwidth. This attribut'
                            + 'e must be configure after out-bandwidth.  The mi'
                            + 'n, max and default value of this attribute are d'
                            + 'etermined by product.'
                              ;
                  type uint32 {
                    range 1..4294967295 {
                      description 'The minimum value may be greater than 1, and'
                                + ' the maximum value may be less than 42949672'
                                + '95, depending on the system.'
                                  ;
                    }
                  }
                  units byte ;
                }
                leaf share-tunnel {
                  description 'The tunnel of bandwidth share, The out port of s'
                            + 'hared tunnel must be the same with the out port '
                            + 'of this tunnel, and the shared tunnel must confi'
                            + 'gure bandwidth first.'
                              ;
                  type string {
                    length 1..31 ;
                  }
                }
                leaf pre-hop {
                  description 'The pre-hop of  positive in-section.'
                              ;
                  type ncd:ipv4-address {
                    pattern '([1-9]|[1-9][0-9]|1[0-9][0-9]|2[0-4][0-9]|25[0-5])'
                          + '(.([0-9]|[1-9][0-9]|1[0-9][0-9]|2[0-4][0-9]|25[0-5'
                          + '])){3}'
                            ;
                  }
                }
                leaf convergence-ratio-mode {
                  description 'The bandwidth convergence ratio mode. the conver'
                            + 'gence ratio mode can only be configurated at inh'
                            + 'erit or config mode.'
                              ;
                  type enumeration {
                    enum inherit {
                      value 1 ;
                    }
                    enum config {
                      value 2 ;
                    }
                  }
                }
                leaf convergence-ratio-value {
                  description 'The bandwidth convergence ratio value. the conve'
                            + 'rgence ratio value can only be configurated betw'
                            + 'een 1 and 100 pecent.'
                              ;
                  type uint8 {
                    range 1..100 ;
                  }
                  default 100 ;
                }
              }
              container reverse-attribute {
                description 'The configuration of reverse out-section in-sectio'
                          + 'n and.'
                            ;
                leaf inport {
                  description 'The reverse in-port.This attribute must be confi'
                            + 'gured with inlabel at the same time.'
                              ;
                  type ncd:ifname ;
                }
                leaf inlabel {
                  description 'The reverse in-label. This attribute must be con'
                            + 'figured with inport at the same time.'
                              ;
                  type uint32 {
                    range '0 | 2 | 3 | 16..1048575'
                          ;
                  }
                }
                leaf outport {
                  description 'The reverse out-port.This attribute must be conf'
                            + 'igured with outlabel at the same time.'
                              ;
                  type ncd:ifname ;
                }
                leaf outlabel {
                  description 'The reverse out-label.This attribute must be con'
                            + 'figured with outport at the same time.'
                              ;
                  type uint32 {
                    range '0 | 2 | 3 | 16..1048575'
                          ;
                  }
                }
                choice next-hop-choice {
                  description 'The reverse next-hop chocie.'
                              ;
                  case ipv4 {
                    description 'The reverse IPv4 next-hop type.'
                                ;
                    leaf next-hop {
                      description 'The reverse IPv4 next-hop address.'
                                  ;
                      type ncd:ipv4-address {
                        pattern '([1-9]|[1-9][0-9]|1[0-9][0-9]|2[0-4][0-9]|25[0'
                              + '-5])(.([0-9]|[1-9][0-9]|1[0-9][0-9]|2[0-4][0-9'
                              + ']|25[0-5])){3}'
                                ;
                      }
                    }
                  }
                  case ipv6 {
                    description 'The reverse IPv6 next-hop type.'
                                ;
                    leaf next-hop-ipv6 {
                      description 'The reverse IPv6 next-hop address.'
                                  ;
                      type ncd:ipv6-address ;
                    }
                    ncd:revise-date 2019-05-13 ;
                  }
                }
                leaf out-bandwidth {
                  description 'The reverse out bandwidth which is exclusive wit'
                            + 'h ct-bandwidth. The min, max and default value o'
                            + 'f this attribute are determined by product.'
                              ;
                  type uint32 {
                    range 0..4294967295 ;
                  }
                  units kbps ;
                  default 0 ;
                }
                leaf out-burst {
                  description 'The burst of out bandwidth. This attribute must '
                            + 'be configure after out-bandwidth.  The min, max '
                            + 'and default value of this attribute are determin'
                            + 'ed by product.'
                              ;
                  type uint32 {
                    range 1..4294967295 {
                      description 'The minimum value may be greater than 1, and'
                                + ' the maximum value may be less than 42949672'
                                + '95, depending on the system.'
                                  ;
                    }
                  }
                  units byte ;
                }
                leaf out-peak {
                  description "The peak of out bandwidth. This attribute can't "
                            + "be less than out-bandwitdth.This attribute must "
                            + "be configure after out-bandwidth.  The min, max "
                            + "and default value of this attribute are determin"
                            + "ed by product."
                              ;
                  type uint32 {
                    range 1..4294967295 {
                      description 'The minimum value may be greater than 1, and'
                                + ' the maximum value may be less than 42949672'
                                + '95, depending on the system.'
                                  ;
                    }
                  }
                  units kbps ;
                }
                leaf out-excess-burst {
                  description 'The excess-burst of out bandwidth. This attribut'
                            + 'e must be configure after out-bandwidth.  The mi'
                            + 'n, max and default value of this attribute are d'
                            + 'etermined by product.'
                              ;
                  type uint32 {
                    range 1..4294967295 {
                      description 'The minimum value may be greater than 1, and'
                                + ' the maximum value may be less than 42949672'
                                + '95, depending on the system.'
                                  ;
                    }
                  }
                  units byte ;
                }
                leaf share-tunnel {
                  description 'The tunnel of bandwidth share, The out port of s'
                            + 'hared tunnel must be the same with the out port '
                            + 'of this tunnel, and the shared tunnel must confi'
                            + 'gure bandwidth first.'
                              ;
                  type string {
                    length 1..31 ;
                  }
                }
                leaf pre-hop {
                  description 'The pre-hop of  reverse in-section.'
                              ;
                  type ncd:ipv4-address {
                    pattern '([1-9]|[1-9][0-9]|1[0-9][0-9]|2[0-4][0-9]|25[0-5])'
                          + '(.([0-9]|[1-9][0-9]|1[0-9][0-9]|2[0-4][0-9]|25[0-5'
                          + '])){3}'
                            ;
                  }
                }
                leaf convergence-ratio-mode {
                  description 'The bandwidth convergence ratio mode. the conver'
                            + 'gence ratio mode can only be configurated at inh'
                            + 'erit or config mode.'
                              ;
                  type enumeration {
                    enum inherit {
                      value 1 ;
                    }
                    enum config {
                      value 2 ;
                    }
                  }
                }
                leaf convergence-ratio-value {
                  description 'The bandwidth convergence ratio value. the conve'
                            + 'rgence ratio value can only be configurated betw'
                            + 'een 1 and 100 pecent.'
                              ;
                  type uint8 {
                    range 1..100 ;
                  }
                  default 100 ;
                }
              }
              container positive-ct-bandwidths {
                description 'The positive ct-bandwidth of static tunnel which i'
                          + 's exclusive with positive out-bandwidth and tunnel'
                          + '-rate-limit.'
                            ;
                list positive-ct-bandwidth {
                  description 'The positive ct-bandwidth list.'
                              ;
                  max-elements 131070 ;
                  key class-type ;
                  leaf class-type {
                    description 'The configuration of class type.'
                                ;
                    type uint8 {
                      range '0..7 | 255'
                            ;
                    }
                  }
                  leaf bandwidth {
                    description 'The bandwidth of class type.'
                                ;
                    type uint32 {
                      range 1..4294967295 ;
                    }
                    units kbps ;
                    mandatory true ;
                  }
                }
              }
              container reverse-ct-bandwidths {
                description 'The reverse ct-bandwidth of static tunnel which is'
                          + ' exclusive with reverse out-bandwidth and tunnel-r'
                          + 'ate-limit.'
                            ;
                list reverse-ct-bandwidth {
                  description 'The positive ct-bandwidth list.'
                              ;
                  max-elements 131070 ;
                  key class-type ;
                  leaf class-type {
                    description 'The configuration of class type.'
                                ;
                    type uint8 {
                      range '0..7 | 255'
                            ;
                    }
                  }
                  leaf bandwidth {
                    description 'The bandwidth of class type.'
                                ;
                    type uint32 {
                      range 1..4294967295 ;
                    }
                    units kbps ;
                    mandatory true ;
                  }
                }
              }
            }
          }
        }
      }
      container static-gtunnels {
        description 'The configuration of static gtunnel.'
                    ;
        presence 'configuration of static gtunnel'
                 ;
        list gtunnel {
          description 'The static GMPLS tunnel list.'
                      ;
          max-elements 131070 ;
          key name ;
          leaf name {
            description 'The static GMPLS tunnel name.'
                        ;
            type ncd:ifname ;
          }
          leaf track-name {
            description 'The track name.'
                        ;
            type string {
              length 1..31 ;
            }
            ncd:revise-date 2017-11-28 ;
          }
          leaf controller-status {
            description 'The static GMPLS tunnel controller status.'
                        ;
            type enumeration {
              enum down {
                value 0 ;
              }
              enum up {
                value 1 ;
              }
            }
            default down ;
          }
          container role-type {
            description 'The static GMPLS tunnel role and direction type.'
                        ;
            presence 'Configure tunnel role and type.'
                     ;
            leaf role {
              description 'The static GMPLS tunnel role including ingress,trans'
                        + 'it and egress.'
                          ;
              type enumeration {
                enum ingressNode {
                  value 1 ;
                }
                enum transitNode {
                  value 2 ;
                }
                enum egressNode {
                  value 3 ;
                }
              }
              mandatory true ;
            }
            leaf direction-type {
              description 'The static GMPLS tunnel direction type.'
                          ;
              type enumeration {
                enum bidirectional {
                  value 2 ;
                }
              }
              mandatory true ;
            }
          }
          container triple {
            description 'The static GMPLS tunnel triple elements.'
                        ;
            presence 'Configure tunnel triple.'
                     ;
            leaf ingress-tunnel-id {
              description 'The ingress tunnel ID,it is used to locate ingress t'
                        + 'unnel.'
                          ;
              type uint32 {
                range 1..65535 ;
              }
              mandatory true ;
            }
            leaf ingress-id {
              description 'The ingress router ID.'
                          ;
              type ncd:ipv4-address ;
              mandatory true ;
            }
            leaf egress-id {
              description 'The egress router ID.'
                          ;
              type ncd:ipv4-address ;
              mandatory true ;
            }
          }
          container bandwidth {
            description 'The static GMPLS tunnel bandwidth.'
                        ;
            presence 'Configure tunnel bandwidth.'
                     ;
            leaf bandwidth {
              description 'The static GMPLS tunnel bandwidth configuration.'
                          ;
              type uint32 {
                range 1..4294967295 {
                  description 'The minimum value may be greater than 1, and the'
                            + ' maximum value may be less than 4294967295, depe'
                            + 'nding on the system.'
                              ;
                }
              }
              units kbps ;
              mandatory true ;
            }
            leaf cbs {
              description 'The static GMPLS tunnel CBS.'
                          ;
              type uint32 {
                range 1..4294967295 {
                  description 'The minimum value may be greater than 1, and the'
                            + ' maximum value may be less than 4294967295, depe'
                            + 'nding on the system.'
                              ;
                }
              }
              units byte ;
            }
            leaf eir {
              description 'The static GMPLS tunnel EIR.'
                          ;
              type uint32 {
                range 1..4294967295 {
                  description 'The minimum value may be greater than 1, and the'
                            + ' maximum value may be less than 4294967295, depe'
                            + 'nding on the system.'
                              ;
                }
              }
              units kbps ;
            }
            leaf ebs {
              description 'The static GMPLS tunnel EBS.'
                          ;
              type uint32 {
                range 1..4294967295 {
                  description 'The minimum value may be greater than 1, and the'
                            + ' maximum value may be less than 4294967295, depe'
                            + 'nding on the system.'
                              ;
                }
              }
              units byte ;
            }
          }
          container lsps {
            description 'The configured LSP of static GMPLS tunnel.'
                        ;
            list lsp {
              description 'LSP list.'
                          ;
              max-elements 1 ;
              key lsp-id ;
              leaf lsp-id {
                description "The static GMPLS tunnel's LSP ID."
                            ;
                type uint16 {
                  range 1 ;
                }
              }
              container positive-in-attribute {
                description 'The configuration of positive in-section.'
                            ;
                presence positive-in-attribute ;
                leaf inport {
                  description 'The positive in-port.'
                              ;
                  type ncd:ifname ;
                  mandatory true ;
                }
                leaf inlabel {
                  description 'The positive in-label.'
                              ;
                  type uint32 {
                    range 1..4093 ;
                  }
                }
              }
              container positive-out-attribute {
                description 'The configuration of positive out-section.'
                            ;
                presence positive-out-attribute ;
                leaf outport {
                  description 'The positive out-port.'
                              ;
                  type ncd:ifname ;
                  mandatory true ;
                }
                leaf outlabel {
                  description 'The positive out-label.'
                              ;
                  type uint32 {
                    range 1..4093 ;
                  }
                }
              }
              container reverse-in-attribute {
                description 'The configuration of reverse in-section.'
                            ;
                presence reverse-in-attribute ;
                leaf inport {
                  description 'The reverse in-port.'
                              ;
                  type ncd:ifname ;
                  mandatory true ;
                }
                leaf inlabel {
                  description 'The reverse in-label.'
                              ;
                  type uint32 {
                    range 1..4093 ;
                  }
                }
              }
              container reverse-out-attribute {
                description 'The configuration of reverse out-section.'
                            ;
                presence reverse-out-attribute ;
                leaf outport {
                  description 'The reverse out-port.'
                              ;
                  type ncd:ifname ;
                  mandatory true ;
                }
                leaf outlabel {
                  description 'The reverse out-label.'
                              ;
                  type uint32 {
                    range 1..4093 ;
                  }
                }
              }
            }
          }
        }
        ncd:revise-date 2017-03-31 ;
      }
      container tnnl-rate-limit {
        description 'The configuration of tunnel rate limit, it is exclusive wi'
                  + 'th common bandwidth and class-type bandwidth. Only the ing'
                  + 'ress tunnel and the bidirectional egress tunnel can config'
                  + 'ure rate limit.'
                    ;
        presence 'configuration of tnnl-rate-limit'
                 ;
        list tunnel {
          description 'The tunnel rate limit list.'
                      ;
          min-elements 0 ;
          max-elements 131072 ;
          key name ;
          leaf name {
            description 'The tunnel name.'
                        ;
            type ncd:ifname ;
          }
          leaf mode {
            description 'The tunnel rate limit mode.'
                        ;
            type enumeration {
              enum blind {
                value 1 ;
              }
              enum aware {
                value 2 ;
              }
            }
            mandatory true ;
          }
          leaf cir {
            description CIR. ;
            type uint32 {
              range 0..4294967295 {
                description 'The maximum value may be less than 4294967295, dep'
                          + 'ending on the system.'
                            ;
              }
            }
            units kbps ;
            mandatory true ;
          }
          leaf cbs {
            description CBS. ;
            type uint32 {
              range 1..4294967295 {
                description 'The minimum value may be greater than 1, and the m'
                          + 'aximum value may be less than 4294967295, dependin'
                          + 'g on the system.'
                            ;
              }
            }
            units KB ;
            mandatory true ;
          }
          leaf pir {
            description "PIR.PIR can't be smaller than CIR."
                        ;
            type uint32 {
              range 1..4294967295 {
                description 'The minimum value may be greater than 1, and the m'
                          + 'aximum value may be less than 4294967295, dependin'
                          + 'g on the system.'
                            ;
              }
            }
            units kbps ;
            mandatory true ;
          }
          leaf pbs {
            description PBS. ;
            type uint32 {
              range 1..4294967295 {
                description 'The minimum value may be greater than 1, and the m'
                          + 'aximum value may be less than 4294967295, dependin'
                          + 'g on the system.'
                            ;
              }
            }
            units KB ;
            mandatory true ;
          }
        }
      }
      container te-ecmp-groups {
        description 'The configuration of ECMP-GROUP.'
                    ;
        presence 'configuration of ECMP-GROUP.'
                 ;
        list te-ecmp-group {
          description 'The ECMP-GROUP list.'
                      ;
          key group-id ;
          leaf group-id {
            description 'ECMP-GROUP id.'
                        ;
            type uint32 {
              range 1..65535 ;
            }
          }
          leaf load-share-policy {
            description 'Load-sharing policy of ECMP-GROUP.'
                        ;
            type enumeration {
              enum per-stream {
                value 1 ;
              }
              enum per-packet {
                value 2 ;
              }
              enum dlb {
                value 3 ;
              }
            }
            default per-stream ;
          }
          container te-ecmp-tunnels {
            description 'The configuration of ECMP-GROUP tunnels.'
                        ;
            list te-ecmp-tunnel {
              description 'The ECMP-GROUP tunnel list.'
                          ;
              key tunnel-id ;
              leaf tunnel-id {
                description 'Configure ECMP-GROUP tunnel.'
                            ;
                type uint32 {
                  range 1..131072 ;
                }
              }
            }
          }
          leaf minimum-member {
            description 'minimum-member of ECMP-GROUP.'
                        ;
            type uint32 {
              range 1..65535 ;
            }
            default 1 ;
          }
          leaf update-delay {
            description 'update-delay of ECMP-GROUP.'
                        ;
            type uint16 {
              range 0..1200 ;
            }
            default 0 ;
          }
        }
      }
      container affinity {
        description 'Configuration of affinity.'
                    ;
        presence 'configuration of affinity'
                 ;
        container tunnels {
          description 'The tunnel configuration of affinity function.'
                      ;
          list tunnel {
            status obsolete {
              ncd:revise-date 2015-06-04 ;
            }
            description 'The tunnel list configuration of affinity function.'
                        ;
            max-elements 131070 ;
            key 'name affinity-type bit-position'
                ;
            leaf name {
              description 'Tunnel name.'
                          ;
              type ncd:ifname ;
            }
            leaf affinity-type {
              description 'The tunnel configuration of affinity type,exclude-an'
                        + 'y(1)/include-any(2)/include-all(3).'
                          ;
              type enumeration {
                enum exclude-any {
                  value 1 ;
                  description 'Configure the exclude-any affinity.'
                              ;
                }
                enum include-any {
                  value 2 ;
                  description 'Configure the include-any affinity.'
                              ;
                }
                enum include-all {
                  value 3 ;
                  description 'Configure the include-all affinity.'
                              ;
                }
              }
            }
            leaf bit-position {
              description 'The tunnel configuration of affinity bit position.'
                          ;
              type uint8 {
                range 0..31 ;
              }
            }
          }
          list tunnel-mod-hot {
            description 'The tunnel hotstandby list configuration of affinity f'
                      + 'unction.'
                        ;
            max-elements 131070 ;
            key 'name bit-position'
                ;
            leaf name {
              description 'Tunnel name.'
                          ;
              type ncd:ifname ;
            }
            leaf affinity-type {
              description 'The tunnel hotstandby configuration of affinity type'
                        + ',exclude-any(1)/include-any(2)/include-all(3).'
                          ;
              type enumeration {
                enum exclude-any {
                  value 1 ;
                  description 'Configure the exclude-any affinity.'
                              ;
                }
                enum include-any {
                  value 2 ;
                  description 'Configure the include-any affinity.'
                              ;
                }
                enum include-all {
                  value 3 ;
                  description 'Configure the include-all affinity.'
                              ;
                }
              }
              mandatory true ;
            }
            leaf bit-position {
              description 'The tunnel hotstandby configuration of affinity bit '
                        + 'position.'
                          ;
              type uint8 {
                range 0..31 ;
              }
            }
            ncd:revise-date 2016-09-12 ;
          }
          list affinity-name-hot {
            description 'The tunnel hotstandby list configuration of affinity f'
                      + 'unction.'
                        ;
            max-elements 131070 ;
            key 'name bit-name'
                ;
            leaf name {
              description 'Tunnel name.'
                          ;
              type ncd:ifname ;
            }
            leaf affinity-type {
              description 'The tunnel hotstandby configuration of affinity type'
                        + ',exclude-any(1)/include-any(2)/include-all(3).'
                          ;
              type enumeration {
                enum exclude-any {
                  value 1 ;
                  description 'Configure the exclude-any affinity.'
                              ;
                }
                enum include-any {
                  value 2 ;
                  description 'Configure the include-any affinity.'
                              ;
                }
                enum include-all {
                  value 3 ;
                  description 'Configure the include-all affinity.'
                              ;
                }
              }
              mandatory true ;
            }
            leaf bit-name {
              description 'The tunnel hotstandby configuration of affinity bit '
                        + 'name.'
                          ;
              type string {
                length 1..32 ;
              }
            }
            ncd:revise-date 2017-11-30 ;
          }
          list tunnel-mod {
            description 'The tunnel list configuration of affinity function.'
                        ;
            max-elements 131070 ;
            key 'name bit-position'
                ;
            leaf name {
              description 'Tunnel name.'
                          ;
              type ncd:ifname ;
            }
            leaf affinity-type {
              description 'The tunnel configuration of affinity type,exclude-an'
                        + 'y(1)/include-any(2)/include-all(3).'
                          ;
              type enumeration {
                enum exclude-any {
                  value 1 ;
                  description 'Configure the exclude-any affinity.'
                              ;
                }
                enum include-any {
                  value 2 ;
                  description 'Configure the include-any affinity.'
                              ;
                }
                enum include-all {
                  value 3 ;
                  description 'Configure the include-all affinity.'
                              ;
                }
              }
              mandatory true ;
            }
            leaf bit-position {
              description 'The tunnel configuration of affinity bit position.'
                          ;
              type uint8 {
                range 0..31 ;
              }
            }
            ncd:revise-date 2015-06-04 ;
          }
          list affinity-name-master {
            description "The tunnel's master lsp list configuration of affinity"
                      + " function."
                        ;
            max-elements 131070 ;
            key 'name bit-name'
                ;
            leaf name {
              description 'Tunnel name.'
                          ;
              type ncd:ifname ;
            }
            leaf affinity-type {
              description 'The tunnel configuration of affinity type,exclude-an'
                        + 'y(1)/include-any(2)/include-all(3).'
                          ;
              type enumeration {
                enum exclude-any {
                  value 1 ;
                  description 'Configure the exclude-any affinity.'
                              ;
                }
                enum include-any {
                  value 2 ;
                  description 'Configure the include-any affinity.'
                              ;
                }
                enum include-all {
                  value 3 ;
                  description 'Configure the include-all affinity.'
                              ;
                }
              }
              mandatory true ;
            }
            leaf bit-name {
              description 'The configuration of affinity bit name.'
                          ;
              type string {
                length 1..32 ;
              }
            }
            ncd:revise-date 2017-11-30 ;
          }
          list affinity-bit-frr {
            description 'The tunnel fast-reroute list configuration of affinity'
                      + ' function.'
                        ;
            max-elements 131070 ;
            key 'name bit-position'
                ;
            leaf name {
              description 'Tunnel name.'
                          ;
              type ncd:ifname ;
            }
            leaf affinity-type {
              description 'The tunnel fast-reroute configuration of affinity ty'
                        + 'pe,exclude-any(1)/include-any(2)/include-all(3).'
                          ;
              type enumeration {
                enum exclude-any {
                  value 1 ;
                  description 'Configure the exclude-any affinity.'
                              ;
                }
                enum include-any {
                  value 2 ;
                  description 'Configure the include-any affinity.'
                              ;
                }
                enum include-all {
                  value 3 ;
                  description 'Configure the include-all affinity.'
                              ;
                }
              }
              mandatory true ;
            }
            leaf bit-position {
              description 'The tunnel fast-reroute configuration of affinity bi'
                        + 't position.'
                          ;
              type uint8 {
                range 0..31 ;
              }
            }
            ncd:revise-date 2018-02-11 ;
          }
          list affinity-name-frr {
            description 'The tunnel fast-reroute list configuration of affinity'
                      + ' function.'
                        ;
            max-elements 131070 ;
            key 'name bit-name'
                ;
            leaf name {
              description 'Tunnel name.'
                          ;
              type ncd:ifname ;
            }
            leaf affinity-type {
              description 'The tunnel fast-reroute configuration of affinity ty'
                        + 'pe,exclude-any(1)/include-any(2)/include-all(3).'
                          ;
              type enumeration {
                enum exclude-any {
                  value 1 ;
                  description 'Configure the exclude-any affinity.'
                              ;
                }
                enum include-any {
                  value 2 ;
                  description 'Configure the include-any affinity.'
                              ;
                }
                enum include-all {
                  value 3 ;
                  description 'Configure the include-all affinity.'
                              ;
                }
              }
              mandatory true ;
            }
            leaf bit-name {
              description 'The tunnel fast-reroute configuration of affinity bi'
                        + 't name.'
                          ;
              type string {
                length 1..32 ;
              }
            }
            ncd:revise-date 2018-02-11 ;
          }
        }
        container interfaces {
          description 'The TE interface configuration of affinity function.'
                      ;
          list interface {
            description 'The TE interface list configuration of affinity functi'
                      + 'on.'
                        ;
            max-elements 8160 ;
            key 'name bit-position'
                ;
            leaf name {
              description 'Interface name.'
                          ;
              type ncd:ifname ;
            }
            leaf bit-position {
              description 'The TE interface configuration of affinity bit posit'
                        + 'ion.'
                          ;
              type uint8 {
                range 0..31 ;
              }
            }
          }
          list affinity-name-interface {
            description 'The TE interface list configuration of affinity functi'
                      + 'on.'
                        ;
            max-elements 8160 ;
            key 'name bit-name'
                ;
            leaf name {
              description 'Interface name.'
                          ;
              type ncd:ifname ;
            }
            leaf bit-name {
              description 'The TE interface configuration of affinity bit name.'
                          ;
              type string {
                length 1..32 ;
              }
            }
            ncd:revise-date 2017-11-30 ;
          }
        }
        container affinity-maps {
          description 'Configuration of affinity map'
                      ;
          presence 'configuration of affinity-map'
                   ;
          list affinity-map {
            description 'The list configuration of affinity map.'
                        ;
            max-elements 32 ;
            key name ;
            leaf name {
              description 'Affinity attribute name'
                          ;
              type string {
                length 1..32 ;
              }
            }
            leaf bit-position {
              description 'Affinity bit position.'
                          ;
              type uint8 {
                range 0..31 ;
              }
              mandatory true ;
            }
          }
          ncd:revise-date 2017-11-30 ;
        }
      }
      container te-trunk {
        description 'The configuration of te-trunk.'
                    ;
        presence 'configuration of te-trunk'
                 ;
        list interface {
          description 'Interface list.'
                      ;
          max-elements 255 ;
          key name ;
          leaf name {
            description 'The name of this interface.'
                        ;
            type ncd:ifname ;
          }
        }
      }
      container gs-config {
        description 'Configuration of graceful-shutdown.'
                    ;
        presence 'graceful-shutdown configuration'
                 ;
        container global {
          description 'graceful-shutdown global configuration.'
                      ;
          presence 'graceful-shutdown global configuration'
                   ;
          leaf enable {
            description 'The global switch of graceful-shutdown.'
                        ;
            type empty ;
          }
        }
        container interfaces {
          description 'graceful-shutdown interface configuration.'
                      ;
          presence 'graceful-shutdown interface configuration'
                   ;
          list interface {
            description 'The interface graceful-shutdown list.'
                        ;
            max-elements 255 ;
            key name ;
            leaf name {
              description 'interface name.'
                          ;
              type ncd:ifname ;
            }
            leaf enable {
              description 'The interface graceful-shutdown enable.'
                          ;
              type empty ;
            }
          }
        }
      }
      container tnnl-policy-class {
        description 'The configuration of tunnel policy class. Only the ingress'
                  + ' tunnel and the bidirectional egress tunnel can configure '
                  + 'policy class.'
                    ;
        presence 'configuration of tnnl-policy-class'
                 ;
        list classes {
          description 'The  value of  policy-class(<0-7> and 255).'+"\n"
                    + 'The  default value of  policy-class is 255.
            '
                    + '      '+"\n"
                    + 'The policy-class range of 0 and 7 and 255 cannot be exis'
                    + 'ted the same time.'+"\n"
                    + 'For example 1,if we set the value  0 and 255 at the same'
                    + ' time(255 behind),the final value is 255.'+"\n"
                    + 'For example 2,if we set the value  255 and 0 at the same'
                    + ' time(0 behind ),the final value is 0.'+"\n"
                    + 'For example 3,if we set the value  0,255,1 and 3 at the '
                    + 'same time the final value is 1 and 3.'
                      ;
          key 'tunnel-name class'
              ;
          leaf tunnel-name {
            description 'The key is consist of the value of policy class and th'
                      + 'e tunnel name.'
                        ;
            type ncd:ifname ;
          }
          leaf class {
            description 'The key is consist of the value of policy class and th'
                      + 'e tunnel name.'
                        ;
            type uint8 {
              range '0..7 | 255'
                    ;
            }
          }
          ncd:revise-date 2015-06-03 ;
        }
        ncd:revise-date 2015-03-27 ;
      }
      container gtunnel-groups {
        description 'The configuration of GMPLS tunnel groups.'
                    ;
        list gtunnel-group {
          description 'The configuration of GMPLS tunnel group.'
                      ;
          max-elements 512 ;
          key group-id ;
          leaf group-id {
            description 'GMPLS tunnel group ID.'
                        ;
            type uint32 {
              range 1..4294967295 {
                description 'GMPLS tunnel group ID.'
                            ;
              }
            }
            mandatory true ;
          }
          leaf load-share-policy {
            description 'Load-sharing policy of GMPLS tunnel group.'
                        ;
            type enumeration {
              enum per-stream {
                value 0 ;
                description Per-stream. ;
              }
              enum per-packet {
                value 1 ;
                description Per-packet. ;
              }
            }
            default per-stream ;
          }
          leaf wtr {
            description 'Wait to restore time of GMPLS tunnel group.'
                        ;
            type uint8 {
              range 0..12 {
                description 'Wait to restore time.'
                            ;
              }
            }
            default 5 ;
          }
          leaf min-member-to-activate {
            description 'Minmum working member to activate the GMPLS tunnel gro'
                      + 'up.'
                        ;
            type uint32 {
              range 1..4294967295 {
                description 'Minmum member to activate the gtunnel-group.'
                            ;
              }
            }
            default 1 ;
          }
          leaf min-bandwidth-to-activate {
            description 'Minmum bandwidth to activate the GMPLS tunnel group.'
                        ;
            type uint32 {
              range 0..4294967295 {
                description 'Minmum bandwidth to activate the gtunnel-group.'
                            ;
              }
            }
            units kbps ;
            default 0 ;
          }
          container group-interface {
            description 'Bind GMPLS tunnel group interface.'
                        ;
            presence 'Bind GMPLS tunnel group interface.'
                     ;
            leaf interface-name {
              description 'GMPLS tunnel group interface name.'
                          ;
              type ncd:ifname ;
              mandatory true ;
            }
          }
          container members {
            description "The configuration of GMPLS tunnel group's member inter"
                      + "faces."
                        ;
            presence 'GMPLS tunnel interfaces.'
                     ;
            list member {
              description "Configure GMPLS tunnel group's member interface."
                          ;
              key interface-name ;
              leaf interface-name {
                description 'GMPLS tunnel interface name.'
                            ;
                type ncd:ifname ;
                mandatory true ;
              }
              leaf role {
                description 'Configure role of GMPLS tunnel interface.'
                            ;
                type enumeration {
                  enum working {
                    value 1 ;
                    description 'Working role.'
                                ;
                  }
                  enum protection {
                    value 2 ;
                    description 'Protection role.'
                                ;
                  }
                }
                mandatory true ;
              }
            }
          }
        }
        ncd:revise-date 2016-07-22 ;
      }
    }
  }
  container state {
    config false ;
    description 'The branch of dynamic data model.'
                ;
    container mpls-te {
      description 'The state of MPLS-TE.'
                  ;
      container dynamic-tunnel {
        description 'The dynamic tunnel information.'
                    ;
        list tunnel {
          description 'The dynamic tunnel list.'
                      ;
          key tunnel-id ;
          leaf tunnel-id {
            description 'The tunnel ID.'
                        ;
            type uint16 ;
          }
          leaf in-use-pathoption {
            description 'The in use path option.'
                        ;
            type uint32 ;
          }
          leaf oper-status {
            description 'The operation status of tunnel.'
                        ;
            type enumeration {
              enum UNKNOWN {
                value 0 ;
              }
              enum UP {
                value 1 ;
              }
              enum DOWN {
                value 2 ;
              }
              enum WTR {
                value 4 ;
              }
            }
          }
          leaf inuselsp-chop-table-index {
            description 'This attribute is used to record chop table index of t'
                      + 'his tunnel.'
                        ;
            type uint32 ;
          }
          leaf inuselsp-arhop-table-index {
            description 'This attribute is used to record arhop table index of '
                      + 'this tunnel.'
                        ;
            type uint32 ;
          }
          leaf hotlsp-chop-table-index {
            description 'This attribute is used to record chop table index of t'
                      + 'his tunnel.'
                        ;
            type uint32 ;
          }
          leaf hotlsp-arhop-table-index {
            description 'This attribute is used to record arhop table index of '
                      + 'this tunnel.'
                        ;
            type uint32 ;
          }
          leaf wtrlsp-chop-table-index {
            description 'This attribute is used to record chop table index of t'
                      + 'his tunnel.'
                        ;
            type uint32 ;
          }
          leaf wtrlsp-arhop-table-index {
            description 'This attribute is used to record arhop table index of '
                      + 'this tunnel.'
                        ;
            type uint32 ;
          }
          leaf hsb-status {
            description 'The hsb status of tunnel.'
                        ;
            type enumeration {
              enum UNKNOWN {
                value 0 ;
              }
              enum READY {
                value 1 ;
              }
              enum ACTIVE {
                value 2 ;
              }
              enum NONE {
                value 254 ;
              }
            }
          }
          leaf inuse-lsp-id {
            description 'The lsp identifier inuse.'
                        ;
            type uint16 ;
          }
          leaf hsb-lsp-id {
            description 'The lsp identifier of hsb.'
                        ;
            type uint16 ;
          }
          leaf wtr-lsp-id {
            description 'The lsp identifier of wtr.'
                        ;
            type uint16 ;
          }
          leaf ingress-id {
            description 'The ingress LSR ID.'
                        ;
            type ncd:ipv4-address ;
          }
          leaf egress-id {
            description 'The egress LSR ID.'
                        ;
            type ncd:ipv4-address ;
          }
          leaf bandwidth-utilization {
            description 'The bandwidth utilization of dynamic tunnel.'
                        ;
            type uint32 ;
            default 4294967295 ;
            ncd:revise-date 2015-11-03 ;
          }
          leaf bandwidth-utilization-in {
            description 'The bandwidth utilization of dynamic tunnel at in dire'
                      + 'ction.'
                        ;
            type uint32 ;
            default 4294967295 ;
            ncd:revise-date 2015-11-03 ;
          }
        }
        container tunnel-chop {
          description 'The tunnel ERO,it is the path-compute result of ROUTE.'
                      ;
          list ero {
            description 'The tunnel ERO list.'
                        ;
            key 'hop-table-index hop-index'
                ;
            leaf hop-table-index {
              description 'The table index of chop.'
                          ;
              type uint32 ;
            }
            leaf hop-index {
              description 'The index of ERO hop.'
                          ;
              type uint32 ;
            }
            leaf addr-type {
              description 'The hop address type.'
                          ;
              type enumeration {
                enum IPV4 {
                  value 1 ;
                }
                enum IPV6 {
                  value 2 ;
                }
                enum AS_NUM {
                  value 3 ;
                }
                enum UNNUM_IF {
                  value 4 ;
                }
                enum LSP_ID {
                  value 5 ;
                }
                enum UNNUM_V6 {
                  value 6 ;
                }
              }
            }
            leaf ip-addr {
              description 'The ip address of hop.'
                          ;
              type ncd:ipv4-address ;
              default 0.0.0.0 ;
            }
            leaf prefix-len {
              description 'The prefix length of ip address.'
                          ;
              type uint8 {
                range 0..64 ;
              }
              default 0 ;
            }
            leaf as-number {
              description 'AS number.'
                          ;
              type uint16 ;
              default 0 ;
            }
            leaf addr-unnum {
              description 'The unnumbered ID.'
                          ;
              type uint32 ;
              default 0 ;
            }
            leaf hop-type {
              description 'The hop type.'
                          ;
              type enumeration {
                enum strictly {
                  value 1 ;
                }
                enum loose {
                  value 2 ;
                }
              }
            }
          }
        }
        container tnnl-ar-hop {
          description 'The tunnel RRO hop,It records the bypassed path informat'
                    + 'ion of tunnel.'
                      ;
          list rro {
            description 'The tunnel RRO hop list.'
                        ;
            key 'hop-table-index hop-index'
                ;
            leaf hop-table-index {
              description 'The table index of arhop.'
                          ;
              type uint32 ;
            }
            leaf hop-index {
              description 'The hop index of RRO.'
                          ;
              type uint32 ;
            }
            leaf lsr-id {
              description 'The router id.'
                          ;
              type ncd:ipv4-address ;
            }
            leaf if-ipaddr {
              description 'The in interface address of tunnel.'
                          ;
              type ncd:ipv4-address ;
            }
            leaf if-ipmask {
              description 'The in interface mask of tunnel.'
                          ;
              type uint32 ;
            }
            leaf path-inlabel {
              description 'The in label of the tunnel path.'
                          ;
              type uint32 ;
            }
            leaf path-outlabel {
              description 'The out label of the tunnel path.'
                          ;
              type uint32 ;
            }
            leaf resv-inlabel {
              description 'The in label of the tunnel resv.'
                          ;
              type uint32 ;
            }
            leaf resv-outlabel {
              description 'The out label of the tunnel resv.'
                          ;
              type uint32 ;
            }
          }
        }
      }
      container remote-tunnel {
        description 'The remote tunnel,it is related with ingress tunnel.'
                    ;
        list tunnel {
          description 'The remote tunnel list.'
                      ;
          key 'local-tunnel-id lsp-id ingress-id egress-id'
              ;
          leaf local-tunnel-id {
            description 'The local tunnel ID of remote tunnel.'
                        ;
            type uint16 ;
          }
          leaf lsp-id {
            description 'The lsp id of remote tunnel.'
                        ;
            type uint16 ;
          }
          leaf ingress-id {
            description 'The ingress LSR ID.'
                        ;
            type ncd:ipv4-address ;
          }
          leaf egress-id {
            description 'The egress LSR ID.'
                        ;
            type ncd:ipv4-address ;
          }
          leaf in-interface {
            description 'The in interface of remote tunnel.'
                        ;
            type string {
              length 1..31 ;
            }
            default unknown ;
          }
          leaf in-label {
            description 'The in label of remote tunnel.'
                        ;
            type uint32 ;
            default 4294967295 ;
          }
          leaf out-interface {
            description 'The out interface of remote tunnel.'
                        ;
            type string {
              length 1..31 ;
            }
            default unknown ;
          }
          leaf out-label {
            description 'The out label of remote tunnel.'
                        ;
            type uint32 {
              range 0..4294967295 ;
            }
            default 4294967295 ;
          }
          leaf oper-status {
            description 'The operation status of remote tunnel.'
                        ;
            type enumeration {
              enum down {
                value 0 ;
              }
              enum up {
                value 1 ;
              }
            }
            default down ;
          }
          ncd:select 'local-tunnel-id lsp-id ingress-id egress-id'
                     ;
        }
      }
      container static-tunnel {
        description 'The state data of static tunnel.'
                    ;
        list tunnel {
          description 'The static tunnel list.'
                      ;
          key tunnel-id ;
          leaf tunnel-id {
            description 'The tunnel ID.'
                        ;
            type uint32 ;
          }
          leaf oper-status {
            description 'The operation status of tunnel.'
                        ;
            type enumeration {
              enum down {
                value 0 ;
              }
              enum up {
                value 1 ;
              }
            }
            default down ;
          }
          leaf admin-status {
            description 'The admin status of tunnel.'
                        ;
            type enumeration {
              enum down {
                value 0 ;
              }
              enum up {
                value 1 ;
              }
            }
            default down ;
          }
          leaf associated-status {
            description 'The associated status of static tunnel.'
                        ;
            type enumeration {
              enum disabled {
                value 1 ;
              }
              enum unbond {
                value 2 ;
              }
              enum bond {
                value 3 ;
              }
            }
            default disabled ;
          }
          leaf sample-bandwidth {
            description 'The sampled bandwidth of static tunnel.'
                        ;
            type uint32 ;
            units kbps ;
            default 0 ;
          }
          leaf bandwidth-utilization {
            description 'The bandwidth utilization of static tunnel.'
                        ;
            type uint32 ;
            default 4294967295 ;
            ncd:revise-date 2015-05-20 ;
          }
          leaf bandwidth-utilization-in {
            description 'The bandwidth utilization of static tunnel at in direc'
                      + 'tion.'
                        ;
            type uint32 ;
            default 4294967295 ;
            ncd:revise-date 2015-11-03 ;
          }
        }
      }
      container egress-tunnel {
        description 'The egress tunnel information.'
                    ;
        list tunnel {
          description 'The egress tunnel list.'
                      ;
          key 'tunnel-id ingress-id egress-id lsp-id'
              ;
          leaf tunnel-id {
            description 'The tunnel ID of egress tunnel.'
                        ;
            type uint16 ;
          }
          leaf ingress-id {
            description 'The ingress LSR ID.'
                        ;
            type ncd:ipv4-address ;
          }
          leaf egress-id {
            description 'The egress LSR ID.'
                        ;
            type ncd:ipv4-address ;
          }
          leaf lsp-id {
            description 'The lsp id of remote tunnel.'
                        ;
            type uint16 ;
          }
          leaf lsp-arhop-index {
            description 'The arhop index of arhop.'
                        ;
            type uint32 ;
          }
        }
      }
      container pathoption-addition {
        description 'The additional information of pathoption.'
                    ;
        list pathoption {
          description 'The list of pathoption.'
                      ;
          key 'tunnel-id option-id'
              ;
          leaf tunnel-id {
            description 'The identifier of tunnel.'
                        ;
            type uint16 ;
          }
          leaf option-id {
            description 'The option identifier of tunnel.'
                        ;
            type uint8 ;
          }
          leaf last-time-rst {
            description 'The result of creat the lsp.'
                        ;
            type uint8 ;
          }
          leaf lsp-id {
            description 'The lsp id of successed creat.'
                        ;
            type uint16 ;
          }
          leaf errcode {
            description 'The type of wrong.'
                        ;
            type uint16 ;
          }
          leaf errvalue {
            description 'The value of last failed creat.'
                        ;
            type uint16 ;
          }
          leaf last-try-time {
            description 'The time of creat the lsp.'
                        ;
            type ncd:datetime ;
          }
          leaf fail-node-ipaddr {
            description 'The wrong value of the failed creat.'
                        ;
            type ncd:ipv4-address ;
          }
        }
      }
      container history-path {
        description 'The information of history-path.'
                    ;
        list hispath {
          description 'The information of history-path.'
                      ;
          key 'tnnlid lspid hopindex'
              ;
          leaf tnnlid {
            description 'tunnel id.'
                        ;
            type uint16 ;
          }
          leaf lspid {
            description 'The lspid of tunnel.'
                        ;
            type uint16 ;
          }
          leaf hopindex {
            description hopindex. ;
            type uint16 ;
          }
          leaf lsprole {
            description "The lsp role of tunnel,it's behalf of master while the"
                      + " value is 1 ,it's behalf of backup while the value is "
                      + "2 ."
                        ;
            type uint8 ;
          }
          leaf pathoption {
            description 'The pathoption of tunnel.'
                        ;
            type uint8 ;
          }
          leaf hishopaddr {
            description 'The address of historypath.'
                        ;
            type ncd:ipv4-address ;
          }
        }
        ncd:revise-date 2015-12-28 ;
      }
      container frr-protect {
        description 'The information of frr-protect.'
                    ;
        list frr-protect {
          status obsolete {
            ncd:revise-date 2018-08-08 ;
          }
          description 'The information of frr-protect.'
                      ;
          key 'intfName priTnnlId priLspId priIgrId priEgrId priPreHop priExtTn'
            + 'nlId'
              ;
          leaf intfName {
            description 'The interface name of protected.'
                        ;
            type string ;
          }
          leaf priTnnlId {
            description 'The tunnel id of primary tunnel.'
                        ;
            type uint32 ;
          }
          leaf priLspId {
            description 'The lsp id of primary tunnel.'
                        ;
            type uint16 ;
          }
          leaf priIgrId {
            description 'The ingress id of primary tunnel.'
                        ;
            type ncd:ipv4-address ;
          }
          leaf priEgrId {
            description 'The egress id of primary tunnel.'
                        ;
            type ncd:ipv4-address ;
          }
          leaf priPreHop {
            description 'The phop id of primary tunnel.'
                        ;
            type ncd:ipv4-address ;
          }
          leaf priExtTnnlId {
            description 'The extunnel id of primary tunnel.'
                        ;
            type ncd:ipv4-address ;
          }
          leaf bkTnnlId {
            description 'The tunnel id of backup tunnel.'
                        ;
            type uint32 ;
          }
          leaf bkLspId {
            description 'The lsp id of backup tunnel.'
                        ;
            type uint16 ;
          }
          leaf bkIgrId {
            description 'The ingress id of backup tunnel.'
                        ;
            type ncd:ipv4-address ;
          }
          leaf bkEgrId {
            description 'The egress id of backup tunnel.'
                        ;
            type ncd:ipv4-address ;
          }
          leaf bkPreHop {
            description 'The prev hop of backup tunnel.'
                        ;
            type ncd:ipv4-address ;
          }
          leaf bkExtTnnlId {
            description 'The extunnel id of backup tunnel.'
                        ;
            type ncd:ipv4-address ;
          }
          leaf frrType {
            description 'The type of frr protect.'
                        ;
            type enumeration {
              enum Manual {
                value 0 ;
              }
              enum Auto {
                value 1 ;
              }
            }
          }
          leaf teTunnelProtType {
            description 'The type of protect tunnel.'
                        ;
            type enumeration {
              enum NONE {
                value 0 ;
              }
              enum HSB {
                value 1 ;
              }
              enum FRR {
                value 2 ;
              }
            }
          }
          leaf workStatus {
            description 'The status in work.'
                        ;
            type enumeration {
              enum Ready {
                value 1 ;
              }
              enum Active {
                value 2 ;
              }
            }
          }
          leaf priDirect {
            description binary-tunnel. ;
            type uint8 ;
          }
          leaf bkDirect {
            description binary-tunnel. ;
            type uint8 ;
          }
        }
        list frr-protect-new {
          description 'The information of frr-protect.'
                      ;
          key 'intfName priTnnlId priLspId priIgrId priEgrId priPreHop priExtTn'
            + 'nlId teTunnelProtType'
              ;
          leaf intfName {
            description 'The interface name of protected.'
                        ;
            type string ;
          }
          leaf priTnnlId {
            description 'The tunnel id of primary tunnel.'
                        ;
            type uint32 ;
          }
          leaf priLspId {
            description 'The lsp id of primary tunnel.'
                        ;
            type uint16 ;
          }
          leaf priIgrId {
            description 'The ingress id of primary tunnel.'
                        ;
            type ncd:ipv4-address ;
          }
          leaf priEgrId {
            description 'The egress id of primary tunnel.'
                        ;
            type ncd:ipv4-address ;
          }
          leaf priPreHop {
            description 'The phop id of primary tunnel.'
                        ;
            type ncd:ipv4-address ;
          }
          leaf priExtTnnlId {
            description 'The extunnel id of primary tunnel.'
                        ;
            type ncd:ipv4-address ;
          }
          leaf bkTnnlId {
            description 'The tunnel id of backup tunnel.'
                        ;
            type uint32 ;
          }
          leaf bkLspId {
            description 'The lsp id of backup tunnel.'
                        ;
            type uint16 ;
          }
          leaf bkIgrId {
            description 'The ingress id of backup tunnel.'
                        ;
            type ncd:ipv4-address ;
          }
          leaf bkEgrId {
            description 'The egress id of backup tunnel.'
                        ;
            type ncd:ipv4-address ;
          }
          leaf bkPreHop {
            description 'The prev hop of backup tunnel.'
                        ;
            type ncd:ipv4-address ;
          }
          leaf bkExtTnnlId {
            description 'The extunnel id of backup tunnel.'
                        ;
            type ncd:ipv4-address ;
          }
          leaf frrType {
            description 'The type of frr protect.'
                        ;
            type enumeration {
              enum Manual {
                value 0 ;
              }
              enum Auto {
                value 1 ;
              }
            }
          }
          leaf teTunnelProtType {
            description 'The type of protect tunnel.'
                        ;
            type enumeration {
              enum NONE {
                value 0 ;
              }
              enum HSB {
                value 1 ;
              }
              enum FRR {
                value 2 ;
              }
              enum SECOND_FRR {
                value 3 ;
              }
            }
          }
          leaf workStatus {
            description 'The status in work.'
                        ;
            type enumeration {
              enum Ready {
                value 1 ;
              }
              enum Active {
                value 2 ;
              }
            }
          }
          leaf priDirect {
            description binary-tunnel. ;
            type uint8 ;
          }
          leaf bkDirect {
            description binary-tunnel. ;
            type uint8 ;
          }
          ncd:select intfName ;
          ncd:select 'intfName priTnnlId'
                     ;
          ncd:select 'intfName priTnnlId priLspId priIgrId priEgrId priPreHop p'
                   + 'riExtTnnlId teTunnelProtType'
                     ;
          ncd:revise-date 2018-08-08 ;
        }
        ncd:revise-date 2015-12-28 ;
      }
      container local-acc-dynamic-tnnl {
        status deprecated ;
        description 'The local access dynamic tunnel information.'+"\n"
                  + 'Use restrictions:The container only suits for the tunnel I'
                  + 'D in range of 1-65535.'+"\n"
                  + 'Recommend container:local-acc-dynamic-tnnl-new.It suits fo'
                  + 'r the tunnel ID in range of 1-4294967295.'
                    ;
        list tunnel {
          status deprecated ;
          description 'The access dynamic tunnel list.'
                      ;
          key tunnel-id ;
          leaf tunnel-id {
            description 'The tunnel ID of local access tunnel.'
                        ;
            type uint16 ;
          }
          leaf acc-bandwidth-utilization {
            description 'The bandwidth utilization of access dynamic tunnel.'
                        ;
            type uint32 ;
            default 4294967295 ;
          }
          leaf acc-bandwidth-utilization-in {
            description 'The bandwidth utilization of access dynamic tunnel at '
                      + 'in direction.'
                        ;
            type uint32 ;
            default 4294967295 ;
          }
        }
        ncd:revise-date 2015-11-03 ;
      }
      container gtunnel-groups {
        description 'State information of GMPLS tunnel groups.'
                    ;
        list gtunnel-group {
          description 'State information of GMPLS tunnel group.'
                      ;
          key group-id ;
          leaf group-id {
            description 'GMPLS tunnel group ID.'
                        ;
            type uint32 {
              range 1..4294967295 {
                description 'GMPLS tunnel group ID.'
                            ;
              }
            }
          }
        }
        container work-members {
          description 'State information of working members.'
                      ;
          presence 'Working GMPLS tunnel interfaces.'
                   ;
          list work-member {
            description 'State information of working members.'
                        ;
            key 'group-id interface-name'
                ;
            leaf group-id {
              description 'GMPLS tunnel group ID.'
                          ;
              type uint32 {
                range 1..4294967295 {
                  description 'GMPLS tunnel group ID.'
                              ;
                }
              }
            }
            leaf interface-name {
              description 'GMPLS tunnel interface name.'
                          ;
              type ncd:ifname ;
            }
            leaf protect-group-id {
              description 'GMPLS protect group ID.'
                          ;
              type uint32 {
                range 1..4294967295 {
                  description 'Protect group ID.'
                              ;
                }
              }
            }
            leaf switch-state {
              description 'Switch state of GMPLS protect group.'
                          ;
              type enumeration {
                enum unknown {
                  value 0 ;
                  description 'Invalid state.'
                              ;
                }
                enum switch {
                  value 1 ;
                  description 'Switch to protection entity.'
                              ;
                }
                enum unswitch {
                  value 2 ;
                  description 'Working entity is active.'
                              ;
                }
              }
            }
          }
        }
        ncd:revise-date 2016-07-22 ;
      }
      container sr-tunnel {
        status obsolete {
          ncd:revise-date 2017-09-14 ;
        }
        description 'The SR tunnel information.'
                    ;
        list tunnel {
          description 'The SR tunnel list.'
                      ;
          key tunnel-id ;
          leaf tunnel-id {
            description 'The tunnel ID.'
                        ;
            type uint16 ;
          }
          leaf ingress-id {
            description 'The ingress LSR ID.'
                        ;
            type ncd:ipv4-address ;
          }
          leaf egress-id {
            description 'The egress LSR ID.'
                        ;
            type ncd:ipv4-address ;
          }
          leaf oper-status {
            description 'The operation status of tunnel.'
                        ;
            type enumeration {
              enum unknown {
                value 0 ;
              }
              enum up {
                value 1 ;
              }
              enum down {
                value 2 ;
              }
              enum WTR {
                value 4 ;
              }
            }
          }
          leaf master-lsp-id {
            description 'The master lsp identifier.'
                        ;
            type uint16 ;
          }
          leaf slave-lsp-id {
            description 'The lsp identifier of slave.'
                        ;
            type uint16 ;
          }
          leaf hsb-status {
            description 'The hsb status of tunnel.'
                        ;
            type enumeration {
              enum none {
                value 0 ;
              }
              enum ready {
                value 1 ;
              }
              enum active {
                value 2 ;
              }
            }
          }
          leaf master-splice-label {
            description 'The master splice label.'
                        ;
            type uint32 ;
          }
          leaf slave-splice-label {
            description 'The splice label of slave.'
                        ;
            type uint32 ;
          }
        }
        container tunnel-sr-path {
          description 'The path of segment-routing tunnel LSP.'
                      ;
          list sr-path-hop {
            description 'The hop of segment routing path.'
                        ;
            key 'tunnel-id lsp-role hop-index'
                ;
            leaf tunnel-id {
              description 'The tunnel ID.'
                          ;
              type uint16 ;
            }
            leaf lsp-role {
              description "The lsp role of tunnel,it's behalf of master while t"
                        + "he value is 1 ,it's behalf of backup while the value"
                        + " is 2."
                          ;
              type enumeration {
                enum master {
                  value 1 ;
                }
                enum slave {
                  value 2 ;
                }
              }
            }
            leaf hop-index {
              description 'The index of sr-path hop.'
                          ;
              type uint16 ;
            }
            leaf lsp-id {
              description 'The lsp identifier.'
                          ;
              type uint16 ;
            }
            leaf sid-type {
              description 'The sid type.'
                          ;
              type enumeration {
                enum default {
                  value 0 ;
                }
                enum node-id-v4 {
                  value 1 ;
                }
                enum node-id-v6 {
                  value 2 ;
                }
                enum adj-id-v4 {
                  value 3 ;
                }
                enum adj-id-v6 {
                  value 4 ;
                }
                enum unnum-adj-id-v4 {
                  value 5 ;
                }
              }
            }
            leaf sid-val {
              description 'The sid value.'
                          ;
              type uint32 ;
            }
            leaf node-ip {
              description 'The node IP.'
                          ;
              type ncd:ipv4-address ;
            }
            leaf adj-local-rid {
              description 'The local router id of adjacency.'
                          ;
              type ncd:ipv4-address ;
            }
            leaf adj-local-ip {
              description 'The local ip of adjacency.'
                          ;
              type ncd:ipv4-address ;
            }
            leaf adj-peer-rid {
              description 'The peer router id of adjacency.'
                          ;
              type ncd:ipv4-address ;
            }
            leaf adj-peer-ip {
              description 'The peer ip of adjacency.'
                          ;
              type ncd:ipv4-address ;
            }
          }
        }
        ncd:revise-date 2017-04-25 ;
      }
      container local-acc-dynamic-tnnl-new {
        description 'The local access dynamic tunnel information.'
                    ;
        list tunnel {
          description 'The access dynamic tunnel list.'
                      ;
          key tunnel-id ;
          leaf tunnel-id {
            description 'The tunnel ID of local access tunnel.'
                        ;
            type uint32 ;
          }
          leaf acc-bandwidth-utilization {
            description 'The bandwidth utilization of access dynamic tunnel.'
                        ;
            type uint32 ;
          }
          leaf acc-bandwidth-utilization-in {
            description 'The bandwidth utilization of access dynamic tunnel at '
                      + 'in direction.'
                        ;
            type uint32 ;
          }
        }
        ncd:revise-date 2019-12-30 ;
      }
    }
  }
  container operation {
    config false ;
    description 'Operation model.'
                ;
    container manual-reopt {
      description 'Operation about manual-reopt.'
                  ;
      leaf tunnel-id {
        description 'Specify the tunnel(s) to be reoptimized.'
                    ;
        type uint32 {
          range 1..65535 ;
        }
      }
      leaf all {
        description 'Configure all tunnels to be reoptimized.'
                    ;
        type empty ;
      }
    }
    container clear {
      description 'Operation about clear.'
                  ;
      container te {
        description 'Operation about te tunnel clear.'
                    ;
        choice tunnel-type {
          description 'Tunnel Selection Type.'
                      ;
          case tunnel {
            description 'Te p2p and sr tunnel'
                        ;
            leaf tunnel-id {
              description 'Specify the tunnel to be cleared.'
                          ;
              type uint32 ;
            }
          }
          case mtunnel {
            description 'Te p2mp tunnel'
                        ;
            leaf mtunnel-id {
              description 'Specify the mtunnel to be cleared.'
                          ;
              type uint32 ;
            }
          }
        }
      }
      ncd:revise-date 2019-04-23 ;
    }
    ncd:revise-date 2015-09-11 ;
  }
  notification dynamic-tunnel {
    description 'The dynamic tunnel information.'
                ;
    list tunnel {
      config false ;
      description 'The dynamic tunnel list.'
                  ;
      key tunnel-id ;
      leaf tunnel-id {
        description 'The tunnel ID.'
                    ;
        type uint16 ;
      }
      leaf in-use-pathoption {
        description 'The in use path option.'
                    ;
        type uint32 ;
      }
      leaf oper-status {
        description 'The operation status of tunnel.'
                    ;
        type enumeration {
          enum UNKNOWN {
            value 0 ;
          }
          enum UP {
            value 1 ;
          }
          enum DOWN {
            value 2 ;
          }
          enum WTR {
            value 4 ;
          }
        }
      }
      leaf inuselsp-chop-table-index {
        description 'This attribute is used to record chop table index of this '
                  + 'tunnel.'
                    ;
        type uint32 ;
      }
      leaf inuselsp-arhop-table-index {
        description 'This attribute is used to record arhop table index of this'
                  + ' tunnel.'
                    ;
        type uint32 ;
      }
      leaf hotlsp-chop-table-index {
        description 'This attribute is used to record chop table index of this '
                  + 'tunnel.'
                    ;
        type uint32 ;
      }
      leaf hotlsp-arhop-table-index {
        description 'This attribute is used to record arhop table index of this'
                  + ' tunnel.'
                    ;
        type uint32 ;
      }
      leaf wtrlsp-chop-table-index {
        description 'This attribute is used to record chop table index of this '
                  + 'tunnel.'
                    ;
        type uint32 ;
      }
      leaf wtrlsp-arhop-table-index {
        description 'This attribute is used to record arhop table index of this'
                  + ' tunnel.'
                    ;
        type uint32 ;
      }
      leaf hsb-status {
        description 'The hsb status of tunnel.'
                    ;
        type enumeration {
          enum UNKNOWN {
            value 0 ;
          }
          enum READY {
            value 1 ;
          }
          enum ACTIVE {
            value 2 ;
          }
          enum NONE {
            value 254 ;
          }
        }
      }
      leaf inuse-lsp-id {
        description 'The lsp identifier inuse.'
                    ;
        type uint16 ;
      }
      leaf hsb-lsp-id {
        description 'The lsp identifier of hsb.'
                    ;
        type uint16 ;
      }
      leaf wtr-lsp-id {
        description 'The lsp identifier of wtr.'
                    ;
        type uint16 ;
      }
      leaf ingress-id {
        description 'The ingress LSR ID.'
                    ;
        type ncd:ipv4-address ;
      }
      leaf egress-id {
        description 'The egress LSR ID.'
                    ;
        type ncd:ipv4-address ;
      }
      leaf report-reason {
        description 'The reason of report.'
                    ;
        type enumeration {
          enum CREAT_SUCC {
            value 1 ;
          }
          enum CREAT_ERR {
            value 2 ;
          }
          enum DELETE_SUCC {
            value 3 ;
          }
          enum DELETE_ERR {
            value 4 ;
          }
          enum CHG_SUCC {
            value 5 ;
          }
          enum CHG_ERR {
            value 6 ;
          }
          enum STATE_CHG {
            value 7 ;
          }
          enum HSB_BINDING_SUCC {
            value 8 ;
          }
          enum HSB_DELETE {
            value 9 ;
          }
          enum HSB_SWITCH {
            value 10 ;
          }
          enum HSB_UNSWITCH {
            value 11 ;
          }
        }
      }
    }
    list ero {
      config false ;
      description 'The tunnel ERO list.'
                  ;
      key 'hop-table-index hop-index'
          ;
      leaf hop-table-index {
        description 'The table index of chop.'
                    ;
        type uint32 ;
      }
      leaf hop-index {
        description 'The index of ERO hop.'
                    ;
        type uint32 ;
      }
      leaf addr-type {
        description 'The hop address type.'
                    ;
        type enumeration {
          enum IPV4 {
            value 1 ;
          }
          enum IPV6 {
            value 2 ;
          }
          enum AS_NUM {
            value 3 ;
          }
          enum UNNUM_IF {
            value 4 ;
          }
          enum LSP_ID {
            value 5 ;
          }
          enum UNNUM_V6 {
            value 6 ;
          }
        }
      }
      leaf ip-addr {
        description 'The ip address of hop.'
                    ;
        type ncd:ipv4-address ;
      }
      leaf prefix-len {
        description 'The prefix length of ip address.'
                    ;
        type uint8 ;
      }
      leaf as-number {
        description 'AS number.'
                    ;
        type uint16 ;
      }
      leaf addr-unnum {
        description 'The unnumbered ID.'
                    ;
        type uint32 ;
      }
      leaf hop-type {
        description 'The hop type.'
                    ;
        type enumeration {
          enum strictly {
            value 1 ;
          }
          enum loose {
            value 2 ;
          }
        }
      }
    }
    list pathoption-addition {
      config false ;
      description 'The additional information of pathoption.'
                  ;
      key 'tunnel-id option-id'
          ;
      leaf tunnel-id {
        description 'The identifier of tunnel.'
                    ;
        type uint16 ;
      }
      leaf option-id {
        description 'The option identifier of tunnel.'
                    ;
        type uint8 ;
      }
      leaf last-time-rst {
        description 'The result of creat the lsp.'
                    ;
        type uint8 ;
      }
      leaf lsp-id {
        description 'The lsp id of successed creat.'
                    ;
        type uint16 ;
      }
      leaf errcode {
        description 'The type of wrong.'
                    ;
        type uint16 ;
      }
      leaf errvalue {
        description 'The value of last failed creat.'
                    ;
        type uint16 ;
      }
      leaf last-try-time {
        description 'The time of creat the lsp.'
                    ;
        type ncd:datetime ;
      }
      leaf fail-node-ipaddr {
        description 'The wrong value of the failed creat.'
                    ;
        type ncd:ipv4-address ;
      }
    }
    ncd:revise-date 2015-03-03 ;
  }
  notification history-path {
    description 'The information of history-path.'
                ;
    list hispath {
      config false ;
      description 'The information of history-path.'
                  ;
      key 'tnnlid lspid hopindex'
          ;
      leaf tnnlid {
        description 'tunnel id.'
                    ;
        type uint16 ;
      }
      leaf lspid {
        description 'The lspid of tunnel.'
                    ;
        type uint16 ;
      }
      leaf hopindex {
        description hopindex. ;
        type uint16 ;
      }
      leaf lsprole {
        description "The lsp role of tunnel,it's behalf of master while the val"
                  + "ue is 1 ,it's behalf of backup while the value is 2 ."
                    ;
        type uint8 ;
      }
      leaf pathoption {
        description 'The pathoption of tunnel.'
                    ;
        type uint8 ;
      }
      leaf hishopaddr {
        description 'The address of historypath.'
                    ;
        type ncd:ipv4-address ;
      }
    }
    ncd:revise-date 2015-03-03 ;
  }
  notification sr-tunnel {
    description 'The SR tunnel information.'
                ;
    status obsolete {
      ncd:revise-date 2017-09-14 ;
    }
    list tunnel {
      config false ;
      description 'The SR tunnel list.'
                  ;
      key tunnel-id ;
      leaf tunnel-id {
        description 'The tunnel ID.'
                    ;
        type uint16 ;
      }
      leaf ingress-id {
        description 'The ingress LSR ID.'
                    ;
        type ncd:ipv4-address ;
      }
      leaf egress-id {
        description 'The egress LSR ID.'
                    ;
        type ncd:ipv4-address ;
      }
      leaf oper-status {
        description 'The operation status of tunnel.'
                    ;
        type enumeration {
          enum unknown {
            value 0 ;
          }
          enum up {
            value 1 ;
          }
          enum down {
            value 2 ;
          }
          enum WTR {
            value 4 ;
          }
        }
      }
      leaf master-lsp-id {
        description 'The master lsp identifier.'
                    ;
        type uint16 ;
      }
      leaf slave-lsp-id {
        description 'The lsp identifier of slave.'
                    ;
        type uint16 ;
      }
      leaf hsb-status {
        description 'The hsb status of tunnel.'
                    ;
        type enumeration {
          enum none {
            value 0 ;
          }
          enum ready {
            value 1 ;
          }
          enum active {
            value 2 ;
          }
        }
      }
      leaf master-splice-label {
        description 'The master splice label.'
                    ;
        type uint32 ;
      }
      leaf slave-splice-label {
        description 'The splice label of slave.'
                    ;
        type uint32 ;
      }
      leaf report-reason {
        description 'The reason of report.'
                    ;
        type enumeration {
          enum CREAT_SUCC {
            value 1 ;
          }
          enum CREAT_ERR {
            value 2 ;
          }
          enum DELETE_SUCC {
            value 3 ;
          }
          enum DELETE_ERR {
            value 4 ;
          }
          enum CHG_SUCC {
            value 5 ;
          }
          enum CHG_ERR {
            value 6 ;
          }
          enum STATE_CHG {
            value 7 ;
          }
          enum HSB_BINDING_SUCC {
            value 8 ;
          }
          enum HSB_DELETE {
            value 9 ;
          }
          enum HSB_SWITCH {
            value 10 ;
          }
          enum HSB_UNSWITCH {
            value 11 ;
          }
        }
      }
    }
    list tunnel-path {
      config false ;
      description 'The path of segment-routing tunnel LSP.'
                  ;
      key 'tunnel-id lsp-role hop-index'
          ;
      leaf tunnel-id {
        description 'The tunnel ID.'
                    ;
        type uint16 ;
      }
      leaf lsp-role {
        description "The lsp role of tunnel,it's behalf of master while the val"
                  + "ue is 1 ,it's behalf of backup while the value is 2."
                    ;
        type enumeration {
          enum master {
            value 1 ;
          }
          enum slave {
            value 2 ;
          }
        }
      }
      leaf hop-index {
        description 'The index of sr-path hop.'
                    ;
        type uint16 ;
      }
      leaf lsp-id {
        description 'The lsp identifier.'
                    ;
        type uint16 ;
      }
      leaf sid-type {
        description 'The sid type.'
                    ;
        type enumeration {
          enum default {
            value 0 ;
          }
          enum node-id-v4 {
            value 1 ;
          }
          enum node-id-v6 {
            value 2 ;
          }
          enum adj-id-v4 {
            value 3 ;
          }
          enum adj-id-v6 {
            value 4 ;
          }
          enum unnum-adj-id-v4 {
            value 5 ;
          }
        }
      }
      leaf sid-val {
        description 'The sid value.'
                    ;
        type uint32 ;
      }
      leaf node-ip {
        description 'The node IP.'
                    ;
        type ncd:ipv4-address ;
      }
      leaf adj-local-rid {
        description 'The local router id of adjacency.'
                    ;
        type ncd:ipv4-address ;
      }
      leaf adj-local-ip {
        description 'The local ip of adjacency.'
                    ;
        type ncd:ipv4-address ;
      }
      leaf adj-peer-rid {
        description 'The peer router id of adjacency.'
                    ;
        type ncd:ipv4-address ;
      }
      leaf adj-peer-ip {
        description 'The peer ip of adjacency.'
                    ;
        type ncd:ipv4-address ;
      }
    }
    ncd:revise-date 2017-04-25 ;
  }
}
