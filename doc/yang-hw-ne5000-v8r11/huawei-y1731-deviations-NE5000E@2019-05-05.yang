/*
Copyright (C) 2019 Huawei Technologies Co., Ltd. All rights reserved.
*/
module huawei-y1731-deviations-NE5000E {
  namespace "urn:huawei:yang:huawei-y1731-deviations-NE5000E";
  prefix y1731-devs-NE5000E;

  import huawei-y1731 {
    prefix y1731;
  }

  organization
    "Huawei Technologies Co., Ltd.";
  contact
    "Huawei Industrial Base
     Bantian, Longgang
     Shenzhen 518129
     People's Republic of China
     Website: http://www.huawei.com
     Email: support@huawei.com";
  description
    "Y.1731 is developed by ITU-T for operations, administration and maintenance (OAM) of Ethernet, which providing fault management and performance management solutions for Ethernet.";

  revision 2019-05-05 {
    description
      "Initial revision.";
    reference "Huawei private.";
  }

  typedef sslm-interval-deviations {
    type enumeration {
      enum 1000ms {
        value 1000;
        description
          "Interval of 1000 ms.";
      }
      enum 10000ms {
        value 10000;
        description
          "Interval of 10000 ms.";
      }
    }
    description
      "SSLM interval.";
  }

  deviation "/y1731:y1731/y1731:global-enable/y1731:mds/y1731:md/y1731:mas/y1731:ma/y1731:meps/y1731:mep/y1731:type/y1731:if-mep/y1731:clear-arp" {
    deviate not-supported;
  }
  deviation "/y1731:y1731/y1731:global-enable/y1731:test-instances/y1731:test-instance/y1731:dual-loss/y1731:enabled" {
    deviate not-supported;
  }
  deviation "/y1731:y1731/y1731:global-enable/y1731:test-instances/y1731:test-instance/y1731:single-loss-recv/y1731:enabled" {
    deviate not-supported;
  }
  deviation "/y1731:y1731/y1731:global-enable/y1731:test-instances/y1731:test-instance/y1731:single-loss-send" {
    deviate not-supported;
  }
  deviation "/y1731:y1731/y1731:global-enable/y1731:mds/y1731:md/y1731:mas/y1731:ma/y1731:meps/y1731:mep/y1731:type/y1731:if-mep/y1731:eth-bn-receive" {
    deviate not-supported;
  }
  deviation "/y1731:y1731/y1731:global-enable/y1731:mds/y1731:md/y1731:mas/y1731:ma/y1731:meps/y1731:mep/y1731:type/y1731:pw-mep" {
    deviate not-supported;
  }
  deviation "/y1731:y1731/y1731:global-enable/y1731:mds/y1731:md/y1731:mas/y1731:ma/y1731:meps/y1731:mep/y1731:type/y1731:if-mep/y1731:port-link" {
    deviate not-supported;
  }
  deviation "/y1731:y1731/y1731:global-enable/y1731:test-instances/y1731:test-instance/y1731:synthetic-loss-send/y1731:interval" {
    deviate replace {
      type y1731-devs-NE5000E:sslm-interval-deviations;
    }
  }
  deviation "/y1731:y1731/y1731:global-enable/y1731:mds/y1731:md/y1731:mas/y1731:ma/y1731:meps/y1731:mep" {
    deviate delete {
      must '(direction and (if-name or peer-ip)) or (not(direction) and not(if-name) and not(peer-ip))';
    }
    deviate add {
      must '(y1731:direction and y1731:if-name ) or (not(y1731:direction) and not(y1731:if-name))';
    }
  }
  deviation "/y1731:y1731/y1731:global-enable/y1731:mds/y1731:md/y1731:mas/y1731:ma/y1731:meps/y1731:mep/y1731:rdi-alarm-disabled" {
    deviate delete {
      must "../rdi-alarm-disabled='false' or (../if-name or ../peer-ip)";
    }
    deviate add {
      must "../y1731:rdi-alarm-disabled='false' or (../y1731:if-name)";
    }
  }
  deviation "/y1731:y1731/y1731:global-enable/y1731:mds/y1731:md/y1731:mas/y1731:ma/y1731:meps/y1731:mep/y1731:ais-alarm-disabled" {
    deviate delete {
      must "../ais-alarm-disabled='false' or (../if-name or ../peer-ip)";
    }
    deviate add {
      must "../y1731:ais-alarm-disabled='false' or (../y1731:if-name)";
    }
  }
  deviation "/y1731:y1731/y1731:global-enable/y1731:test-instances/y1731:test-instance/y1731:peer-ip" {
    deviate not-supported;
  }
  deviation "/y1731:y1731/y1731:global-enable/y1731:test-instances/y1731:test-instance/y1731:vc-id" {
    deviate not-supported;
  }
  deviation "/y1731:y1731/y1731:global-enable/y1731:mds/y1731:md/y1731:mas/y1731:ma/y1731:unexpected-mep-alarm" {
    deviate not-supported;
  }
  deviation "/y1731:y1731/y1731:global-enable/y1731:test-instances/y1731:test-instance/y1731:priority" {
    deviate delete {
      must '(../priority and not(../peer-ip) and not(../vc-id)) or not(../priority)';
    }
  }
  deviation "/y1731:y1731/y1731:global-enable/y1731:mds/y1731:md/y1731:mas/y1731:ma/y1731:map-service/y1731:bind-vlan" {
    deviate not-supported;
  }
}
