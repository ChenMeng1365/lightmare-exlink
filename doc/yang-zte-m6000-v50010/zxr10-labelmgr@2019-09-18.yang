module zxr10-labelmgr {
  namespace 'http://www.zte.com.cn/zxr10/netconf/schema/rosng/labelmgr'
            ;
  prefix labelmgr ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe labelmgr. Labelmgr configure the '
            + 'protocol label range and block unit.The range <global-min,global'
            + '-max> is the total range of labels, label range for each protoco'
            + 'l must be in the global label range. According to the agreement '
            + 'on the label range to be divided, each label ranges can not over'
            + 'lap. The configuration of label range for kompella is optional, '
            + 'the range is invalid representing not support kompella label whe'
            + 'n no configuration at the first time, and the range <kompella-mi'
            + 'n,kompella-max> can not exceed the maximum 65536 when configurat'
            + 'ion. Label range changes will take effect at the next reload.'
              ;
  revision 2019-09-18 {
    description 'add nodes: '+"\n"
              + '/configuration/labelmgr/srgb-label-range/support-state,'
                ;
  }
  revision 2019-01-22 {
    description 'Modify nodes: '+"\n"
              + '/configuration/labelmgr/label-range/ac/min,'+"\n"
              + '/configuration/labelmgr/label-range/ac/max,'+"\n"
              + '/configuration/labelmgr/label-range/srgb/min,'+"\n"
              + '/configuration/labelmgr/label-range/srgb/max,'+"\n"
              + '/configuration/labelmgr/label-range/srlb/min,'+"\n"
              + '/configuration/labelmgr/label-range/srlb/max.'
                ;
  }
  revision 2018-11-16 {
    description 'Modify nodes: '+"\n"
              + '/configuration/labelmgr/srgb-label-range/min,'+"\n"
              + '/configuration/labelmgr/srgb-label-range/max,'+"\n"
              + '/configuration/labelmgr/bier-label-range/min,'+"\n"
              + '/configuration/labelmgr/bier-label-range/max,'+"\n"
              + '/configuration/labelmgr/srlb-label-range/min,'+"\n"
              + '/configuration/labelmgr/srlb-label-range/max.'
                ;
  }
  revision 2018-07-03 {
    description 'Modify feature node: label-range.'
                ;
  }
  revision 2018-05-22 {
    description 'Add configuration node of srlb-label-range.'
                ;
  }
  revision 2018-04-12 {
    description 'Add nodes: '+"\n"
              + '/configuration/labelmgr/label-reservation/srlb,'+"\n"
              + '/configuration/labelmgr/bier-label-range. '+"\n"
              + 'Modify nodes: '+"\n"
              + '/configuration/labelmgr/label-range/global/min,'+"\n"
              + '/configuration/labelmgr/label-range/global/max,'+"\n"
              + '/configuration/labelmgr/label-range/static/min,'+"\n"
              + '/configuration/labelmgr/label-range/static/max,'+"\n"
              + '/configuration/labelmgr/label-range/ldp/min,'+"\n"
              + '/configuration/labelmgr/label-range/ldp/max,'+"\n"
              + '/configuration/labelmgr/label-range/pwe3/min,'+"\n"
              + '/configuration/labelmgr/label-range/pwe3/max,'+"\n"
              + '/configuration/labelmgr/label-range/rsvp/min,'+"\n"
              + '/configuration/labelmgr/label-range/rsvp/max,'+"\n"
              + '/configuration/labelmgr/label-range/bgp/min,'+"\n"
              + '/configuration/labelmgr/label-range/bgp/max,'+"\n"
              + '/configuration/labelmgr/label-range/bgpv6/min,'+"\n"
              + '/configuration/labelmgr/label-range/bgpv6/max,'+"\n"
              + '/configuration/labelmgr/label-range/kompella/min,'+"\n"
              + '/configuration/labelmgr/label-range/kompella/max,'+"\n"
              + '/configuration/labelmgr/kompella-range-size/label-range-size,'+"\n"
              + '/configuration/labelmgr/auto-relocalization/enable,'+"\n"
              + '/configuration/labelmgr/srgb-label-range/min,'+"\n"
              + '/configuration/labelmgr/srgb-label-range/max,'+"\n"
              + '/state/labelmgr/label-manager-info/label-range-entry/service.'
                ;
  }
  revision 2018-03-29 {
    description 'Add configuration node of srgb-label-range.'
                ;
  }
  revision 2016-12-01 {
    description 'Add configuration node of forbidden-label-range.'
                ;
  }
  revision 2016-07-08 {
    description '1.Add two enum items of the leaf node "state/labelmgr/label-ma'
              + 'nage-info/label-range-entry/service".'
                ;
  }
  revision 2015-05-28 {
    description '1.Modify the default value and the Perf-code of 6 leaf nodes, '
              + 'such as configuration/labelmgr/label-reservation/ldp, configur'
              + 'ation/labelmgr/label-reservation/pwe3, configuration/labelmgr/'
              + 'label-reservation/rsvp, configuration/labelmgr/label-reservati'
              + 'on/bgp, configuration/labelmgr/label-reservation/bgpv6, config'
              + 'uration/labelmgr/label-reservation/ac-label.'+"\n"
              + '2.Modify the operation change type of configuration/labelmgr/l'
              + 'abel-reservation.'+"\n"
              + '3.Modify the max value of configuration/labelmgr/kompella-rang'
              + 'e-size/label-range-size.'+"\n"
              + '4.Remove a container named "labelmgr-enable" under the configu'
              + 'ration/labelmgr.'
                ;
  }
  revision 2015-04-24 {
    description 'Modify the description and the type of state/labelmgr/label-ma'
              + 'nager-info/label-range-entry/service leaf node, in which the e'
              + 'numeration name "null" has been changed to "free".'+"\n"
              + 'Add a new feature named "label-range".'+"\n"
              + 'Add an if-feature named "label-range" in the configuration/lab'
              + 'elmgr/label-range container node.'
                ;
  }
  revision 2014-08-19 {
    description 'Modify the description of configuration node and labelmgr node'
              + ' under configuration node .'+"\n"
              + 'Delete the label-range node.'+"\n"
              + 'Add kompella-range-size, static-label-ranges, label-reservatio'
              + 'n, operation, and state nodes.'
                ;
  }
  revision 2013-09-22 {
    description 'Modify the description of labelmgr,label-range and kompella no'
              + 'des.'+"\n"
              + 'Delete the block-unit node.'
                ;
  }
  revision 2013-07-22 {
    description 'Initial version'
                ;
  }
  feature label-range {
    description 'The label-range container node can be supported by current som'
              + 'e projects.'
                ;
  }
  container configuration {
    description 'Configuration information.'
                ;
    container labelmgr {
      description 'Label manager module configuration root node.'
                  ;
      container label-range {
        // if-feature label-range ;
        description 'The configuration info about label-range. The range <globa'
                  + 'l-min,global-max> is the total range of labels, label rang'
                  + 'e for each protocol must be in the global label range.'+"\n"
                  + 'According to the agreement on the label range to be divide'
                  + 'd, each label ranges can not overlap. The configuration of'
                  + ' label range for kompella is optional,  the range is inval'
                  + 'id representing not support kompella label when no configu'
                  + 'ration at the first time, and the range <kompella-min,komp'
                  + 'ella-max> can not exceed the maximum 65536 when configurat'
                  + 'ion. Label range changes will take effect at the next relo'
                  + 'ad.'
                    ;
        presence 'Configuration data for label range.'
                 ;
        container global {
          description 'The range of global label. Its value is not constant, ma'
                    + 'y be different for each product. In some products it is '
                    + '16-1048575.'
                      ;
          leaf min {
            description 'The minimum of global label.'
                        ;
            type uint32 {
              range 16..1048575 ;
            }
            mandatory true ;
          }
          leaf max {
            description 'The maximum of global label.'
                        ;
            type uint32 {
              range 16..1048575 ;
            }
            mandatory true ;
          }
        }
        container static {
          description 'The range of static label. Its value is not constant, ma'
                    + 'y be different for each product. In some products it is '
                    + '16-16383.'
                      ;
          leaf min {
            description 'The minimum of static label.'
                        ;
            type uint32 {
              range 16..1048575 ;
            }
            mandatory true ;
          }
          leaf max {
            description 'The maximum of static label.'
                        ;
            type uint32 {
              range 16..1048575 ;
            }
            mandatory true ;
          }
        }
        container ldp {
          description 'The range of LDP label. Its value is not constant, may b'
                    + 'e different for each product. In some products it is 163'
                    + '84-81919.'
                      ;
          leaf min {
            description 'The minimum of LDP label.'
                        ;
            type uint32 {
              range 16..1048575 ;
            }
            mandatory true ;
          }
          leaf max {
            description 'The maximum of LDP label.'
                        ;
            type uint32 {
              range 16..1048575 ;
            }
            mandatory true ;
          }
        }
        container pwe3 {
          description 'The range of PWE3 label. Its value is not constant, may '
                    + 'be different for each product. In some products it is 81'
                    + '920-147455.'
                      ;
          leaf min {
            description 'The minimum of PWE3 label.'
                        ;
            type uint32 {
              range 16..1048575 ;
            }
            mandatory true ;
          }
          leaf max {
            description 'The maximum of PWE3 label.'
                        ;
            type uint32 {
              range 16..1048575 ;
            }
            mandatory true ;
          }
        }
        container rsvp {
          description 'The range of RSVP label. Its value is not constant, may '
                    + 'be different for each product. In some products it is 14'
                    + '7456-212991.'
                      ;
          leaf min {
            description 'The minimum of RSVP label.'
                        ;
            type uint32 {
              range 16..1048575 ;
            }
            mandatory true ;
          }
          leaf max {
            description 'The maximum of RSVP label.'
                        ;
            type uint32 {
              range 16..1048575 ;
            }
            mandatory true ;
          }
        }
        container bgp {
          description 'The range of BGP label. Its value is not constant, may b'
                    + 'e different for each product. In some products it is 212'
                    + '992-622591.'
                      ;
          leaf min {
            description 'The minimum of BGP label.'
                        ;
            type uint32 {
              range 16..1048575 ;
            }
            mandatory true ;
          }
          leaf max {
            description 'The maximum of BGP label.'
                        ;
            type uint32 {
              range 16..1048575 ;
            }
            mandatory true ;
          }
        }
        container bgpv6 {
          description 'The range of BGPv6 label. Its value is not constant, may'
                    + ' be different for each product. In some products it is 6'
                    + '22592-1032191.'
                      ;
          leaf min {
            description 'The minimum of BGPv6 label.'
                        ;
            type uint32 {
              range 16..1048575 ;
            }
            mandatory true ;
          }
          leaf max {
            description 'The maximum of BGPv6 label.'
                        ;
            type uint32 {
              range 16..1048575 ;
            }
            mandatory true ;
          }
        }
        container kompella {
          description 'Kompella label range is optional, if you configure the r'
                    + 'ange of other labels not configuring kompella label rang'
                    + 'e at the first time, kompella label range is invalid. If'
                    + ' the entire label-range is not set, kompella use the def'
                    + 'ault range. The default range is different for each prod'
                    + 'uct, and in some products it is 1032192-1048575.'
                      ;
          presence 'Label range of  kompella.'
                   ;
          leaf min {
            description 'The minimum of kompella label.'
                        ;
            type uint32 {
              range 16..1048575 ;
            }
            mandatory true ;
          }
          leaf max {
            description 'The maximum of kompella label.'
                        ;
            type uint32 {
              range 16..1048575 ;
            }
            mandatory true ;
          }
        }
        container ac {
          description 'Ac label range is optional, if you configure the range o'
                    + 'f other labels not configuring Ac label range at the fir'
                    + 'st time, Ac label range is invalid. If the entire label-'
                    + 'range is not set, Ac label range use the default range. '
                    + 'The default range is different for each product.'
                      ;
          presence 'Label range of  ac.'
                   ;
          leaf min {
            description 'The minimum of Ac label range.'
                        ;
            type uint32 {
              range 16..1048575 ;
            }
            mandatory true ;
          }
          leaf max {
            description 'The maximum of Ac label range.'
                        ;
            type uint32 {
              range 16..1048575 ;
            }
            mandatory true ;
          }
          ncd:revise-date 2019-01-22 ;
        }
        container srgb {
          description 'SRGB label range is optional, if you configure the range'
                    + ' of other labels not configuring SRGB label range at the'
                    + ' first time, SRGB label range is invalid. If the entire '
                    + 'label-range is not set, SRGB use the default range.The d'
                    + 'efault range is different for each product.'
                      ;
          presence 'Label range of  SRGB.'
                   ;
          leaf min {
            description 'The minimum of SRGB label range.'
                        ;
            type uint32 {
              range 16..1048575 ;
            }
            mandatory true ;
          }
          leaf max {
            description 'The maximum of SRGB label range.'
                        ;
            type uint32 {
              range 16..1048575 ;
            }
            mandatory true ;
          }
          ncd:revise-date 2019-01-22 ;
        }
        container srlb {
          description 'SRLB label range is optional, if you configure the range'
                    + ' of other labels not configuring SRLB label range at the'
                    + ' first time, SRLB label range is invalid. If the entire '
                    + 'label-range is not set, SRLB use the default range. The '
                    + 'default range is different for each product.'
                      ;
          presence 'Label range of  SRLB.'
                   ;
          leaf min {
            description 'The minimum of SRLB label range.'
                        ;
            type uint32 {
              range 16..1048575 ;
            }
            mandatory true ;
          }
          leaf max {
            description 'The maximum of SRLB label range.'
                        ;
            type uint32 {
              range 16..1048575 ;
            }
            mandatory true ;
          }
          ncd:revise-date 2019-01-22 ;
        }
      }
      container kompella-range-size {
        description 'Configure Kompella label range size.'
                    ;
        presence 'Configuration data for Kompella range size.'
                 ;
        leaf label-range-size {
          description 'Label range size.'
                      ;
          type uint32 {
            range 0..1048560 ;
          }
          mandatory true ;
        }
      }
      container static-label-ranges {
        description 'Configure static label range.'
                    ;
        presence 'Configuration data for static label range.'
                 ;
        list static-label-range {
          description 'Configure some segments for static label range.'
                      ;
          key min ;
          leaf min {
            description 'The minimum of the static label range.'
                        ;
            type uint32 {
              range 16..1048575 ;
            }
          }
          leaf max {
            description 'The maximum of the static label range.'
                        ;
            type uint32 {
              range 16..1048575 ;
            }
            mandatory true ;
          }
        }
      }
      container label-reservation {
        description 'Configure label reservation number for each protocol.'
                    ;
        presence 'Configuration data for label reservation.'
                 ;
        leaf ldp {
          description 'The reservation number of LDP label.'
                      ;
          type int32 {
            range 0..1048560 ;
          }
          default 2000 ;
        }
        leaf pwe3 {
          description 'The reservation number of PWE3 label.'
                      ;
          type uint32 {
            range 0..1048560 ;
          }
          default 8000 ;
        }
        leaf rsvp {
          description 'The reservation number of RSVP label.'
                      ;
          type uint32 {
            range 0..1048560 ;
          }
          default 1000 ;
        }
        leaf bgp {
          description 'The reservation number of BGP label.'
                      ;
          type uint32 {
            range 0..1048560 ;
          }
          default 0 ;
        }
        leaf bgpv6 {
          description 'The reservation number of BGPV6 label.'
                      ;
          type uint32 {
            range 0..1048560 ;
          }
          default 0 ;
        }
        leaf ac-label {
          description 'The reservation number of AC label.'
                      ;
          type uint32 {
            range 0..1048560 ;
          }
          default 0 ;
        }
        leaf srlb {
          description 'The reservation number of SRLB label.'
                      ;
          type uint32 {
            range 0..1048560 ;
          }
          default 0 ;
          ncd:revise-date 2018-04-12 ;
        }
      }
      container auto-relocalization {
        description 'Control capability of automatic relocalization for label r'
                  + 'esource.'
                    ;
        presence 'Operation for auto-relocalization'
                 ;
        leaf enable {
          description 'The capability of automatic relocalization for label res'
                    + 'ource.'+"\n"
                    + 'ENABLE    :    1'+"\n"
                    + 'DISABLE :      2'
                      ;
          type enumeration {
            enum ENABLE {
              value 1 ;
              description 'Enable automatic relocalization for label resource.'
                          ;
            }
            enum DISABLE {
              value 2 ;
              description 'Disable automatic relocalization for label resource.'
                          ;
            }
          }
          mandatory true ;
        }
      }
      container forbidden-label-ranges {
        description 'Configure forbidden label range.'
                    ;
        presence 'Configuration data for forbidden label range.'
                 ;
        list forbidden-label-range {
          description 'Configure some segments for forbidden label range.'
                      ;
          key 'min max'
              ;
          leaf min {
            description 'The minimum of the forbidden label range.'
                        ;
            type uint32 ;
          }
          leaf max {
            description 'The maximum of the forbidden label range.'
                        ;
            type uint32 ;
          }
        }
        ncd:revise-date 2016-12-01 ;
      }
      container srgb-label-range {
        description 'Configure SRGB label range.'
                    ;
        presence 'Configuration data for SRGB label range.'
                 ;
        leaf min {
          description 'The minimum of SRGB label range.'
                      ;
          type uint32 {
            range '0 | 16..1048575'
                  ;
          }
          mandatory true ;
        }
        leaf max {
          description 'The maximum of SRGB label range.'
                      ;
          type uint32 {
            range '0 | 16..1048575'
                  ;
          }
          mandatory true ;
        }
        ncd:revise-date 2018-03-29 ;
      }
      container bier-label-range {
        description 'Configure BIER label range.'
                    ;
        presence 'Configuration data for BIER label range.'
                 ;
        leaf min {
          description 'The minimum of BIER label range.'
                      ;
          type uint32 {
            range '0 | 16..1048575'
                  ;
          }
          mandatory true ;
        }
        leaf max {
          description 'The maximum of BIER label range.'
                      ;
          type uint32 {
            range '0 | 16..1048575'
                  ;
          }
          mandatory true ;
        }
        ncd:revise-date 2018-04-12 ;
      }
      container srlb-label-range {
        presence 'Configuration data for SRLB label range.'
                 ;
        leaf min {
          description 'The minimum of SRLB label range.'
                      ;
          type uint32 {
            range '0 | 16..1048575'
                  ;
          }
          mandatory true ;
        }
        leaf max {
          description 'The maximum of SRLB label range.'
                      ;
          type uint32 {
            range '0 | 16..1048575'
                  ;
          }
        }
        leaf support-state {
          reference 'The function of srlb-label-range is not supported.'
                    ;
          type uint8 ;
          ncd:revise-date 2019-09-18 ;
        }
        ncd:revise-date 2018-05-22 ;
      }
    }
  }
  container operation {
    config false ;
    description 'Operation information.'
                ;
    container labelmgr {
      description 'Label manager module operation root node.'
                  ;
      container prepare-range {
        description 'Prepare label resource for enlarging static label range.'
                    ;
        presence 'Operation for preparing label range.'
                 ;
        leaf min {
          description 'The minimum of the prepared label range.'
                      ;
          type uint32 {
            range 16..1048575 ;
          }
          mandatory true ;
        }
        leaf max {
          description 'The maximum of the prepared label range.'
                      ;
          type uint32 {
            range 16..1048575 ;
          }
          mandatory true ;
        }
        leaf cancel {
          description 'Cancel prepared label range.
CANCEL: 1'
                      ;
          type enumeration {
            enum CANCEL {
              value 1 ;
              description 'Cancel prepared label range.'
                          ;
            }
          }
        }
      }
    }
  }
  container state {
    config false ;
    description 'State infomation'
                ;
    container labelmgr {
      description 'Label manager module state root node.'
                  ;
      container label-manager-info {
        description 'The state infomation of the label manager. It contains the'
                  + ' label range list infomation.'
                    ;
        presence 'State of  the label manger.'
                 ;
        list label-range-entry {
          description 'It contains label resource utilization infomation of eac'
                    + 'h service.'
                      ;
          key 'service label-min'
              ;
          leaf service {
            description 'The type of the label range pool.'+"\n"
                      + 'STATIC :    0'+"\n"
                      + 'LDP    :    1'+"\n"
                      + 'PWE3 :    2'+"\n"
                      + 'RSVP    :    3'+"\n"
                      + 'BGP :    4'+"\n"
                      + 'BGPV6    :   5'+"\n"
                      + 'KOMPELLA :    6'+"\n"
                      + 'AC    :    7'+"\n"
                      + 'PREPARED :    8'+"\n"
                      + 'FREE    :    9'+"\n"
                      + 'GLOBAL :    10'+"\n"
                      + 'SRGB :    11'+"\n"
                      + 'SRLB :    12'+"\n"
                      + 'FORBIDDEN :    13'+"\n"
                      + 'BIER:    14'
                        ;
            type enumeration {
              enum STATIC {
                value 0 ;
                description 'The static label range pool.'
                            ;
              }
              enum LDP {
                value 1 ;
                description 'The LDP label range pool.'
                            ;
              }
              enum PWE3 {
                value 2 ;
                description 'The PWE3 label range pool.'
                            ;
              }
              enum RSVP {
                value 3 ;
                description 'The RSVP label range pool.'
                            ;
              }
              enum BGP {
                value 4 ;
                description 'The BGP label range pool.'
                            ;
              }
              enum BGPV6 {
                value 5 ;
                description 'The BGPV6 label range pool.'
                            ;
              }
              enum KOMPELLA {
                value 6 ;
                description 'The KOMPELLA label range pool.'
                            ;
              }
              enum AC {
                value 7 ;
                description 'The AC label range pool.'
                            ;
              }
              enum PREPARED {
                value 8 ;
                description 'The prepared label range pool.'
                            ;
              }
              enum FREE {
                value 9 ;
                description 'The free label range pool.'
                            ;
              }
              enum GLOBAL {
                value 10 ;
                description 'The global label range pool.'
                            ;
              }
              enum SRGB {
                value 11 ;
                description 'The SRGB label range pool.'
                            ;
              }
              enum SRLB {
                value 12 ;
                description 'The SRLB label range pool.'
                            ;
              }
              enum FORBIDDEN {
                value 13 ;
                description 'The forbidden label range pool.'
                            ;
              }
              enum BIER {
                value 14 ;
                description 'The BIER label range pool.'
                            ;
              }
            }
          }
          leaf error-flag {
            description 'The error flag of the label range pool.'+"\n"
                      + 'NO-ERROR :    0'+"\n"
                      + 'ERROR    :    1'
                        ;
            type enumeration {
              enum NO-ERROR {
                value 0 ;
                description 'The label range pool has no error.'
                            ;
              }
              enum ERROR {
                value 1 ;
                description 'The label range pool has error.'
                            ;
              }
            }
          }
          leaf fixed-flag {
            description 'The fixed flag of the label range pool.'+"\n"
                      + 'NOT-FIXED :    0'+"\n"
                      + 'FIXED    :    1'
                        ;
            type enumeration {
              enum NOT-FIXED {
                value 0 ;
                description 'The label range is not fixed.'
                            ;
              }
              enum FIXED {
                value 1 ;
                description 'The label range is fixed.'
                            ;
              }
            }
          }
          leaf reserved-num {
            description 'The number of reserved label.'
                        ;
            type uint32 ;
          }
          leaf localized-num {
            description 'The number of localized label.'
                        ;
            type uint32 ;
          }
          leaf label-min {
            description 'The minimum of the label range.'
                        ;
            type uint32 ;
          }
          leaf label-max {
            description 'The maximum of the label range.'
                        ;
            type uint32 ;
          }
          leaf static-hole-num {
            description 'The number of static holes.'
                        ;
            type uint32 ;
          }
          leaf kompella-hole-num {
            description 'The number of Kompella holes.'
                        ;
            type uint32 ;
          }
          leaf legacy-num {
            description 'The number of legacy label.'
                        ;
            type uint32 ;
          }
          leaf sample-used-num {
            description 'The number of used label at the sample moment.'
                        ;
            type uint32 ;
          }
        }
      }
    }
  }
}
