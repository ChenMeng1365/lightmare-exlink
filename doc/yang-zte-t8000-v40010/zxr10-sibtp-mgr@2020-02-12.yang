module zxr10-sibtp-mgr {
  namespace 'http://www.zte.com.cn/zxr10/netconf/schema/rosng/sibtp-mgr'
            ;
  prefix sibtp-mgr ;
  import zxr10-netconf-defs {
    prefix ncd ;
    revision-date 2019-07-16 ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2020-02-12 {
    description 'Initial version.'
                ;
  }
  container state {
    description 'The state of SIBTP-MGR.'
                ;
    config false ;
    container sibtp-mgr {
      description 'The SIBTP-MGR state.'
                  ;
      container link-list {
        description 'The link list.'
                    ;
        list link-ipv4-public {
          description 'The ipv4 link.'
                      ;
          key 'source-ipv4 peer-ipv4 source-port peer-port'
              ;
          leaf source-ipv4 {
            description 'The source ipv4.'
                        ;
            type ncd:ipv4-address-none-zero ;
          }
          leaf peer-ipv4 {
            description 'The peer ipv4.'
                        ;
            type ncd:ipv4-address-none-zero ;
          }
          leaf source-port {
            description 'The source port.'
                        ;
            type uint32 {
              range 1025..65535 ;
            }
          }
          leaf peer-port {
            description 'The peer port.'
                        ;
            type uint32 {
              range 1025..65535 ;
            }
          }
          leaf state {
            description 'The state.'
                        ;
            type string {
              length 1..31 ;
            }
          }
        }
        list link-ipv4-vrf {
          description 'The ipv4 link.'
                      ;
          key 'source-ipv4 peer-ipv4 source-port peer-port vrf-name'
              ;
          leaf source-ipv4 {
            description 'The source ipv4.'
                        ;
            type ncd:ipv4-address-none-zero ;
          }
          leaf peer-ipv4 {
            description 'The peer ipv4.'
                        ;
            type ncd:ipv4-address-none-zero ;
          }
          leaf source-port {
            description 'The source port.'
                        ;
            type uint32 {
              range 1025..65535 ;
            }
          }
          leaf peer-port {
            description 'The peer port.'
                        ;
            type uint32 {
              range 1025..65535 ;
            }
          }
          leaf vrf-name {
            description 'The vrf name.'
                        ;
            type string {
              length 1..32 ;
            }
          }
          leaf state {
            description 'The state.'
                        ;
            type string {
              length 1..31 ;
            }
          }
        }
        list link-ipv6-public {
          description 'The ipv4 link.'
                      ;
          key 'source-ipv6 peer-ipv6 source-port peer-port'
              ;
          leaf source-ipv6 {
            description 'The source ipv6.'
                        ;
            type ncd:ipv6-address-none-zero ;
          }
          leaf peer-ipv6 {
            description 'The peer ipv6.'
                        ;
            type ncd:ipv6-address-none-zero ;
          }
          leaf source-port {
            description 'The source port.'
                        ;
            type uint32 {
              range 1025..65535 ;
            }
          }
          leaf peer-port {
            description 'The peer port.'
                        ;
            type uint32 {
              range 1025..65535 ;
            }
          }
          leaf state {
            description 'The state.'
                        ;
            type string {
              length 1..31 ;
            }
          }
        }
        list link-ipv6-vrf {
          description 'The ipv4 link.'
                      ;
          key 'source-ipv6 peer-ipv6 source-port peer-port vrf-name'
              ;
          leaf source-ipv6 {
            description 'The source ipv6.'
                        ;
            type ncd:ipv6-address-none-zero ;
          }
          leaf peer-ipv6 {
            description 'The peer ipv6.'
                        ;
            type ncd:ipv6-address-none-zero ;
          }
          leaf source-port {
            description 'The source port.'
                        ;
            type uint32 {
              range 1025..65535 ;
            }
          }
          leaf peer-port {
            description 'The peer port.'
                        ;
            type uint32 {
              range 1025..65535 ;
            }
          }
          leaf vrf-name {
            description 'The vrf name.'
                        ;
            type string {
              length 1..32 ;
            }
          }
          leaf state {
            description 'The state.'
                        ;
            type string {
              length 1..31 ;
            }
          }
        }
      }
    }
  }
  container configuration {
    description 'The configuration of SIBTP-MGR.'
                ;
    container sibtp-mgr {
      description 'Configure SIBTP-MGR.'
                  ;
      container link-list {
        description 'The link list.'
                    ;
        container link-ipv4-public-list {
          description 'The link ipv4 public list.'
                      ;
          list link-ipv4-public {
            description 'The ipv4 public link.'
                        ;
            key 'source-ipv4 peer-ipv4 source-port peer-port'
                ;
            leaf source-ipv4 {
              description 'The source ipv4.'
                          ;
              type ncd:ipv4-address-none-zero ;
            }
            leaf peer-ipv4 {
              description 'The peer ipv4.'
                          ;
              type ncd:ipv4-address-none-zero ;
            }
            leaf source-port {
              description 'The source port.'
                          ;
              type uint32 {
                range 1025..65535 ;
              }
            }
            leaf peer-port {
              description 'The peer port.'
                          ;
              type uint32 {
                range 1025..65535 ;
              }
            }
            leaf tcp-mss {
              description 'The tcp mss.'
                          ;
              type uint32 {
                range 68..10000 ;
              }
              default 1400 ;
            }
          }
        }
        container link-ipv4-vrf-list {
          description 'The link ipv4 vrf list.'
                      ;
          list link-ipv4-vrf {
            description 'The ipv4 vrf link.'
                        ;
            key 'source-ipv4 peer-ipv4 source-port peer-port vrf-name'
                ;
            leaf source-ipv4 {
              description 'The source ipv4.'
                          ;
              type ncd:ipv4-address-none-zero ;
            }
            leaf peer-ipv4 {
              description 'The peer ipv4.'
                          ;
              type ncd:ipv4-address-none-zero ;
            }
            leaf source-port {
              description 'The source port.'
                          ;
              type uint32 {
                range 1025..65535 ;
              }
            }
            leaf peer-port {
              description 'The peer port.'
                          ;
              type uint32 {
                range 1025..65535 ;
              }
            }
            leaf tcp-mss {
              description 'The tcp mss.'
                          ;
              type uint32 {
                range 68..10000 ;
              }
              default 1400 ;
            }
            leaf vrf-name {
              description 'The vrf name.'
                          ;
              type string {
                length 1..32 ;
              }
            }
          }
        }
        container link-ipv6-public-list {
          description 'The link ipv6 public list.'
                      ;
          list link-ipv6-public {
            description 'The ipv6 public link.'
                        ;
            key 'source-ipv6 peer-ipv6 source-port peer-port'
                ;
            leaf source-ipv6 {
              description 'The source ipv6.'
                          ;
              type ncd:ipv6-address-none-zero ;
            }
            leaf peer-ipv6 {
              description 'The peer ipv6.'
                          ;
              type ncd:ipv6-address-none-zero ;
            }
            leaf source-port {
              description 'The source port.'
                          ;
              type uint32 {
                range 1025..65535 ;
              }
            }
            leaf peer-port {
              description 'The peer port.'
                          ;
              type uint32 {
                range 1025..65535 ;
              }
            }
          }
        }
        container link-ipv6-vrf-list {
          description 'The link ipv6 vrf list.'
                      ;
          list link-ipv6-vrf {
            description 'The ipv6 vrf link.'
                        ;
            key 'source-ipv6 peer-ipv6 source-port peer-port vrf-name'
                ;
            leaf source-ipv6 {
              description 'The source ipv6.'
                          ;
              type ncd:ipv6-address-none-zero ;
            }
            leaf peer-ipv6 {
              description 'The peer ipv6.'
                          ;
              type ncd:ipv6-address-none-zero ;
            }
            leaf source-port {
              description 'The source port.'
                          ;
              type uint32 {
                range 1025..65535 ;
              }
            }
            leaf peer-port {
              description 'The peer port.'
                          ;
              type uint32 {
                range 1025..65535 ;
              }
            }
            leaf vrf-name {
              description 'The vrf name.'
                          ;
              type string {
                length 1..32 ;
              }
            }
          }
        }
      }
    }
  }
}
