/*
Copyright (C) 2019 Huawei Technologies Co., Ltd. All rights reserved.
*/
module huawei-nqa-deviations-NE5000E {
  namespace "urn:huawei:yang:huawei-nqa-deviations-NE5000E";
  prefix nqa-devs-NE5000E;

  import huawei-nqa {
    prefix nqa;
  }

  organization
    "Huawei Technologies Co., Ltd.";
  contact
    "Huawei Industrial Base
     Bantian, Longgang
     Shenzhen 518129
     People's Republic of China
     Website: http://www.huawei.com
     Email: support@huawei.com";
  description
    "Network quality analysis.";

  revision 2019-10-29 {
    description
      "Initial revision.";
    reference "Huawei private.";
  }

  typedef pw-type-deviations {
    type enumeration {
      enum vlan {
        value 4;
        description
          "VLAN.";
      }
      enum ethernet {
        value 5;
        description
          "Ethernet.";
      }
      enum hdlc {
        value 6;
        description
          "High - level Data Link Control.";
      }
      enum ppp {
        value 7;
        description
          "Point - to - Point Protocol.";
      }
      enum ip-layer2 {
        value 11;
        description
          "IP layer 2.";
      }
      enum ip-interworking {
        value 64;
        description
          "IP interworking.";
      }
    }
    description
      "Description of pw-type.";
  }

  typedef lsp-reply-mode-type-deviations {
    type enumeration {
      enum no-reply {
        value 1;
        description
          "NQA test packets are not to be responded.";
      }
      enum udp {
        value 2;
        description
          "UDP packets are used to respond NQA test packets.";
      }
    }
    description
      "Description of lsp-reply-mode-type.";
  }

  deviation "/nqa:nqa/nqa:global/nqa:vxlan-echo-v4" {
    deviate not-supported;
  }
  deviation "/nqa:nqa/nqa:global/nqa:gmac-ltm-receive-enable" {
    deviate not-supported;
  }
  deviation "/nqa:nqa/nqa:global/nqa:gmac-ping-enable" {
    deviate not-supported;
  }
  deviation "/nqa:nqa/nqa:global/nqa:gmac-trace-enable" {
    deviate not-supported;
  }
  deviation "/nqa:nqa/nqa:reflectors" {
    deviate not-supported;
  }
  deviation "/nqa:nqa/nqa:instances/nqa:instance/nqa:type/nqa:pwe3-trace/nqa:pwe3-trace-input/nqa:lsp-version" {
    deviate not-supported;
  }
  deviation "/nqa:nqa/nqa:instances/nqa:instance/nqa:type/nqa:pwe3-trace/nqa:pwe3-trace-input/nqa:local-pw-type" {
    deviate replace {
      type nqa-devs-NE5000E:pw-type-deviations;
    }
  }
  deviation "/nqa:nqa/nqa:instances/nqa:instance/nqa:type/nqa:lsp-jitter/nqa:lsp-jitter-input/nqa:lsp-protocol/nqa:te/nqa:te-lsp-jitter/nqa:reply-mode" {
    deviate replace {
      type nqa-devs-NE5000E:lsp-reply-mode-type-deviations;
    }
  }
}
