module zxr10-free-deploy {
  namespace 'http://www.zte.com.cn/zxr10/netconf/schema/rosng/free-deploy' ;
  prefix free-deploy ;
  import zxr10-netconf-defs {
    prefix ncd ;
  }
  organization 'ZTE Corporation' ;
  contact "ZTE Corporation  
\n"
        + "   Nanjing Institute of ZTE Corporation 
\n"
        + "   No.68 Zijinghua Rd. Yuhuatai District, Nanjing, China 
\n"
        + '   Tel: +86-25-52870000'
          ;
  description 'The netconf model to describe free deploy.' ;
  revision 2014-01-17 {
    description 'Increase  the interface filter number' ;
  }
  revision 2013-08-26 {
    description 'Initial version.' ;
  }
  container configuration {
    description 'Configuration model info.' ;
    container free-deploy {
      description 'Free-deploy module' ;
      container interface-free-deploys {
        description 'Interface free-deploys' ;
        list interface-free-deploy {
          description 'Configure of interface free-deploy, for two layer switch'
                    + 'ing properties ports (61 projects), support for Ethernet'
                    + ' physical interface and the SG interface enabled; three '
                    + 'layer routing properties ports (61 and 65 projects), sup'
                    + 'port for ordinary Ethernet physical interface to enable'
                      ;
          key interface-name ;
          leaf interface-name {
            description 'Interface name' ;
            type ncd:ifname {
              length 1..31 ;
            }
          }
          leaf free-deploy-status {
            description 'Interface free-deploy enable or disable' ;
            type enumeration {
              enum disable {
                value 0 ;
                description 'interface free-deploy switch turn off' ;
              }
              enum enable {
                value 1 ;
                description 'interface free-deploy switch turn on' ;
              }
            }
            mandatory true ;
          }
        }
      }
    }
  }
}
