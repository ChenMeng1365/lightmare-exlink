module zxr10-acl-dev-t8k {
  namespace 'http://www.zte.com.cn/zxr10/netconf/schema/rosng/acl-dev-t8k'
            ;
  prefix acl-dev-t8k ;
  import zxr10-acl {
    prefix acl ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'Mse project deviation function.'
              ;
  revision 2015-06-08 {
    description "T8K project deviation function.
\n1.Some mse project doesn't s"
              + "upport some ACL statistics fields, such as stats-bytes, stats-"
              + "rate."
                ;
  }
  deviation '/acl:state/acl:acl/acl:acl-v4-statistics/acl:acl-v4-statistic/acl:'
          + 'stats-bytes'
            {
    description 'Matching packet bytes'
                ;
    deviate not-supported ;
  }
  deviation '/acl:state/acl:acl/acl:acl-v4-statistics/acl:acl-v4-statistic/acl:'
          + 'stats-rate'
            {
    description 'Matching packet rate'
                ;
    deviate not-supported ;
  }
  deviation '/acl:state/acl:acl/acl:acl-v6-statistics/acl:acl-v6-statistic/acl:'
          + 'stats-bytes'
            {
    description 'Matching packet bytes'
                ;
    deviate not-supported ;
  }
  deviation '/acl:state/acl:acl/acl:acl-v6-statistics/acl:acl-v6-statistic/acl:'
          + 'stats-rate'
            {
    description 'Matching packet rate'
                ;
    deviate not-supported ;
  }
}
