module zxr10-lacp {
  namespace 'http://www.zte.com.cn/zxr10/netconf/schema/rosng/lacp'
            ;
  prefix lacp ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe the Link Aggregation Control Prot'
            + 'ocol'
              ;
  revision 2021-01-25 {
    description 'Change the presence of container node configuration/lacp/globa'
              + 'l/mclag/mclag-ccheck-critical to critical-type should be manda'
              + 'tory.'+"\n"
              + 'Add the presence of container node configuration/lacp/global/m'
              + 'clag/mclag-ccheck-normal.'+"\n"
              + 'Change leaf node configuration/lacp/global/mclag/mclag-ccheck-'
              + 'normal/normal-type to mandatory.'+"\n"
              + 'Delete revision-date 2014-06-24.'+"\n"
              + 'Change derived type ncd:ipv6-address to derived type ncd:ipv6-'
              + 'address-none-zero.'+"\n"
              + 'Add length to leaf node configuration/lacp/global/mclag/mclag-'
              + 'ipv4-address/vrf/vrf-choice/vrf-name-case/vrf-name.'+"\n"
              + 'Add length to leaf node configuration/lacp/global/mclag/mclag-'
              + 'ipv6-address/vrf/vrf-choice/vrf-name-case/vrf-name.'+"\n"
              + 'Add length to leaf node configuration/lacp/local/smartgroups/s'
              + 'martgroup/mclag/mclag-ipv4-address/vrf/vrf-choice/vrf-name-cas'
              + 'e/vrf-name.'+"\n"
              + 'Add length to leaf node configuration/lacp/local/smartgroups/s'
              + 'martgroup/mclag/mclag-ipv6-address/vrf/vrf-choice/vrf-name-cas'
              + 'e/vrf-name.'
                ;
  }
  revision 2021-01-08 {
    description 'Add the load-balance node enumeration type gtp.'
                ;
  }
  revision 2020-12-28 {
    description 'Add leaf node configuration/lacp/local/smartgroups/smartgroup/'
              + 'delay-down-time.'
                ;
  }
  revision 2020-10-22 {
    description 'Add container node configuration/lacp/global/mclag/mclag-track'
              + '-groups.'+"\n"
              + 'Add list node configuration/lacp/global/mclag/mclag-track-grou'
              + 'ps/mclag-track-group.'+"\n"
              + 'Add leaf node configuration/lacp/global/mclag/mclag-track-grou'
              + 'ps/mclag-track-group/track-group-name.'+"\n"
              + 'Add leaf node configuration/lacp/global/mclag/mclag-track-grou'
              + 'ps/mclag-track-group/track-group-type.'
                ;
  }
  revision 2020-10-12 {
    description 'Add container node configuration/lacp/local/smartgroups/smartg'
              + 'roup/preempt.'+"\n"
              + 'Add leaf node configuration/lacp/local/smartgroups/smartgroup/'
              + 'preempt/switch.'+"\n"
              + 'Add leaf node configuration/lacp/local/smartgroups/smartgroup/'
              + 'preempt/delay-time.'
                ;
  }
  revision 2020-09-15 {
    description 'Add leaf node configuration/lacp/local/smartgroups/smartgroup/'
              + 'smartgroup-constant-up.'
                ;
  }
  revision 2020-09-09 {
    description 'Add leaf node configuration/lacp/local/smartgroups/smartgroup/'
              + 'admin-status-linkage.'
                ;
  }
  revision 2020-08-31 {
    description 'Add container node configuration/lacp/local/smartgroups/smartg'
              + 'roup/lag-bfd.'+"\n"
              + 'Add container node configuration/lacp/local/smartgroups/smartg'
              + 'roup/lag-bfd-ipv6.'+"\n"
              + 'Change the container node configuration/lacp/local/ports/port/'
              + 'lag-bfd/time to container node configuration/lacp/local/ports/'
              + 'port/lag-bfd/time-type-choice/time-case/time.'+"\n"
              + 'Add leaf node configuration/lacp/local/ports/port/lag-bfd/time'
              + '-type-choice/template-case/template.'+"\n"
              + 'Add container node configuration/lacp/local/ports/port/lag-bfd'
              + '-ipv6.'
                ;
  }
  revision 2020-06-30 {
    description 'Add container node configuration/lacp/global/mclag.'+"\n"
              + 'Add container node configuration/lacp/global/mclag/mclag-backo'
              + 'ff.'+"\n"
              + 'Add container node configuration/lacp/global/mclag/mclag-consi'
              + 'stency-check.'+"\n"
              + 'Add container node configuration/lacp/global/mclag/mclag-delay'
              + '-time.'+"\n"
              + 'Add container node configuration/lacp/global/mclag/mclag-dual-'
              + 'malfunction-protect.'+"\n"
              + 'Add container node configuration/lacp/global/mclag/mclag-exemp'
              + 'ts.'+"\n"
              + 'Add container node configuration/lacp/global/mclag/mclag-ipv4-'
              + 'address.'+"\n"
              + 'Add container node configuration/lacp/global/mclag/mclag-ipv6-'
              + 'address.'+"\n"
              + 'Add container node configuration/lacp/global/mclag/mclag-prior'
              + 'ity.'+"\n"
              + 'Add container node configuration/lacp/global/mclag/mclag-track'
              + 's.'+"\n"
              + 'Add container node configuration/lacp/global/mclag/mclag-udp.'+"\n"
              + 'Add container node configuration/lacp/local/smartgroups/smartg'
              + 'roup/mclag/mclag-ipv4-address.'+"\n"
              + 'Add container node configuration/lacp/local/smartgroups/smartg'
              + 'roup/mclag/mclag-ipv6-address.'+"\n"
              + 'Add leaf node configuration/lacp/local/smartgroups/smartgroup/'
              + 'fsm-mode.'+"\n"
              + 'Add leaf node configuration/lacp/local/smartgroups/smartgroup/'
              + 'speed-reassign.'+"\n"
              + 'Add enumeration type peer-type of the leaf node configuration/'
              + 'lacp/local/smartgroups/smartgroup/mclag/tracks/track/track-typ'
              + 'e.'+"\n"
              + 'Add leaf node state/lacp/mclag/actor-roid.'+"\n"
              + 'Add leaf node state/lacp/mclag/actor-node-id.'
                ;
  }
  revision 2020-06-19 {
    description 'Add leaf node configuration\lacp\local\ports\port\description'
                ;
  }
  revision 2020-04-24 {
    description 'Add container mclag-ip-use-global.'
                ;
  }
  revision 2020-01-02 {
    description 'Add container protocol-packet.'
                ;
  }
  revision 2019-04-23 {
    description 'Obsolete the enum item peer-link-type of the leaf mclag-tracks'
              + '/track-type.'
                ;
  }
  revision 2019-04-16 {
    description 'Add the range of leaf node smartgroup-id from 1025 to 2048 and'
              + ' change the corresponding description.'+"\n"
              + 'Add the range of leaf node group-id from 1025 to 2048 and chan'
              + 'ge the corresponding description.'
                ;
  }
  revision 2018-12-21 {
    description 'Obsolete leaf node system-active-number.'
                ;
  }
  revision 2018-11-20 {
    description 'Add leaf node state/mclag/work-mode.'+"\n"
              + 'Add leaf node state/mclag/state.'+"\n"
              + 'Add leaf node state/mclag/actor-smartgroup-state.'+"\n"
              + 'Add leaf node state/mclag/partner-smartgroup-state.'
                ;
  }
  revision 2018-10-30 {
    description 'Add the load-balance node enumeration type dlb-flow-fixed.'+"\n"
              + 'Add the load-balance node enumeration type dlb-flow-timeout.'+"\n"
              + 'Add the load-balance node enumeration type dlb-packet.'
                ;
  }
  revision 2018-10-25 {
    description 'Change the range of leaf node system-active-number from 1-16 t'
              + 'o 1-1024.'+"\n"
              + 'Change the range of leaf node active-number from 1-16 to 1-102'
              + '4.'+"\n"
              + 'Change the range of leaf node active-limit from 1-16 to 1-1024'
              + '.'+"\n"
              + 'Change the range of leaf node smartgroup-id from 1-64 to 1-102'
              + '4.'+"\n"
              + 'Change the range of leaf node group-id from 1-64 to 1-1024.'+"\n"
              + 'Change the range of leaf node min-tx from 10-990 to 1-65535.'+"\n"
              + 'Change the range of leaf node min-rx from 10-990 to 1-65535.'
                ;
  }
  revision 2018-09-13 {
    description 'Add data selector leaf node.'+"\n"
              + 'Obsolete the container of mclag-receive-flag.'
                ;
  }
  revision 2018-07-18 {
    description 'Add LACP service-switch leaf node.'
                ;
  }
  revision 2018-06-12 {
    description 'Add alarm-to-notification leaf node.'
                ;
  }
  revision 2018-01-08 {
    description 'Add mclag-multi-link-role container node.'+"\n"
              + 'Add mclag-receive-flag container node.'+"\n"
              + 'Add protect-state leaf node.'
                ;
  }
  revision 2017-07-20 {
    description 'Add sd-detection leaf node.'
                ;
  }
  revision 2017-07-12 {
    description 'Add container peer-link.
Add mc-lag track peer-link-type.'
                ;
  }
  revision 2017-03-01 {
    description '1. Obsolete the container of old mclag-track and add the new m'
              + 'clag-tracks.'
                ;
  }
  revision 2016-11-16 {
    description 'Add list member.'
                ;
  }
  revision 2016-10-10 {
    description 'Add unconditional-active leaf node.'+"\n"
              + 'Modify description of the negotiation-flag leaf node.'+"\n"
              + 'Modify description of the negotiation-mac leaf node.'
                ;
  }
  revision 2016-09-19 {
    description 'Add negotiation-mac leaf node.'
                ;
  }
  revision 2016-08-25 {
    description 'Add negotiation-flag leaf node.'
                ;
  }
  revision 2016-03-28 {
    description 'Add port-dispersion leaf node.'
                ;
  }
  revision 2015-12-30 {
    description 'Add the load-balance node enumeration type dst-ip-dst-port.'+"\n"
              + 'Add the load-balance node enumeration type src-ip-src-port.'+"\n"
              + 'Add the load-balance node enumeration type src-dst-ip-src-dst-'
              + 'port.'
                ;
  }
  revision 2015-03-03 {
    description 'Add mclag-track.
Add track and lag-bfd.'
                ;
  }
  revision 2015-01-08 {
    description 'Modify descriptions of the nodes.'
                ;
  }
  revision 2014-03-17 {
    description 'Modify range of hold-off;'+"\n"
              + 'Modify if-filter-id of state smartgroup interface-name;'+"\n"
              + 'Modify if-filter-id of state port interface-name;'+"\n"
              + 'Modify if-filter-id of state mclag interface-name;'+"\n"
              + 'Add choice node clear-choice and move it to clear;'+"\n"
              + 'Add case node group-id-case and move it to clear-choice;'+"\n"
              + 'Move group-id to group-id-case;'+"\n"
              + 'Add case node all-case and move it to clear;'+"\n"
              + 'Add leaf node all and move it to all-case;'+"\n"
              + 'Add Perf-code of clear group-id;'+"\n"
              + 'Modify description of clear;'+"\n"
              + 'Modify description of clear group-id;'+"\n"
              + 'Add if-filter-id of forceswitch interface-name.'
                ;
  }
  revision 2014-02-28 {
    description 'Change choice name restore to restore-choice;'+"\n"
              + 'Change case name revertive to revertive-case;'+"\n"
              + 'Change case name immediately to immediately-case;'+"\n"
              + 'Change case name non-revertive to non-revertive-case;'+"\n"
              + 'Change leaf name hold-time to restore-time;'+"\n"
              + 'Add container restore and move restore-choice to restore;'+"\n"
              + 'Add reset-value of fast-respond;'+"\n"
              + 'Add reset-value of revertive;'+"\n"
              + 'Add reset-value of immediately;'+"\n"
              + 'Add reset-value of non-revertive;'+"\n"
              + 'Add reset-value of back-up.'
                ;
  }
  revision 2014-01-20 {
    description 'Add container local;'+"\n"
              + 'Add container smartgroups;'+"\n"
              + 'Add container ports;'+"\n"
              + 'Move smartgroup to smartgroups;'+"\n"
              + 'Move port to ports;'+"\n"
              + 'Move smartgroups and ports to local;'+"\n"
              + 'Modify revertive keyref path;'+"\n"
              + 'Modify immediately keyref path;'+"\n"
              + 'Modify non-revertive keyref path;'+"\n"
              + 'Modify mclag-system keyref path;'+"\n"
              + 'Modify mclag-roid keyref path;'+"\n"
              + 'Modify mclag-iccp keyref path;'+"\n"
              + 'Modify mclag-attr keyref path;'+"\n"
              + 'Modify range of active-limit;'+"\n"
              + 'Add leaf smartgroup-id and move it to state node port.'
                ;
  }
  revision 2014-01-09 {
    description 'Modify range of system-active-number;'+"\n"
              + 'Modify Perf-code of system-active-number;'+"\n"
              + 'Modify enum order and description of load-balance;'+"\n"
              + 'Modify Perf-code of load-balance;'+"\n"
              + 'Modify range and default value of active-number;'+"\n"
              + 'Modify Perf-code of active-number;'+"\n"
              + 'Modify range of active-limit;'+"\n"
              + 'Modify Perf-code of active-limit;'+"\n"
              + 'Modify range of hold-off;'+"\n"
              + 'Modify range of smartgroup-id;'+"\n"
              + 'Modify Perf-code of smartgroup-id;'+"\n"
              + 'Modify if-filter-id of smartgroup interface-name;'+"\n"
              + 'Modify if-filter-id of port interface-name;'+"\n"
              + 'Modify enum order of lacp-state.'
                ;
  }
  revision 2013-10-22 {
    description 'Modify system-active-number and active-number node range from '
              + '1 .. 32 to 1 .. 65535;'+"\n"
              + 'Add the load-balance node enumeration type per-subinterface;'+"\n"
              + 'Add the default value of active-number and load-balance node;'+"\n"
              + 'Modify the data type of the mac node and partner-system-mac no'
              + 'de from string to mac-address.'+"\n"
              + 'Change mclag-system node from choice to container.'+"\n"
              + 'Change mclag-roid node from choice to container.'+"\n"
              + 'Change mclag-iccp node from choice to container.'+"\n"
              + 'Change mclag-attr node from choice to container.'
                ;
  }
  revision 2013-06-19 {
    description 'The initial version'
                ;
  }
  feature lacp-protocol-packet {
    description 'Set the rule of the control plane sending protocol packet for '
              + 'smartgroup.'
                ;
  }
  container configuration {
    description 'Describe the configuration of Link Aggregation Control Protoco'
              + 'l.'
                ;
    container lacp {
      description 'Describe the parameters of LACP to be configured.'
                  ;
      container global {
        description 'Describe the global parameters to be configured.'
                    ;
        leaf system-priority {
          description 'The global system priority. In the case of the smartgrou'
                    + 'p-priority leaf of smartgroup list is not configured, th'
                    + 'is value will be used.'
                      ;
          type uint16 {
            range 1..65535 ;
          }
          default 32768 ;
        }
        leaf system-active-number {
          status obsolete {
            ncd:revise-date 2018-12-21 ;
          }
          description 'The global system active number, its maximum value depen'
                    + 'ds on the performance parameters. In the case of the act'
                    + 'ive-number leaf of smartgroup list is not configured, th'
                    + 'is value will be used.'
                      ;
          type uint32 {
            range 1..1024 {
              description 'The maximum value depends on the performance paramet'
                        + 'ers.'
                          ;
            }
          }
          default 1 ;
        }
        leaf alarm-to-notification {
          description 'The flag that turns alarm to notification, its default v'
                    + 'alue depends on the performance parameters.'
                      ;
          type enumeration {
            enum disable {
              value 0 ;
              description 'Disable the alarm to notification function.'
                          ;
            }
            enum enable {
              value 1 ;
              description 'Enable the alarm to notification function.'
                          ;
            }
          }
          ncd:revise-date 2018-06-12 ;
        }
        leaf service-switch {
          description 'LACP service switch, its default value depends on the pe'
                    + 'rformance parameters.'
                      ;
          type enumeration {
            enum disable {
              value 0 ;
              description 'Disable LACP service.'
                          ;
            }
            enum enable {
              value 1 ;
              description 'Enable LACP service.'
                          ;
            }
          }
          ncd:revise-date 2018-07-18 ;
        }
        container mclag {
          description 'Describe the parameters of global MC-LAG to be configure'
                    + 'd.'
                      ;
          container mclag-backoff {
            description 'Describe the parameters of global MC-LAG backoff to be'
                      + ' configured.'
                        ;
            leaf backoff {
              description 'The backoff of global MC-LAG.'
                          ;
              type enumeration {
                enum disable {
                  value 1 ;
                  description 'Disable global MC-LAG backoff .'
                              ;
                }
                enum enable {
                  value 0 ;
                  description 'Enable global MC-LAG backoff.'
                              ;
                }
              }
              default enable ;
            }
          }
          container mclag-ccheck-critical {
            description 'Describe the parameters of global MC-LAG consistency c'
                      + 'heck to be configured.'
                        ;
            presence 'critical-type should be mandatory'
                     ;
            leaf critical-type {
              description 'The consistency check type of global MC-LAG is criti'
                        + 'cal.'
                          ;
              type empty ;
              mandatory true ;
            }
            leaf mode {
              description 'The consistency check mode of global MC-LAG.'
                          ;
              type enumeration {
                enum loose {
                  value 0 ;
                  description 'The consistency check mode of global MC-LAG is l'
                            + 'oose.'
                              ;
                }
                enum strict {
                  value 1 ;
                  description 'The consistency check mode of global MC-LAG is s'
                            + 'trict.'
                              ;
                }
              }
              default loose ;
            }
          }
          container mclag-ccheck-normal {
            description 'Describe the parameters of global MC-LAG consistency c'
                      + 'heck to be configured.'
                        ;
            presence 'normal-type should be mandatory'
                     ;
            leaf normal-type {
              description 'The consistency check type of global MC-LAG is norma'
                        + 'l.'
                          ;
              type empty ;
              mandatory true ;
            }
          }
          container mclag-delay-time {
            description 'Describe the parameters of global MC-LAG delay time to'
                      + ' be configured.'
                        ;
            leaf delay-down-time {
              description 'The delay down time to global MC-LAG, its default va'
                        + 'lue depends on the performance parameters.'
                          ;
              type uint16 {
                range 0..180 ;
              }
              units second ;
              default 3 ;
            }
            leaf delay-up-time {
              description 'The delay up time to global MC-LAG, its default valu'
                        + 'e depends on the performance parameters.'
                          ;
              type uint16 {
                range 0..3600 ;
              }
              units second ;
              default 480 ;
            }
            leaf reload-delay-up-time {
              description 'The reload delay up time to global MC-LAG, its defau'
                        + 'lt value depends on the performance parameters.'
                          ;
              type uint16 {
                range 0..3600 ;
              }
              units second ;
              default 480 ;
            }
          }
          container mclag-dual-malfunction-protect {
            description 'Describe the parameters of global MC-LAG dual malfunct'
                      + 'ion protect to be configured.'
                        ;
            leaf dual-malfunction-protect {
              description 'The dual malfunction protect of global MC-LAG,its de'
                        + 'fault value depends on the performance parameters.'
                          ;
              type enumeration {
                enum disable {
                  value 0 ;
                  description 'The dual malfunction protect of global MC-LAG is'
                            + ' disable.'
                              ;
                }
                enum enable {
                  value 1 ;
                  description 'The dual malfunction protect of global MC-LAG is'
                            + ' enable.'
                              ;
                }
              }
              default enable ;
            }
          }
          container mclag-exempts {
            description 'Describe the parameters of global MC-LAG exempt interf'
                      + 'ace to be configured.'
                        ;
            list mclag-exempt {
              description 'Describe the parameters of global MC-LAG exempt inte'
                        + 'rface to be configured.'
                          ;
              key interface-name ;
              leaf interface-name {
                description 'The exempt interface of global MC-LAG.'
                            ;
                type ncd:ifname ;
              }
            }
          }
          container mclag-ipv4-address {
            description 'Describe the parameters of global MC-LAG IPv4 source a'
                      + 'nd destination address to be configured.'
                        ;
            presence 'source-address and destination-address should be mandatory'
                     ;
            leaf source-address {
              description 'The IPv4 source address of global MC-LAG.'
                          ;
              type ncd:ipv4-address ;
              mandatory true ;
            }
            leaf destination-address {
              description 'The IPv4 destination address of global MC-LAG.'
                          ;
              type ncd:ipv4-address ;
              mandatory true ;
            }
            container vrf {
              description 'Describe the parameters of global MC-LAG VRF name to'
                        + ' be configured.'
                          ;
              choice vrf-choice {
                description 'The VRF name of global MC-LAG.'
                            ;
                case vrf-name-case {
                  description 'The VRF name of global MC-LAG, whose name cannot'
                            + ' be mng.'
                              ;
                  leaf vrf-name {
                    description 'The VRF name of global MC-LAG, whose name cann'
                              + 'ot be mng.'
                                ;
                    type string {
                      length 1..32 ;
                    }
                  }
                }
                case vrf-mng-case {
                  description 'The VRF mng instance of global MC-LAG.'
                              ;
                  leaf vrf-mng {
                    description 'The VRF mng instance of global MC-LAG.'
                                ;
                    type empty ;
                  }
                }
              }
            }
          }
          container mclag-ipv6-address {
            description 'Describe the parameters of global MC-LAG IPv6 source a'
                      + 'nd destination address to be configured.'
                        ;
            presence 'source-address and destination-address should be mandatory'
                     ;
            leaf source-address {
              description 'The IPv6 source address of global MC-LAG.'
                          ;
              type ncd:ipv6-address-none-zero ;
              mandatory true ;
            }
            leaf destination-address {
              description 'The IPv6 destination address of global MC-LAG.'
                          ;
              type ncd:ipv6-address-none-zero ;
              mandatory true ;
            }
            container vrf {
              description 'Describe the parameters of global MC-LAG VRF name to'
                        + ' be configured.'
                          ;
              choice vrf-choice {
                description 'The VRF name of global MC-LAG.'
                            ;
                case vrf-name-case {
                  description 'The VRF name of global MC-LAG, whose name cannot'
                            + ' be mng.'
                              ;
                  leaf vrf-name {
                    description 'The VRF name of global MC-LAG, whose name cann'
                              + 'ot be mng.'
                                ;
                    type string {
                      length 1..32 ;
                    }
                  }
                }
                case vrf-mng-case {
                  description 'The VRF mng instance of global MC-LAG.'
                              ;
                  leaf vrf-mng {
                    description 'The VRF mng instance of global MC-LAG.'
                                ;
                    type empty ;
                  }
                }
              }
            }
          }
          container mclag-priority {
            description 'Describe the parameters of global MC-LAG priority to b'
                      + 'e configured.'
                        ;
            leaf priority {
              description 'The priority of global MC-LAG.'
                          ;
              type uint32 {
                range 1..65535 ;
              }
              default 32768 ;
            }
          }
          container mclag-tracks {
            description 'Describe the parameters of global MC-LAG track to be c'
                      + 'onfigured.'
                        ;
            presence 'track-name and track-type should be mandatory'
                     ;
            list mclag-track {
              description 'Describe the parameters of global MC-LAG track to be'
                        + ' configured.'
                          ;
              key track-name ;
              leaf track-name {
                description 'The track name of global MC-LAG.'
                            ;
                type string {
                  length 1..31 ;
                }
              }
              leaf track-type {
                description 'The track type of global MC-LAG.'
                            ;
                type enumeration {
                  enum peer-type {
                    value 3 ;
                    description 'The track type of global MC-LAG is peer-type.'
                                ;
                  }
                }
                mandatory true ;
              }
            }
          }
          container mclag-udp {
            description 'Describe the parameters of global MC-LAG udp port swit'
                      + 'ch to be configured.'
                        ;
            leaf udp {
              description 'The udp port switch to global MC-LAG, its default va'
                        + 'lue depends on the performance parameters.'
                          ;
              type enumeration {
                enum disable {
                  value 0 ;
                  description 'The udp port switch of global MC-LAG is disable.'
                              ;
                }
                enum enable {
                  value 1 ;
                  description 'The udp port switch of global MC-LAG is enable.'
                              ;
                }
              }
              default enable ;
            }
          }
          container mclag-track-groups {
            description 'Describe the parameters of global MC-LAG track-group t'
                      + 'o be configured.'
                        ;
            presence 'track-group-name and track-group-type should be mandatory'
                     ;
            list mclag-track-group {
              description 'Describe the parameters of global MC-LAG track-group'
                        + ' to be configured.'
                          ;
              key track-group-name ;
              leaf track-group-name {
                description 'The track-group name of global MC-LAG.'
                            ;
                type string {
                  length 1..31 ;
                }
              }
              leaf track-group-type {
                description 'The track-group type of global MC-LAG.'
                            ;
                type enumeration {
                  enum controller-type {
                    value 1 ;
                    description 'The track-group type of global MC-LAG is contr'
                              + 'oller-type.'
                                ;
                  }
                }
                mandatory true ;
              }
            }
            ncd:revise-date 2020-10-22 ;
          }
          ncd:revise-date 2020-06-30 ;
        }
      }
      container local {
        description 'Describe the parameters of smartgroup and member port to b'
                  + 'e configured.'
                    ;
        container smartgroups {
          description 'Describe the parameters of smartgroup to be configured.'
                      ;
          list smartgroup {
            description 'Describe the parameters of smartgroup to be configured'
                      + '. The smartgroup interface is created and deleted by I'
                      + 'nterface Management.'
                        ;
            key interface-name ;
            leaf interface-name {
              description 'The interface name of smartgroup.'
                          ;
              type ncd:ifname ;
            }
            leaf bond-mode {
              description 'The bond mode of smartgroup. Smartgroup has two mode'
                        + 's, on and 802.3ad.'
                          ;
              type enumeration {
                enum on {
                  value 0 ;
                  description 'The aggregated mode is on.'
                              ;
                }
                enum 802.3ad {
                  value 1 ;
                  description 'The aggregated mode is 802.3ad.'
                              ;
                }
              }
              default on ;
            }
            leaf load-balance {
              description 'The load sharing strategy of smartgroup, its default'
                        + ' value depends on the performance parameters.'
                          ;
              type enumeration {
                enum dst-ip {
                  value 1 ;
                  description 'The load-balance mode is dst-ip.'
                              ;
                }
                enum dst-mac {
                  value 2 ;
                  description 'The load-balance mode is dst-mac.'
                              ;
                }
                enum src-dst-ip {
                  value 3 ;
                  description 'The load-balance mode is src-dst-ip.'
                              ;
                }
                enum src-dst-mac {
                  value 4 ;
                  description 'The load-balance mode is src-dst-mac.'
                              ;
                }
                enum src-ip {
                  value 5 ;
                  description 'The load-balance mode is src-ip.'
                              ;
                }
                enum src-mac {
                  value 6 ;
                  description 'The load-balance mode is src-mac.'
                              ;
                }
                enum src-port {
                  value 7 ;
                  description 'The load-balance mode is src-port.'
                              ;
                }
                enum dst-port {
                  value 8 ;
                  description 'The load-balance mode is dst-port.'
                              ;
                }
                enum src-dst-port {
                  value 9 ;
                  description 'The load-balance mode is src-dst-port.'
                              ;
                }
                enum per-destination {
                  value 10 ;
                  description 'The load-balance mode is per-destination.'
                              ;
                }
                enum per-packet {
                  value 11 ;
                  description 'The load-balance mode is per-packet.'
                              ;
                }
                enum pri-label {
                  value 12 ;
                  description 'The load-balance mode is pri-label.'
                              ;
                }
                enum pub-label {
                  value 13 ;
                  description 'The load-balance mode is pub-label.'
                              ;
                }
                enum pub-pri-label {
                  value 14 ;
                  description 'The load-balance mode is pub-pri-label.'
                              ;
                }
                enum vlan {
                  value 15 ;
                  description 'The load-balance mode is vlan.'
                              ;
                }
                enum mac-vlan {
                  value 16 ;
                  description 'The load-balance mode is mac-vlan.'
                              ;
                }
                enum intelligent-hash {
                  value 17 ;
                  description 'The load-balance mode is intelligent-hash.'
                              ;
                }
                enum per-subinterface {
                  value 18 ;
                  description 'The load-balance mode is per-subinterface.'
                              ;
                }
                enum dst-ip-dst-port {
                  value 19 ;
                  description 'The load-balance mode is dst-ip-dst-port.'
                              ;
                }
                enum src-ip-src-port {
                  value 20 ;
                  description 'The load-balance mode is src-ip-src-port.'
                              ;
                }
                enum src-dst-ip-src-dst-port {
                  value 21 ;
                  description 'The load-balance mode is src-dst-ip-src-dst-port.'
                              ;
                }
                enum enhance {
                  value 24 ;
                  description 'The load-balance mode is enhance.'
                              ;
                }
                enum dlb-flow-fixed {
                  value 25 ;
                  description 'The load-balance mode is dlb-flow-fixed.'
                              ;
                }
                enum dlb-flow-timeout {
                  value 26 ;
                  description 'The load-balance mode is dlb-flow-timeout.'
                              ;
                }
                enum dlb-packet {
                  value 27 ;
                  description 'The load-balance mode is dlb-packet.'
                              ;
                }
                enum gtp {
                  value 28 ;
                  description 'The load-balance mode is gtp.'
                              ;
                }
              }
              default per-destination ;
            }
            leaf active-number {
              description 'The active number of smartgroup, its maximum value d'
                        + 'epends on the performance parameters.'
                          ;
              type uint32 {
                range 1..1024 {
                  description 'The maximum value depends on the performance par'
                            + 'ameters.'
                              ;
                }
              }
              default 1 ;
            }
            leaf active-limit {
              description 'The active limit of smartgroup, its maximum value an'
                        + 'd default value depend on the performance parameters'
                        + '.'
                          ;
              type uint32 {
                range 0..1024 {
                  description 'The maximum value and default value depend on th'
                            + 'e performance parameters.'
                              ;
                }
              }
              default 16 ;
            }
            leaf fast-respond {
              description 'The fast respond of smartgroup. Only the value of bo'
                        + 'nd-mode leaf is 802.3ad can this attribute be config'
                        + 'ured.'
                          ;
              type empty ;
            }
            container restore {
              description 'The restore mode of smartgroup.'
                          ;
              choice restore-choice {
                description 'The restore mode of smartgroup.'
                            ;
                default immediately-case ;
                case revertive-case {
                  description 'The restore mode of smartgroup is revertive.'
                              ;
                  leaf revertive {
                    description 'The restore mode of smartgroup is revertive.'
                                ;
                    type empty ;
                    mandatory true ;
                  }
                  leaf restore-time {
                    description 'The revertive time of smartgroup.'
                                ;
                    type uint32 {
                      range 1..65535 ;
                    }
                    units second ;
                    mandatory true ;
                  }
                }
                case immediately-case {
                  description 'The restore mode of smartgroup is immediately.'
                              ;
                  leaf immediately {
                    description 'The restore mode of smartgroup is immediately.'
                                ;
                    type empty ;
                  }
                }
                case non-revertive-case {
                  description 'The restore mode of smartgroup is non-revertive.'
                              ;
                  leaf non-revertive {
                    description 'The restore mode of smartgroup is non-revertiv'
                              + 'e.'
                                ;
                    type empty ;
                  }
                }
              }
            }
            leaf smartgroup-priority {
              description 'The priority of smartgroup.'
                          ;
              type uint16 {
                range 1..65535 ;
              }
              default 32768 ;
            }
            leaf agg-timeout {
              description 'The aggregator timeout of smartgroup.'
                          ;
              type uint16 {
                range 10..500 ;
              }
              units second ;
              default 30 ;
            }
            leaf hold-off {
              description 'The hold-off time of smartgroup.'
                          ;
              type uint32 {
                range 0..65535 ;
              }
              units second ;
              default 0 ;
            }
            container mclag {
              description 'Describe the parameters of MC-LAG to be configured.'
                          ;
              container mclag-system {
                description 'Describe the parameters of MC-LAG system to be con'
                          + 'figured.'
                            ;
                presence 'system-id and system-priority should be mandatory'
                         ;
                leaf system-id {
                  description 'The system MAC of MC-LAG.'
                              ;
                  type ncd:mac-address ;
                  mandatory true ;
                }
                leaf system-priority {
                  description 'The system priority of MC-LAG.'
                              ;
                  type uint16 {
                    range 1..65535 ;
                  }
                  mandatory true ;
                }
              }
              container mclag-roid {
                description 'Describe the parameters of MC-LAG identifier to be'
                          + ' configured.'
                            ;
                presence 'roid and node-id should be mandatory'
                         ;
                leaf roid {
                  description 'The roid of MC-LAG.'
                              ;
                  type uint64 {
                    range 1..4294967293 ;
                  }
                  mandatory true ;
                }
                leaf node-id {
                  description 'The node id of MC-LAG.'
                              ;
                  type uint32 {
                    range 0..7 ;
                  }
                  mandatory true ;
                }
              }
              container mclag-iccp {
                description 'Describe the parameters of MC-LAG ICCP to be confi'
                          + 'gured.'
                            ;
                leaf iccp {
                  description 'The ICCP id of MC-LAG.'
                              ;
                  type uint32 {
                    range 1..4294967293 ;
                  }
                }
              }
              container mclag-attr {
                description 'Describe the parameters of MC-LAG attributes to be'
                          + ' configured.'
                            ;
                leaf mode {
                  description 'The mode of MC-LAG. MC-LAG has three modes, auto'
                            + ' and force-master and force-slave.'
                              ;
                  type enumeration {
                    enum auto {
                      value 1 ;
                      description 'The MC-LAG mode is auto.'
                                  ;
                    }
                    enum force-master {
                      value 2 ;
                      description 'The MC-LAG mode is force-master.'
                                  ;
                    }
                    enum force-slave {
                      value 3 ;
                      description 'The MC-LAG mode is force-slave.'
                                  ;
                    }
                  }
                  default auto ;
                }
                leaf priority {
                  description 'The priority of MC-LAG.'
                              ;
                  type uint32 {
                    range 1..65535 ;
                  }
                  default 32768 ;
                }
              }
              container mclag-track {
                status obsolete {
                  ncd:revise-date 2017-03-01 ;
                }
                description 'Describe the parameters of MC-LAG track to be conf'
                          + 'igured.'
                            ;
                presence 'track-name and track-type should be mandatory'
                         ;
                leaf track-name {
                  description 'The track name of MC-LAG.'
                              ;
                  type string {
                    length 1..31 ;
                  }
                  mandatory true ;
                }
                leaf track-type {
                  description 'The track type of MC-LAG.'
                              ;
                  type enumeration {
                    enum pw-type {
                      value 1 ;
                      description 'The track type of MC-LAG is pw-type.'
                                  ;
                    }
                  }
                  mandatory true ;
                }
              }
              container mclag-tracks {
                description 'Describe the parameters of MC-LAG track to be conf'
                          + 'igured.'
                            ;
                presence 'track-type should be mandatory'
                         ;
                list mclag-track {
                  description 'Describe the parameters of MC-LAG track to be co'
                            + 'nfigured.'
                              ;
                  key track-name ;
                  leaf track-name {
                    description 'The track name of MC-LAG.'
                                ;
                    type string {
                      length 1..31 ;
                    }
                  }
                  leaf track-type {
                    description 'The track type of MC-LAG.'
                                ;
                    type enumeration {
                      enum pw-type {
                        value 1 ;
                        description 'The track type of MC-LAG is pw-type.'
                                    ;
                      }
                      enum peer-link-type {
                        value 2 ;
                        description 'The track type of MC-LAG is peer-link-type.'
                                    ;
                        status obsolete ;
                      }
                      enum peer-type {
                        value 3 ;
                        description 'The track type of MC-LAG is peer-type.'
                                    ;
                      }
                    }
                    mandatory true ;
                  }
                }
                ncd:revise-date 2017-03-01 ;
              }
              container mclag-multi-link-role {
                description 'Describe the parameters of MC-LAG multi-link-role '
                          + 'to be configured.'
                            ;
                leaf multi-link-role {
                  description 'The multi-link-role of MC-LAG.'
                              ;
                  type enumeration {
                    enum master {
                      value 1 ;
                      description 'The MC-LAG multi-link-role is master.'
                                  ;
                    }
                    enum slave {
                      value 2 ;
                      description 'The MC-LAG multi-link-role is slave.'
                                  ;
                    }
                  }
                }
                ncd:revise-date 2018-01-08 ;
              }
              container mclag-receive-flag {
                status obsolete {
                  ncd:revise-date 2018-09-13 ;
                }
                description 'Describe the parameters of MC-LAG receive flag to '
                          + 'be configured.'
                            ;
                leaf receive-flag {
                  description 'The receive flag of MC-LAG.'
                              ;
                  type empty ;
                }
                ncd:revise-date 2018-01-08 ;
              }
              container mclag-ip-use-global {
                description 'The IP address of MC-LAG uses the IP address confi'
                          + 'gured globally.'
                            ;
                leaf ip-use-global {
                  description 'The IP address of MC-LAG uses the IP address con'
                            + 'figured globally.'
                              ;
                  type empty ;
                }
                ncd:revise-date 2020-04-24 ;
              }
              container mclag-ipv4-address {
                description 'Describe the parameters of MC-LAG IPv4 source and '
                          + 'destination address to be configured.'
                            ;
                presence 'source-address and destination-address should be mand'
                       + 'atory'
                         ;
                leaf source-address {
                  description 'The IPv4 source address of MC-LAG.'
                              ;
                  type ncd:ipv4-address ;
                  mandatory true ;
                }
                leaf destination-address {
                  description 'The IPv4 destination address of MC-LAG.'
                              ;
                  type ncd:ipv4-address ;
                  mandatory true ;
                }
                container vrf {
                  description 'Describe the parameters of MC-LAG VRF name to be'
                            + ' configured.'
                              ;
                  choice vrf-choice {
                    description 'The VRF name of MC-LAG.'
                                ;
                    case vrf-name-case {
                      description 'The VRF name of MC-LAG, whose name cannot be'
                                + ' mng.'
                                  ;
                      leaf vrf-name {
                        description 'The VRF name of MC-LAG, whose name cannot '
                                  + 'be mng.'
                                    ;
                        type string {
                          length 1..32 ;
                        }
                      }
                    }
                    case vrf-mng-case {
                      description 'The VRF mng instance of MC-LAG.'
                                  ;
                      leaf vrf-mng {
                        description 'The VRF mng instance of MC-LAG.'
                                    ;
                        type empty ;
                      }
                    }
                  }
                }
                ncd:revise-date 2020-06-30 ;
              }
              container mclag-ipv6-address {
                description 'Describe the parameters of MC-LAG IPv6 source and '
                          + 'destination address to be configured.'
                            ;
                presence 'source-address and destination-address should be mand'
                       + 'atory'
                         ;
                leaf source-address {
                  description 'The IPv6 source address of MC-LAG.'
                              ;
                  type ncd:ipv6-address-none-zero ;
                  mandatory true ;
                }
                leaf destination-address {
                  description 'The IPv6 destination address of MC-LAG.'
                              ;
                  type ncd:ipv6-address-none-zero ;
                  mandatory true ;
                }
                container vrf {
                  description 'Describe the parameters of MC-LAG VRF name to be'
                            + ' configured.'
                              ;
                  choice vrf-choice {
                    description 'The VRF name of MC-LAG.'
                                ;
                    case vrf-name-case {
                      description 'The VRF name of MC-LAG, whose name cannot be'
                                + ' mng.'
                                  ;
                      leaf vrf-name {
                        description 'The VRF name of MC-LAG, whose name cannot '
                                  + 'be mng.'
                                    ;
                        type string {
                          length 1..32 ;
                        }
                      }
                    }
                    case vrf-mng-case {
                      description 'The VRF mng instance of MC-LAG.'
                                  ;
                      leaf vrf-mng {
                        description 'The VRF mng instance of MC-LAG.'
                                    ;
                        type empty ;
                      }
                    }
                  }
                }
                ncd:revise-date 2020-06-30 ;
              }
            }
            leaf port-dispersion {
              description 'The port dispersion switch of smartgroup.'
                          ;
              type enumeration {
                enum off {
                  value 0 ;
                  description 'Close the port dispersion switch.'
                              ;
                }
                enum on {
                  value 1 ;
                  description 'Open the port dispersion switch.'
                              ;
                }
              }
              default off ;
              ncd:revise-date 2016-03-28 ;
            }
            leaf negotiation-flag {
              description 'The negotiation flag of smartgroup.Only the value of'
                        + ' bond-mode leaf is 802.3ad can this attribute be con'
                        + 'figured.'
                          ;
              type uint8 {
                range 0..1 ;
              }
              default 0 ;
              ncd:revise-date 2016-08-25 ;
            }
            leaf sd-detection {
              description 'The SD detection switch of smartgroup.'
                          ;
              type enumeration {
                enum disable {
                  value 0 ;
                  description 'Close the SD detection switch.'
                              ;
                }
                enum enable {
                  value 1 ;
                  description 'Open the SD detection switch.'
                              ;
                }
              }
              default disable ;
              ncd:revise-date 2017-07-20 ;
            }
            leaf data-selector {
              description "The data receive mode of smartgroup's members. Smart"
                        + "group has two modes, selective and merging."
                          ;
              type enumeration {
                enum selective {
                  value 0 ;
                  description 'Selective mode'
                              ;
                }
                enum merging {
                  value 1 ;
                  description 'Merging mode'
                              ;
                }
              }
              default selective ;
              ncd:revise-date 2018-09-13 ;
            }
            container protocol-packet {
              if-feature lacp-protocol-packet ;
              description 'The rule of the control plane sending protocol packe'
                        + 't for smartgroup,its default value depends on the pe'
                        + 'rformance parameters.'
                          ;
              choice protocol-packet-choice {
                description 'The rule of the control plane sending protocol pac'
                          + 'ket for smartgroup,its default value depends on th'
                          + 'e performance parameters.'
                            ;
                case load-balance-case {
                  description 'The rule of the control plane sending protocol p'
                            + 'acket for smartgroup is load balance mode.'
                              ;
                  leaf load-balance {
                    description 'The rule of the control plane sending protocol'
                              + ' packet for smartgroup is load balance mode.'
                                ;
                    type empty ;
                    mandatory true ;
                  }
                  leaf mode {
                    description 'The load sharing strategy of smartgroup, its d'
                              + 'efault value depends on the performance parame'
                              + 'ters.'
                                ;
                    type enumeration {
                      enum per-destination {
                        value 10 ;
                        description 'The load-balance mode is per-destination.'
                                    ;
                      }
                      enum per-packet {
                        value 11 ;
                        description 'The load-balance mode is per-packet.'
                                    ;
                      }
                    }
                    mandatory true ;
                  }
                }
                case random-case {
                  description 'The rule of the control plane sending protocol p'
                            + 'acket for smartgroup is random selection.'
                              ;
                  leaf random {
                    description 'The rule of the control plane sending protocol'
                              + ' packet for smartgroup is random selection.'
                                ;
                    type empty ;
                  }
                }
                case ip-fixed-case {
                  description 'The rule of the control plane sending protocol p'
                            + 'acket for smartgroup is fixed selection by desti'
                            + 'nation.'
                              ;
                  leaf ip-fixed {
                    description 'The rule of the control plane sending protocol'
                              + ' packet for smartgroup is fixed selection by d'
                              + 'estination.'
                                ;
                    type empty ;
                  }
                }
              }
              ncd:revise-date 2020-01-02 ;
            }
            leaf fsm-mode {
              description 'The finite state machine mode of smartgroup. Smartgr'
                        + 'oup has two modes, fast and normal.'
                          ;
              type enumeration {
                enum normal {
                  value 0 ;
                  description 'The finite state machine mode of smartgroup is n'
                            + 'ormal.'
                              ;
                }
                enum fast {
                  value 1 ;
                  description 'The finite state machine mode of smartgroup is f'
                            + 'ast.'
                              ;
                }
              }
              default normal ;
              ncd:revise-date 2020-06-30 ;
            }
            leaf speed-reassign {
              description 'The speed field reassignment of smartgroup.'
                          ;
              type enumeration {
                enum disable {
                  value 0 ;
                  description 'The speed field reassignment of smartgroup is di'
                            + 'sable.'
                              ;
                }
                enum enable {
                  value 1 ;
                  description 'The speed field reassignment of smartgroup is en'
                            + 'able.'
                              ;
                }
              }
              default disable ;
              ncd:revise-date 2020-06-30 ;
            }
            container lag-bfd {
              description 'The lag-bfd of smartgroup.'
                          ;
              presence 'destination should be mandatory'
                       ;
              leaf source {
                description 'The source IP of lag-bfd.'
                            ;
                type ncd:ipv4-address-none-zero ;
              }
              leaf destination {
                description 'The destination IP of lag-bfd.'
                            ;
                type ncd:ipv4-address-none-zero ;
                mandatory true ;
              }
              container time-type {
                description 'The time or template parameters of lag-bfd.'
                            ;
                choice time-type-choice {
                  description 'The time or template parameters of lag-bfd.'
                              ;
                  case time-case {
                    description 'The time parameters of lag-bfd.'
                                ;
                    container time {
                      description 'The time parameters of lag-bfd.'
                                  ;
                      presence 'min-tx and min-rx and multiplier should be mand'
                             + 'atory'
                               ;
                      leaf min-tx {
                        description 'The minimum send interval of lag-bfd, its '
                                  + 'minimum value and maximum value depend on '
                                  + 'the performance parameters.'
                                    ;
                        type uint32 ;
                        units millisecond ;
                        mandatory true ;
                      }
                      leaf min-rx {
                        description 'The minimum receive interval of lag-bfd, i'
                                  + 'ts minimum value and maximum value depend '
                                  + 'on the performance parameters.'
                                    ;
                        type uint32 ;
                        units millisecond ;
                        mandatory true ;
                      }
                      leaf multiplier {
                        description 'The detect multiplier of lag-bfd.'
                                    ;
                        type uint8 {
                          range 3..50 ;
                        }
                        mandatory true ;
                      }
                    }
                  }
                  case template-case {
                    description 'The template parameters of lag-bfd.'
                                ;
                    leaf template {
                      description 'The template parameters of lag-bfd.'
                                  ;
                      type string {
                        length 1..31 ;
                      }
                    }
                  }
                }
              }
              ncd:revise-date 2020-08-31 ;
            }
            container lag-bfd-ipv6 {
              description 'The lag-bfd ipv6 of smartgroup.'
                          ;
              presence 'destination should be mandatory'
                       ;
              leaf source {
                description 'The source IP of lag-bfd ipv6.'
                            ;
                type ncd:ipv6-address-none-zero ;
              }
              leaf destination {
                description 'The destination IP of lag-bfd ipv6.'
                            ;
                type ncd:ipv6-address-none-zero ;
                mandatory true ;
              }
              container time-type {
                description 'The time or template parameters of lag-bfd ipv6.'
                            ;
                choice time-type-choice {
                  description 'The time or template parameters of lag-bfd ipv6.'
                              ;
                  case time-case {
                    description 'The time parameters of lag-bfd ipv6.'
                                ;
                    container time {
                      description 'The time parameters of lag-bfd ipv6.'
                                  ;
                      presence 'min-tx and min-rx and multiplier should be mand'
                             + 'atory'
                               ;
                      leaf min-tx {
                        description 'The minimum send interval of lag-bfd ipv6,'
                                  + ' its minimum value and maximum value depen'
                                  + 'd on the performance parameters.'
                                    ;
                        type uint32 {
                          range 1..65535 {
                            description 'The minimum value and maximum value depend on the performance parameters.'
                                        ;
                          }
                        }
                        units millisecond ;
                        mandatory true ;
                      }
                      leaf min-rx {
                        description 'The minimum receive interval of lag-bfd ip'
                                  + 'v6, its minimum value and maximum value de'
                                  + 'pend on the performance parameters.'
                                    ;
                        type uint32 {
                          range 1..65535 {
                            description 'The minimum value and maximum value depend on the performance parameters.'
                                        ;
                          }
                        }
                        units millisecond ;
                        mandatory true ;
                      }
                      leaf multiplier {
                        description 'The detect multiplier of lag-bfd ipv6.'
                                    ;
                        type uint8 {
                          range 3..50 ;
                        }
                        mandatory true ;
                      }
                    }
                  }
                  case template-case {
                    description 'The template parameters of lag-bfd ipv6.'
                                ;
                    leaf template {
                      description 'The template parameters of lag-bfd ipv6.'
                                  ;
                      type string {
                        length 1..31 ;
                      }
                    }
                  }
                }
              }
              ncd:revise-date 2020-08-31 ;
            }
            leaf admin-status-linkage {
              description 'The admin status linkage switch of smartgroup, its d'
                        + 'efault value depends on the performance parameters.'
                          ;
              type enumeration {
                enum disable {
                  value 0 ;
                  description 'Disable admin status linkage.'
                              ;
                }
                enum enable {
                  value 1 ;
                  description 'Enable admin status linkage.'
                              ;
                }
              }
              default disable ;
              ncd:revise-date 2020-09-09 ;
            }
            leaf smartgroup-constant-up {
              description 'The protocal constant up flag of smartgroup.'
                          ;
              type empty ;
              ncd:revise-date 2020-09-15 ;
            }
            container preempt {
              description 'The preempt parameter of smartgroup.'
                          ;
              leaf switch {
                description 'The preempt switch of smartgroup.'
                            ;
                type enumeration {
                  enum disable {
                    value 0 ;
                    description 'The preempt switch of smartgroup is disable.'
                                ;
                  }
                  enum enable {
                    value 1 ;
                    description 'The preempt switch of smartgroup is enable.'
                                ;
                  }
                }
                default enable ;
              }
              leaf delay-time {
                description 'The preempt delay time of smartgroup.'
                            ;
                type uint32 {
                  range 0..180 ;
                }
                units second ;
                default 0 ;
              }
              ncd:revise-date 2020-10-12 ;
            }
            leaf delay-down-time {
              description 'The delay down time of smartgroup.'
                          ;
              type uint32 {
                range 0..180 ;
              }
              units second ;
              default 0 ;
              ncd:revise-date 2020-12-28 ;
            }
          }
        }
        container ports {
          description 'Describe the parameters of member port to be configured.'
                      ;
          list port {
            description 'Describe the parameters of member port to be configure'
                      + 'd.'
                        ;
            key interface-name ;
            leaf interface-name {
              description 'The interface name of member port.'
                          ;
              type ncd:ifname ;
            }
            leaf smartgroup-id {
              description 'The group id bound by member port, its maximum value'
                        + '(the both range) and minimum vaule (the second range'
                        + ')depends on the performance parameters.'
                          ;
              type uint32 {
                range '1..1024 | 1025..2048'
                      {
                  description 'The maximum value(the both range) depends on the'
                            + ' performance parameters.'+"\n"
                            + 'The minimum value(the second range) depends on t'
                            + 'he performance parameters.'
                              ;
                }
              }
              mandatory true ;
            }
            leaf mode {
              description 'The bind mode of member port. Member port has three '
                        + 'bind modes, on and passive and active.'
                          ;
              type enumeration {
                enum passive {
                  value 1 ;
                  description 'The bind mode is passive.'
                              ;
                }
                enum on {
                  value 2 ;
                  description 'The bind mode is on.'
                              ;
                }
                enum active {
                  value 3 ;
                  description 'The bind mode is active.'
                              ;
                }
              }
              mandatory true ;
            }
            leaf port-priority {
              description 'The priority of member port.'
                          ;
              type uint16 {
                range 1..65535 ;
              }
              default 32768 ;
            }
            leaf timeout {
              description 'The timeout type of member port. Timeout has two typ'
                        + 'es, long and short.'
                          ;
              type enumeration {
                enum long {
                  value 0 ;
                  description 'The time-out type is long.'
                              ;
                }
                enum short {
                  value 1 ;
                  description 'The time-out type is short.'
                              ;
                }
              }
              default long ;
            }
            leaf back-up {
              description 'The backup attribute of member port. Only the value '
                        + 'of bond-mode leaf is on can this attribute be config'
                        + 'ured.'
                          ;
              type empty ;
            }
            leaf track {
              description 'The track name of member port.'
                          ;
              type string {
                length 1..31 ;
              }
            }
            container lag-bfd {
              description 'The lag-bfd of member port.'
                          ;
              presence 'destination should be mandatory'
                       ;
              leaf source {
                description 'The source IP of lag-bfd.'
                            ;
                type ncd:ipv4-address-none-zero ;
              }
              leaf destination {
                description 'The destination IP of lag-bfd.'
                            ;
                type ncd:ipv4-address-none-zero ;
                mandatory true ;
              }
              choice time-type-choice {
                description 'The time or template parameters of lag-bfd.'
                            ;
                case time-case {
                  description 'The time parameters of lag-bfd.'
                              ;
                  container time {
                    description 'The time parameters of lag-bfd.'
                                ;
                    presence 'min-tx and min-rx and multiplier should be mandat'
                           + 'ory'
                             ;
                    leaf min-tx {
                      description 'The minimum send interval of lag-bfd, its mi'
                                + 'nimum value and maximum value depend on the '
                                + 'performance parameters.'
                                  ;
                      type uint32 {
                        range 1..65535 {
                          description 'The minimum value and maximum value depe'
                                    + 'nd on the performance parameters.'
                                      ;
                        }
                      }
                      units millisecond ;
                      mandatory true ;
                    }
                    leaf min-rx {
                      description 'The minimum receive interval of lag-bfd, its'
                                + ' minimum value and maximum value depend on t'
                                + 'he performance parameters.'
                                  ;
                      type uint32 {
                        range 1..65535 {
                          description 'The minimum value and maximum value depe'
                                    + 'nd on the performance parameters.'
                                      ;
                        }
                      }
                      units millisecond ;
                      mandatory true ;
                    }
                    leaf multiplier {
                      description 'The detect multiplier of lag-bfd.'
                                  ;
                      type uint8 {
                        range 3..50 ;
                      }
                      mandatory true ;
                    }
                  }
                }
                case template-case {
                  description 'The template parameters of lag-bfd.'
                              ;
                  leaf template {
                    description 'The template parameters of lag-bfd.'
                                ;
                    type string {
                      length 1..31 ;
                    }
                  }
                  ncd:revise-date 2020-08-31 ;
                }
              }
            }
            leaf negotiation-mac {
              description 'The negotiation MAC of member port.Only the value of'
                        + ' bond-mode leaf is 802.3ad can this attribute be con'
                        + 'figured.'
                          ;
              type ncd:mac-address-none-zero ;
              ncd:revise-date 2016-09-19 ;
            }
            leaf unconditional-active {
              description 'The unconditional active flag of member port.Only th'
                        + 'e value of bond-mode leaf is 802.3ad can this attrib'
                        + 'ute be configured.'
                          ;
              type empty ;
              ncd:revise-date 2016-10-10 ;
            }
            leaf description {
              description 'Member port description.'
                          ;
              type ncd:string-with-blank {
                length 1..64 ;
              }
              ncd:revise-date 2020-06-19 ;
            }
            container lag-bfd-ipv6 {
              description 'The lag-bfd ipv6 of member port.'
                          ;
              presence 'destination should be mandatory'
                       ;
              leaf source {
                description 'The source IP of lag-bfd ipv6.'
                            ;
                type ncd:ipv6-address-none-zero ;
              }
              leaf destination {
                description 'The destination IP of lag-bfd ipv6.'
                            ;
                type ncd:ipv6-address-none-zero ;
                mandatory true ;
              }
              container time-type {
                description 'The time or template parameters of lag-bfd ipv6.'
                            ;
                choice time-type-choice {
                  description 'The time or template parameters of lag-bfd ipv6.'
                              ;
                  case time-case {
                    description 'The time parameters of lag-bfd ipv6.'
                                ;
                    container time {
                      description 'The time parameters of lag-bfd ipv6.'
                                  ;
                      presence 'min-tx and min-rx and multiplier should be mand'
                             + 'atory'
                               ;
                      leaf min-tx {
                        description 'The minimum send interval of lag-bfd ipv6,'
                                  + ' its minimum value and maximum value depen'
                                  + 'd on the performance parameters.'
                                    ;
                        type uint32 {
                          range 1..65535 {
                            description 'The minimum value and maximum value depend on the performance parameters.'
                                        ;
                          }
                        }
                        units millisecond ;
                        mandatory true ;
                      }
                      leaf min-rx {
                        description 'The minimum receive interval of lag-bfd ip'
                                  + 'v6, its minimum value and maximum value de'
                                  + 'pend on the performance parameters.'
                                    ;
                        type uint32 {
                          range 1..65535 {
                            description 'The minimum value and maximum value depend on the performance parameters.'
                                        ;
                          }
                        }
                        units millisecond ;
                        mandatory true ;
                      }
                      leaf multiplier {
                        description 'The detect multiplier of lag-bfd ipv6.'
                                    ;
                        type uint8 {
                          range 3..50 ;
                        }
                        mandatory true ;
                      }
                    }
                  }
                  case template-case {
                    description 'The template parameters of lag-bfd ipv6.'
                                ;
                    leaf template {
                      description 'The template parameters of lag-bfd ipv6.'
                                  ;
                      type string {
                        length 1..31 ;
                      }
                    }
                  }
                }
              }
              ncd:revise-date 2020-08-31 ;
            }
          }
        }
      }
      container peer-link {
        description 'Describe the peer-link interface to be configured.'
                    ;
        leaf interface-name {
          description 'The interface name of peer-link.'
                      ;
          type ncd:ifname ;
        }
        ncd:revise-date 2017-07-12 ;
      }
    }
  }
  container state {
    config false ;
    description 'Describe the state of Link Aggregation Control Protocol.'
                ;
    container lacp {
      description 'Describe the state of LACP.'
                  ;
      list smartgroup {
        description 'Describe the state of smartgroup.'
                    ;
        key interface-name ;
        leaf interface-name {
          description 'The interface name of smartgroup.'
                      ;
          type ncd:ifname ;
        }
        leaf mac {
          description 'The MAC of smartgroup.'
                      ;
          type ncd:mac-address ;
        }
        leaf enable-mclag {
          description 'Is MC-LAG enabled by smartgroup.'
                      ;
          type enumeration {
            enum enable {
              value 1 ;
              description 'The smartgroup has enabled MC-LAG.'
                          ;
            }
            enum disable {
              value 2 ;
              description 'The smartgroup has not enabled MC-LAG.'
                          ;
            }
          }
        }
        leaf protect-state {
          description 'The protect state of smartgroup.'
                      ;
          type enumeration {
            enum non-m/s-relation {
              value 0 ;
              description 'Non master/slave relation.'
                          ;
            }
            enum m/s-relation {
              value 1 ;
              description 'Master/slave relation.'
                          ;
            }
            enum waiting-recovery {
              value 2 ;
              description 'Waiting for recovery.'
                          ;
            }
            enum non-recovery {
              value 3 ;
              description 'Non recovery.'
                          ;
            }
            enum master-signal-failure {
              value 4 ;
              description 'Master signal failure.'
                          ;
            }
            enum slave-signal-failure {
              value 5 ;
              description 'Slave signal failure.'
                          ;
            }
          }
          ncd:revise-date 2018-01-08 ;
        }
      }
      list port {
        description 'Describe the state of member port.'
                    ;
        key interface-name ;
        leaf interface-name {
          description 'The interface name of member port.'
                      ;
          type ncd:ifname ;
        }
        leaf smartgroup-id {
          description 'The group id bound by member port.'
                      ;
          type uint32 ;
        }
        leaf actor-oper-key {
          description 'The actor operate key of member port.'
                      ;
          type uint32 ;
        }
        leaf actor-oper-state {
          description 'The actor operate state of member port.'
                      ;
          type uint32 ;
        }
        leaf partner-oper-key {
          description 'The partner operate key of member port.'
                      ;
          type uint32 ;
        }
        leaf partner-oper-state {
          description 'The partner operate state of member port.'
                      ;
          type uint32 ;
        }
        leaf partner-port-priority {
          description 'The partner port priority of member port.'
                      ;
          type uint32 ;
        }
        leaf lacp-state {
          description 'The LACP port state of member port. LACP has two port st'
                    + 'ates, active and inactive.'
                      ;
          type enumeration {
            enum inactive {
              value 1 ;
              description 'The LACP port state is inactive.'
                          ;
            }
            enum active {
              value 2 ;
              description 'The LACP port state is active.'
                          ;
            }
          }
        }
        leaf partner-system-priority {
          description 'The partner system priority of member port.'
                      ;
          type uint32 ;
        }
        leaf partner-system-mac {
          description 'The partner system MAC of member port.'
                      ;
          type ncd:mac-address ;
        }
      }
      list mclag {
        description 'Describe the state of MC-LAG.'
                    ;
        key interface-name ;
        leaf interface-name {
          description 'The interface name of smartgroup.'
                      ;
          type ncd:ifname ;
        }
        leaf actor-roid {
          description 'The actor roid of MC-LAG.'
                      ;
          type uint64 ;
          ncd:revise-date 2020-06-30 ;
        }
        leaf actor-node-id {
          description 'The actor node id of MC-LAG.'
                      ;
          type uint32 ;
          ncd:revise-date 2020-06-30 ;
        }
        leaf actor-back-up {
          description 'The actor backup attribute of MC-LAG.'
                      ;
          type enumeration {
            enum disable {
              value 1 ;
              description 'The MC-LAG actor has not configured backup attribute.'
                          ;
            }
            enum enable {
              value 2 ;
              description 'The MC-LAG actor has configured backup attribute.'
                          ;
            }
          }
        }
        leaf partner-system-mac {
          description 'The partner system MAC of MC-LAG.'
                      ;
          type ncd:mac-address ;
        }
        leaf partner-system-priority {
          description 'The partner system priority of MC-LAG.'
                      ;
          type uint32 ;
        }
        leaf partner-priority {
          description 'The partner priority of MC-LAG.'
                      ;
          type uint32 ;
        }
        leaf partner-roid {
          description 'The partner roid of MC-LAG.'
                      ;
          type uint64 ;
        }
        leaf parnter-node-id {
          description 'The partner node id of MC-LAG.'
                      ;
          type uint32 ;
        }
        leaf work-mode {
          description 'The work mode of MC-LAG. Only the smartgroup with 802.3a'
                    + 'd is effective.'
                      ;
          type enumeration {
            enum none {
              value 0 ;
              description 'None mode'
                          ;
            }
            enum auto {
              value 1 ;
              description 'Auto mode'
                          ;
            }
            enum force-master {
              value 2 ;
              description 'Force-master mode'
                          ;
            }
            enum force-backup {
              value 3 ;
              description 'Force-backup mode'
                          ;
            }
            enum na {
              value 4 ;
              description 'Invalid mode'
                          ;
            }
          }
          ncd:revise-date 2018-11-20 ;
        }
        leaf state {
          description 'The state of MC-LAG.'
                      ;
          type enumeration {
            enum none {
              value 0 ;
              description 'The MC-LAG has not been established.'
                          ;
            }
            enum ms {
              value 1 ;
              description 'The MC-LAG is in master and slave state.'
                          ;
            }
            enum ms-nonRevertive {
              value 2 ;
              description 'The MC-LAG is in master and slave state, but cannot '
                        + 'be revertive.'
                          ;
            }
            enum ms-wtr {
              value 3 ;
              description 'The MC-LAG is in master and slave state, and is wait'
                        + 'ing for recovery.'
                          ;
            }
            enum ms-continueToWtr {
              value 4 ;
              description 'The MC-LAG is in master and slave state, but needs t'
                        + 'o continue to wait for recovery.'
                          ;
            }
            enum ms-manualSwitch {
              value 5 ;
              description 'The MC-LAG is in master and slave state, but is also'
                        + ' in manual switch state.'
                          ;
            }
            enum load-sharing {
              value 6 ;
              description 'The MC-LAG is in load-sharing state.'
                          ;
            }
            enum abnormal {
              value 7 ;
              description 'The MC-LAG is in abnormal state.'
                          ;
            }
            enum peer-unknown {
              value 8 ;
              description 'The MC-LAG is interrupted and cannot get peer inform'
                        + 'ation.'
                          ;
            }
          }
          ncd:revise-date 2018-11-20 ;
        }
        leaf actor-smartgroup-state {
          description 'The actor smartgroup state of MC-LAG.'
                      ;
          type enumeration {
            enum down {
              value 0 ;
              description 'The state is down.'
                          ;
            }
            enum up {
              value 1 ;
              description 'The state is up.'
                          ;
            }
          }
          ncd:revise-date 2018-11-20 ;
        }
        leaf partner-smartgroup-state {
          description 'The partner smartgroup state of MC-LAG.'
                      ;
          type enumeration {
            enum down {
              value 0 ;
              description 'The state is down.'
                          ;
            }
            enum up {
              value 1 ;
              description 'The state is up.'
                          ;
            }
            enum unknown {
              value 2 ;
              description 'The state is unknown.'
                          ;
            }
          }
          ncd:revise-date 2018-11-20 ;
        }
      }
      list member {
        description 'Describe the member port information of smartgroup.'
                    ;
        key interface-name ;
        leaf interface-name {
          description 'The interface name of smartgroup.'
                      ;
          type ncd:ifname ;
        }
        container ports {
          description 'Describe the information of member port.'
                      ;
          list port {
            description 'Describe the information of member port.'
                        ;
            key port-name ;
            leaf port-name {
              description 'The interface name of member port.'
                          ;
              type ncd:ifname ;
            }
            leaf port-state {
              description 'The state of member port. LACP has two port states, '
                        + 'active and inactive.'
                          ;
              type enumeration {
                enum inactive {
                  value 1 ;
                  description 'The LACP port state is inactive.'
                              ;
                }
                enum active {
                  value 2 ;
                  description 'The LACP port state is active.'
                              ;
                }
              }
            }
          }
        }
        ncd:revise-date 2016-11-16 ;
      }
    }
  }
  container operation {
    config false ;
    description 'Describe the operation of Link Aggregation Control Protocol.'
                ;
    container lacp {
      description 'Describe the operation of LACP.'
                  ;
      container clear {
        description 'Clear the packet count.'
                    ;
        choice clear-choice {
          description 'Clear the packet count.'
                      ;
          case group-id-case {
            description 'Clear the packet count of smartgroup.'
                        ;
            leaf group-id {
              description 'Clear the packet count of smartgroup, its maximum va'
                        + 'lue(the both range) and minimum vaule (the second ra'
                        + 'nge)depends on the performance parameters.'
                          ;
              type uint32 {
                range '1..1024 | 1025..2048'
                      {
                  description 'The maximum value(the both range) depends on the'
                            + ' performance parameters.'+"\n"
                            + 'The minimum value(the second range) depends on t'
                            + 'he performance parameters.'
                              ;
                }
              }
            }
          }
          case all-case {
            description 'Clear the packet count of all smartgroups.'
                        ;
            leaf all {
              description 'Clear the packet count of all smartgroups.'
                          ;
              type empty ;
            }
          }
        }
      }
      container forceswitch {
        description 'The force swith operation of smartgroup.'
                    ;
        leaf interface-name {
          description 'The interface name of smartgroup.'
                      ;
          type ncd:ifname ;
        }
      }
    }
  }
}
