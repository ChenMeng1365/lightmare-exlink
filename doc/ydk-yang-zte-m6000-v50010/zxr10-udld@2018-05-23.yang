module zxr10-udld {
  namespace 'http://www.zte.com.cn/zxr10/netconf/schema/rosng/udld'
            ;
  prefix udld ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe Unidirection Link Detection(UDLD)'
              ;
  revision 2018-05-23 {
    description 'The initial version'
                ;
  }
  container configuration {
    description 'Describe the configuration of UDLD'
                ;
    container udld {
      description 'Configuration data of UDLD'
                  ;
      container udld-attrs {
        description 'UDLD attribute configuration'
                    ;
        list udld-attr {
          description 'Configure UDLD parameters'
                      ;
          key ifname ;
          leaf ifname {
            description 'This value identifies the UDLD interface name.This att'
                      + 'ribute is created by Interface Management'
                        ;
            type ncd:ifname ;
          }
          leaf protocol-flag {
            description 'UDLD protocol correlation configuration'
                        ;
            type enumeration {
              enum disable {
                value 0 ;
                description 'Disable UDLD'
                            ;
              }
              enum enable {
                value 1 ;
                description 'Enable UDLD'
                            ;
              }
            }
            default disable ;
          }
          leaf work-mode {
            description 'Configure UDLD mode'
                        ;
            type enumeration {
              enum normal {
                value 0 ;
                description 'Normal mode'
                            ;
              }
              enum aggressive {
                value 1 ;
                description 'Aggressive mode'
                            ;
              }
            }
            default normal ;
          }
          leaf message-timer {
            description 'Configure UDLD message timer'
                        ;
            type uint8 {
              range 7..90 ;
            }
            units seconds ;
            default 15 ;
          }
          leaf recovery-flag {
            description 'Configure UDLD auto-recovery'
                        ;
            type enumeration {
              enum disable {
                value 0 ;
                description 'Disable auto-recovery'
                            ;
              }
              enum enable {
                value 1 ;
                description 'Enable auto-recovery'
                            ;
              }
            }
            default disable ;
          }
          leaf dos-protect {
            description 'Configure UDLD dos protect'
                        ;
            type enumeration {
              enum disable {
                value 0 ;
                description 'Disable UDLD DoS protect'
                            ;
              }
              enum enable {
                value 1 ;
                description 'Enable UDLD DoS protect'
                            ;
              }
            }
            default disable ;
          }
          leaf recovery-timer {
            description 'Configure UDLD recovery timer'
                        ;
            type uint32 {
              range 10..600 ;
            }
            units seconds ;
            default 30 ;
          }
        }
      }
    }
  }
  container operation {
    description 'Describe the operation of UDLD'
                ;
    config false ;
    container udld {
      description 'Operation data of UDLD'
                  ;
      container udld-reset {
        description 'UDLD reset correlation operation'
                    ;
        list reset {
          description 'Reset interface down by UDLD'
                      ;
          key ifname ;
          leaf ifname {
            description 'This value identifies the UDLD interface name.This att'
                      + 'ribute is created by Interface Management'
                        ;
            type ncd:ifname ;
          }
          leaf udld-reset {
            description 'Reset interface down by UDLD'
                        ;
            type uint8 {
              range 0..1 ;
            }
          }
        }
      }
    }
  }
  container state {
    description 'Describe the state of UDLD'
                ;
    config false ;
    container udld {
      description 'State data of UDLD'
                  ;
      container udld-info {
        description 'Show UDLD information'
                    ;
        list udld-state {
          description 'UDLD correlation state'
                      ;
          key ifname ;
          leaf ifname {
            description 'This value identifies the UDLD interface name.This att'
                      + 'ribute is created by Interface Management'
                        ;
            type ncd:ifname ;
          }
          leaf protocol-flag {
            description 'UDLD protocol state'
                        ;
            type enumeration {
              enum disable {
                value 0 ;
                description 'Udld disable'
                            ;
              }
              enum enable {
                value 1 ;
                description 'Udld enable'
                            ;
              }
            }
          }
          leaf work-mode {
            description 'UDLD protocol mode'
                        ;
            type enumeration {
              enum normal {
                value 0 ;
                description 'Normal mode'
                            ;
              }
              enum aggressive {
                value 1 ;
                description 'Aggressive mode'
                            ;
              }
            }
          }
          leaf current-state {
            description 'UDLD machine status'
                        ;
            type enumeration {
              enum disable {
                value 0 ;
                description 'Disable state'
                            ;
              }
              enum probe {
                value 1 ;
                description 'Probe state'
                            ;
              }
              enum always-hello {
                value 2 ;
                description 'Always hello state'
                            ;
              }
              enum neighbour-build {
                value 3 ;
                description 'Neighbour build state'
                            ;
              }
              enum bidirection {
                value 4 ;
                description 'Bidirection state'
                            ;
              }
              enum unidirection {
                value 5 ;
                description 'Unidirection state'
                            ;
              }
              enum other {
                value 6 ;
                description 'Other state'
                            ;
              }
            }
          }
          leaf recovery-flag {
            description 'UDLD auto-recovery flag'
                        ;
            type enumeration {
              enum disable {
                value 0 ;
                description 'Auto-recovery disable'
                            ;
              }
              enum enable {
                value 1 ;
                description 'Auto-recovery enable'
                            ;
              }
            }
          }
          leaf recovery-timer {
            description 'UDLD recovery timer'
                        ;
            type uint32 {
              range 10..600 ;
            }
          }
          leaf message-timer {
            description 'UDLD message timer'
                        ;
            type uint8 {
              range 7..90 ;
            }
          }
          leaf neighbour-num {
            description 'Neighbour num'
                        ;
            type uint8 {
              range 0..16 ;
            }
          }
          container neighbour {
            description 'UDLD neighbour information'
                        ;
            list neighbour-info {
              description 'UDLD neighbour information'
                          ;
              key port-id ;
              leaf port-id {
                description 'Neighbour port ID'
                            ;
                type ncd:ifname ;
              }
              leaf device-id {
                description 'Neighbour device ID'
                            ;
                type string {
                  length 1..32 ;
                }
              }
              leaf device-name {
                description 'Neighbour device ID'
                            ;
                type string {
                  length 1..64 ;
                }
              }
              leaf expiration-timer {
                description 'Neighbour expiration timer'
                            ;
                type uint32 {
                  range 0..270 ;
                }
              }
              leaf message-timer {
                description 'Neighbour message timer'
                            ;
                type uint8 {
                  range 0..90 ;
                }
              }
              leaf timeout-interval {
                description 'Neighbour timeout interval'
                            ;
                type uint8 {
                  range 0..255 ;
                }
              }
            }
          }
        }
      }
    }
  }
}
