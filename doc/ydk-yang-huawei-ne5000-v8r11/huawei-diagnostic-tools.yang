/*
Copyright (C) 2019-2020 Huawei Technologies Co., Ltd. All rights reserved.
*/
module huawei-diagnostic-tools {
  yang-version 1;
  namespace "urn:huawei:yang:huawei-diagnostic-tools";
  prefix diagnostic-tools;
  import huawei-extension {
    prefix ext;
  }
  include huawei-diagnostic-tools-ipv4;
  include huawei-diagnostic-tools-ipv6;
  include huawei-diagnostic-tools-lsp;
  include huawei-diagnostic-tools-type;
  include huawei-diagnostic-tools-srv6;
  include huawei-diagnostic-tools-evpn;
  include huawei-diagnostic-tools-common;
  include huawei-diagnostic-tools-tcp;
  include huawei-diagnostic-tools-gmac;
  organization
    "Huawei Technologies Co., Ltd.";
  contact
    "Huawei Industrial Base
     Bantian, Longgang
     Shenzhen 518129
     People's Republic of China
     Website: http://www.huawei.com
     Email: support@huawei.com";
  description
     "Diagnosis tool.";

  revision 2020-01-14 {
    description
      "Modify of evpn.";
    reference
      "Huawei private.";
  }
  revision 2019-11-05 {
    description
      "Initial revision.";
    reference
      "Huawei private.";
  }
  ext:task-name "sla";
}
