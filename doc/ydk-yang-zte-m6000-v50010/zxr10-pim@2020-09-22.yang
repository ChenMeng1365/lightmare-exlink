module zxr10-pim {
  namespace 'http://www.zte.com.cn/zxr10/netconf/schema/rosng/pim'
            ;
  prefix pim ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module of describing PIM.'
              ;
  revision 2020-09-22 {
    description 'Add data-filter-acl leaf node to /configuration/router-pim/vrf'
              + '-pims/vrf-pim/intfs/intf/ and /configuration/router-pim/pim/in'
              + 'tfs/intf/.'
                ;
  }
  revision 2020-07-01 {
    description '1,Modify the range of leaf node:/configuration/router-pim/vrf-'
              + 'pims/vrf-pim/crps/crp/prefix-list.'+"\n"
              + '2,Modify the range of leaf node:/configuration/router-pim/vrf-'
              + 'pims/vrf-pim/srps/srp/prefix-list.'+"\n"
              + '3,Modify the range of leaf node:/configuration/router-pim/pim/'
              + 'crps/crp/prefix-list.'+"\n"
              + '4,Modify the range of leaf node:/configuration/router-pim/pim/'
              + 'srps/srp/prefix-list.'+"\n"
              + '5,Modify the range of leaf node:/state/pim/public/bsr/crps/crp'
              + '/group-list.'+"\n"
              + '6,Modify the range of leaf node:/state/pim/private/bsrs/bsr/cr'
              + 'ps/crp/group-list.'
                ;
  }
  revision 2020-06-20 {
    description '1,Add mvpn-signal-acl leaf node to /configuration/router-pim/p'
              + 'im/global;'
                ;
  }
  revision 2020-05-19 {
    description 'Add bfd-template leaf node to /configuration/router-pim/vrf-pi'
              + 'ms/vrf-pim/intfs/intf and /configuration/router-pim/pim/intfs/'
              + 'intf.'
                ;
  }
  revision 2019-11-12 {
    description 'Add the containers :/configuration/router-pim/pim/trust-reg-so'
              + 'urces and /configuration/router-pim/vrf-pims/vrf-pim/trust-reg'
              + '-sources.'
                ;
  }
  revision 2019-09-29 {
    description '1,Add join-attribute leaf node to /configuration/router-pim/pi'
              + 'm/global;'
                ;
  }
  revision 2019-08-29 {
    description '1,Add interface-identifier and ecmp-redirect leaf nodes to /co'
              + 'nfiguration/router-pim/vrf-pims/vrf-pim and /configuration/rou'
              + 'ter-pim/pim/global;'+"\n"
              + '2,Add ecmp-bundle container to /configuration/router-pim/vrf-p'
              + 'ims/vrf-pim/intfs/intf and /configuration/router-pim/pim/intfs'
              + '/intf.'
                ;
  }
  revision 2019-07-15 {
    description '1,Add bsr-policy-acl and reg-data-forward leaf nodes to /confi'
              + 'guration/router-pim/vrf-pims/vrf-pim and /configuration/router'
              + '-pim/pim/global;'+"\n"
              + '2,Add triggered-hello-delay and pfm-border leaf nodes to /conf'
              + 'iguration/router-pim/vrf-pims/vrf-pim/intfs/intf and /configur'
              + 'ation/router-pim/pim/intfs/intf.'+"\n"
              + '3,Add pfm container to /configuration/router-pim/vrf-pims/vrf-'
              + 'pim and /configuration/router-pim/pim;'+"\n"
              + '4,Add pfm-gsh-caches container to /operation/pim/public/clear '
              + 'and /operation/pim/private/clear;'+"\n"
              + '5,Add pfm-instance,pfm-gsh-summary and pfm-gsh-caches containe'
              + 'rs to /state/pim/public;'+"\n"
              + '6,Add pfm-instances,pfm-gsh-summarys and pfm-gsh-caches contai'
              + 'ners to /state/pim/private;'
                ;
  }
  revision 2019-06-25 {
    description 'Add pimdm leaf node to /configuration/router-pim/vrf-pims/vrf-'
              + 'pim/intfs/intf.'
                ;
  }
  revision 2019-01-15 {
    description 'Add the containers :/state/pim/public/intf-brief and /state/pi'
              + 'm/private/intf-briefs.'
                ;
  }
  revision 2018-02-08 {
    description 'Modify the description of leaf node:/configuration/router-pim/'
              + 'vrf-pims/vrf-pim/ and /configuration/router-pim/pim/global/ ke'
              + 'epalive-period.'
                ;
  }
  revision 2017-08-18 {
    description 'Delete presence of /configuration/router-pim/vrf-pims/vrf-pim/'
              + 'groups/binds/bind/bind-attrs/ and /configuration/router-pim/pi'
              + 'm/groups/binds/bind/bind-attrs/.'
                ;
  }
  revision 2016-12-08 {
    description 'Add hello-track-support leaf node to /configuration/router-pim'
              + '/vrf-pims/vrf-pim/intfs/intf/ and /configuration/router-pim/pi'
              + 'm/intfs/intf/.'
                ;
  }
  revision 2016-07-25 {
    description '1.modify the length of the leaves: /state/pim/public/dfs/df/rp'
              + 'a-states/rpa-state/state and /state/pim/private/dfs/df/rpa-sta'
              + 'tes/rpa-state/state.'+"\n"
              + '2.modify the description of the leaves: /state/pim/public/dfs/'
              + 'df/rpa-states/rpa-state/state and /state/pim/private/dfs/df/rp'
              + 'a-states/rpa-state/state.'
                ;
  }
  revision 2016-03-18 {
    description '1.Add the leaves :/configuration/router-pim/pim/global/pim-sta'
              + 'tistics-acl and /configuration/router-pim/vrf-pims/vrf-pim/pim'
              + '-statistics-acl.'+"\n"
              + '2.Add the containers :/state/pim/public/statistics, /state/pim'
              + '/private/statistics, /operation/pim/public/clear/statistics an'
              + 'd /operation/pim/private/clear/statistics.'+"\n"
              + '3.Add the feature of pim-statistics.'
                ;
  }
  revision 2015-12-15 {
    description 'add the leaves: /state/pim/public/mroutes/mroute/fallback-vrf,'
              + ' /state/pim/private/mroutes/mroute/fallback-vrf, /state/pim/pu'
              + 'blic/nhps/nhp/fallback-vrf and /state/pim/private/nhps/nhp/fal'
              + 'lback-vrf.'
                ;
  }
  revision 2015-09-28 {
    description 'Add the feature to the node:/configuration/router-pim/vrf-pims'
              + '/vrf-pim/keepalive-period and /configuration/router-pim/pim/gl'
              + 'obal/keepalive-period.'
                ;
  }
  revision 2015-09-23 {
    description 'Add pimdm-reg leaf node to /configuration/router-pim/pim/globa'
              + 'l/.'
                ;
  }
  revision 2015-06-19 {
    description 'Add hello-dr-addr leaf node to /configuration/router-pim/vrf-p'
              + 'ims/vrf-pim/intfs/intf/ and /configuration/router-pim/pim/intf'
              + 's/intf/.'
                ;
  }
  revision 2015-06-01 {
    description '1.Add cbsr-holdtime and cbsr-interval leaf nodes to /configura'
              + 'tion/router-pim/vrf-pims/vrf-pim/ and /configuration/router-pi'
              + 'm/pim/global/.'+"\n"
              + '2.Add crp-holdtime leaf node to /configuration/router-pim/vrf-'
              + 'pims/vrf-pim/crps/crp/ and /configuration/router-pim/pim/crps/'
              + 'crp/.'
                ;
  }
  revision 2015-03-31 {
    description 'Add state and operation of PIM.'
                ;
  }
  revision 2015-03-05 {
    description '1.modify the description of the leaves: /configuration/router-'
              + 'pim/vrf-pims/vrf-pim/mofrr-filter-acl and mldp-signal-filter.'+"\n"
              + '2.modify the description of the leaves: /configuration/router-'
              + 'pim/pim/global/mofrr-filter-acl and mldp-signal-filter, /confi'
              + 'guration/router-pim/pim/intfs/intf/jp-max-packet.'
                ;
  }
  revision 2015-02-12 {
    description '1.Add assert-holdtime,graft-retry-time,keepalive-period and jo'
              + 'in-prune-speed leaf nodes to /configuration/router-pim/vrf-pim'
              + 's/vrf-pim/ and /configuration/router-pim/pim/global/.'+"\n"
              + '2.Add propagation-delay,override-interval and jp-max-packet-le'
              + 'ngth leaf node to /configuration/router-pim/vrf-pims/vrf-pim/i'
              + 'ntfs/intf/ and /configuration/router-pim/pim/intfs/intf/.'
                ;
  }
  revision 2014-10-10 {
    description '1.Add mldp-signal-enable and mldp-signal-filter leaf nodes to '
              + '/configuration/router-pim/vrf-pims/vrf-pim/ and /configuration'
              + '/router-pim/pim/global/.'+"\n"
              + '2.Add frr-enable leaf node to /configuration/router-pim/vrf-pi'
              + 'ms/vrf-pim/intfs/intf/ and /configuration/router-pim/pim/intfs'
              + '/intf/.'
                ;
  }
  revision 2014-02-26 {
    description 'Initial version.'
                ;
  }
  feature keepalive-period {
    description 'Only for the use of 15K PC'
                ;
  }
  feature pim-statistics {
    description 'Only for the use of T8000, PC and M6000.'
                ;
  }
  feature hello-track-support {
    description "PIM hello packet sended with the T bit in the LAN Prune Delay "
              + "option, this indicates the neighbor's capability to disable Jo"
              + "in message suppression."
                ;
  }
  feature trust-reg-source {
    description 'Only for the use of T8000,15K and PC.'
                ;
  }
  container configuration {
    description 'PIM module configuration info.'
                ;
    container router-pim {
      description 'PIM module configure root node.'
                  ;
      container vrf-pims {
        description 'Private mode of PIM module configure root node.'
                    ;
        list vrf-pim {
          description 'Private mode of PIM module configure root node.'
                      ;
          key vrf-name ;
          leaf vrf-name {
            description 'VPN Routing/Forwarding instance name'
                        ;
            type string {
              length 1..32 ;
            }
          }
          leaf srp-override {
            description 'Static RP override'
                        ;
            type empty ;
          }
          leaf srp-smartswitch {
            description 'PIM RP smart switch'
                        ;
            type empty ;
          }
          leaf bsm-unicast {
            description 'PIM unicast bootstrap messages'
                        ;
            type empty ;
          }
          leaf ssm-enable {
            description 'SSM enable'
                        ;
            type empty ;
          }
          leaf dr-switch-delay-value {
            description 'PIM DR switch back delay'
                        ;
            type uint16 {
              range 1..300 ;
            }
            units second ;
          }
          leaf accept-rp-acl {
            description 'PIM RP accept filter'
                        ;
            type string {
              length 1..31 ;
            }
          }
          leaf reg-filter-acl {
            description 'PIM registers accept filter'
                        ;
            type string {
              length 1..31 ;
            }
          }
          leaf data-filter-acl {
            description 'PIM data filter'
                        ;
            type string {
              length 1..31 ;
            }
          }
          leaf jp-holdtime {
            description 'PIM router join-prune holdtime'
                        ;
            type uint16 {
              range 210..65535 ;
            }
            units second ;
            default 210 ;
          }
          leaf rp-proxy {
            description 'PIM RP proxy'
                        ;
            type empty ;
          }
          leaf reg-suppression-interval {
            description 'PIM router register suppression interval'
                        ;
            type uint16 {
              range 60..3600 ;
            }
            units second ;
            default 60 ;
          }
          leaf reg-probe-interval {
            description 'PIM router register probe interval'
                        ;
            type uint16 {
              range 1..210 ;
            }
            units second ;
            default 5 ;
          }
          leaf bidir-pim {
            description 'Enable BIDIR-PIM'
                        ;
            type empty ;
          }
          leaf jp-interval {
            description 'PIM router join-prune interval'
                        ;
            type uint16 {
              range 10..6000 ;
            }
            units second ;
            default 60 ;
          }
          leaf reg-holdtime {
            description 'Register holdtime without receiving register stop'
                        ;
            type uint16 {
              range 1..600 ;
            }
            units second ;
          }
          leaf mofrr-filter-acl {
            description 'PIM MoFRR filter'
                        ;
            type string {
              length 1..31 ;
            }
          }
          leaf mldp-signal-enable {
            description 'mldp-signal enable'
                        ;
            type empty ;
          }
          leaf mldp-signal-filter {
            description 'mldp-signal ACL'
                        ;
            type string {
              length 1..31 ;
            }
          }
          leaf assert-holdtime {
            description 'configure assert holdtime'
                        ;
            type uint16 {
              range 60..65535 ;
            }
            units second ;
            default 180 ;
          }
          leaf graft-retry-time {
            description 'configure graft retry time'
                        ;
            type uint16 {
              range 1..65535 ;
            }
            units second ;
            default 3 ;
          }
          leaf keepalive-period {
            // if-feature keepalive-period ;
            description "The configuration of keepalive period. It's validated "
                      + "minimum may be related to the performance of the  cert"
                      + "ain product."
                        ;
            type uint16 {
              range 60..65535 ;
            }
            units second ;
            default 210 ;
          }
          leaf join-prune-speed {
            description 'configure join prune speed'
                        ;
            type uint16 {
              range 1000..50000 ;
            }
            default 10000 ;
          }
          leaf cbsr-holdtime {
            description 'PIM router candidate BSR holdtime'
                        ;
            type uint16 {
              range 130..65535 ;
            }
            units second ;
            default 130 ;
            ncd:revise-date 2015-06-01 ;
          }
          leaf cbsr-interval {
            description 'PIM router candidate BSR interval'
                        ;
            type uint16 {
              range 10..65535 ;
            }
            units second ;
            default 60 ;
            ncd:revise-date 2015-06-01 ;
          }
          leaf pim-statistics-acl {
            // if-feature pim-statistics ;
            description 'PIM packet statistics filter.'
                        ;
            type string {
              length 1..31 ;
            }
            ncd:revise-date 2016-03-18 ;
          }
          leaf reg-data-forward {
            description 'PIM router register data forward.'
                        ;
            type empty ;
            ncd:revise-date 2019-07-15 ;
          }
          leaf bsr-policy-acl {
            description 'PIM BSR filter.'
                        ;
            type string {
              length 1..31 ;
            }
            ncd:revise-date 2019-07-15 ;
          }
          leaf interface-identifier {
            description 'Enable interface identifier option.'
                        ;
            type empty ;
            ncd:revise-date 2019-08-29 ;
          }
          leaf ecmp-redirect {
            description 'Enable ECMP redirect.'
                        ;
            type empty ;
            ncd:revise-date 2019-08-29 ;
          }
          container bsr {
            description 'PIM candidate bootstrap router (candidate BSR)'
                        ;
            presence 'The leaf intf_name of this container should be mandatory,'
                   + ' and other leafs are not.'
                     ;
            leaf intf-name {
              description 'Interface name'
                          ;
              type ncd:ifname {
                length 1..31 ;
              }
              mandatory true ;
            }
            leaf priority {
              description 'Priority value for candidate BSR'
                          ;
              type uint8 {
                range 0..255 ;
              }
              default 0 ;
            }
            leaf hash-len {
              description 'Hash mask length for candidate BSR'
                          ;
              type uint8 {
                range 0..32 ;
              }
              default 30 ;
            }
          }
          container spt {
            description 'PIM source-tree switching threshold'
                        ;
            presence 'The leaf infinity of this container should be mandatory, '
                   + 'and other leafs are not.'
                     ;
            leaf acl {
              description 'Access list name for group prefix'
                          ;
              type string {
                length 1..31 ;
              }
            }
            leaf infinity {
              description 'Never switch to source-tree'
                          ;
              type empty ;
              mandatory true ;
            }
          }
          container intfs {
            description 'PIM interface'
                        ;
            list intf {
              description 'PIM interface'
                          ;
              key intf-name ;
              leaf intf-name {
                description 'Interface name'
                            ;
                type ncd:ifname {
                  length 1..31 ;
                }
              }
              leaf pimsm {
                description 'Enable PIM-SM operation on the interface'
                            ;
                type empty ;
              }
              leaf pimdm {
                description 'Enable PIM-DM operation on the interface'
                            ;
                type empty ;
                ncd:revise-date 2019-06-25 ;
              }
              leaf assert-disable {
                description 'PIM assert disable'
                            ;
                type empty ;
              }
              leaf bfd-enable {
                description 'PIM BFD enable'
                            ;
                type empty ;
              }
              leaf bfd-template {
                description 'Set template name for bfd'
                            ;
                type string {
                  length 1..31 ;
                }
                ncd:revise-date 2020-05-19 ;
              }
              leaf bsr-border {
                description 'Border of PIM domain'
                            ;
                type empty ;
              }
              leaf dr-priority {
                description 'PIM router DR priority'
                            ;
                type uint32 {
                  range 0..4294967295 ;
                }
                default 1 ;
              }
              leaf nbr-filter-acl {
                description 'PIM peering filter'
                            ;
                type string {
                  length 1..31 ;
                }
              }
              leaf hello-interval {
                description 'PIM router hello interval'
                            ;
                type uint16 {
                  range 1..65535 ;
                }
                units second ;
                default 30 ;
              }
              leaf silent {
                description 'PIM silent'
                            ;
                type empty ;
              }
              leaf dr-ignore {
                description 'PIM-SM DR ignore'
                            ;
                type empty ;
              }
              leaf frr-enable {
                description 'PIM FRR enable'
                            ;
                type empty ;
              }
              leaf propagation-delay {
                description 'PIM propagation delay'
                            ;
                type uint16 {
                  range 1..100 ;
                }
                units 100millisecond ;
                default 5 ;
              }
              leaf override-interval {
                description 'PIM override interval'
                            ;
                type uint16 {
                  range 1..600 ;
                }
                units 100millisecond ;
                default 25 ;
              }
              leaf jp-max-packet-length {
                description 'configure the max length of Join/Prune packet'
                            ;
                type uint16 {
                  range 100..8100 ;
                }
                units byte ;
                default 1400 ;
              }
              leaf hello-dr-addr {
                description 'PIM hello packet sended with hello DR address'
                            ;
                type empty ;
                ncd:revise-date 2015-06-19 ;
              }
              leaf hello-track-support {
                // if-feature hello-track-support ;
                description "PIM hello packet sended with the T bit in the LAN "
                          + "Prune Delay option, this indicates the neighbor's "
                          + "capability to disable Join message suppression."
                            ;
                type empty ;
                ncd:revise-date 2016-12-08 ;
              }
              leaf triggered-hello-delay {
                description 'Triggered hello delay time.'
                            ;
                type uint16 {
                  range 1..5 ;
                }
                units second ;
                default 5 ;
                ncd:revise-date 2019-07-15 ;
              }
              leaf pfm-border {
                description 'PFM border.'
                            ;
                type empty ;
                ncd:revise-date 2019-07-15 ;
              }
              container ecmp-bundle {
                description 'ECMP bundle.'
                            ;
                presence ecmp-bundle ;
                leaf name {
                  description 'ECMP bundle name.'
                              ;
                  type string {
                    length 1..31 ;
                  }
                  mandatory true ;
                }
                leaf metric {
                  description 'ECMP path metric.'
                              ;
                  type uint64 {
                    range 1..18446744073709551615 ;
                  }
                  mandatory true ;
                }
                ncd:revise-date 2019-08-29 ;
              }
              leaf data-filter-acl {
                description 'PIM data filter'
                            ;
                type string {
                  length 1..31 ;
                }
                ncd:revise-date 2020-09-22 ;
              }
            }
          }
          container crps {
            description 'PIM candidate RP'
                        ;
            list crp {
              description 'PIM candidate RP'
                          ;
              key intf-name ;
              leaf intf-name {
                description 'Interface name'
                            ;
                type ncd:ifname {
                  length 1..31 ;
                }
              }
              leaf prefix-list {
                description Group-list ;
                type string {
                  length 1..169 ;
                }
              }
              leaf priority {
                description 'Priority value for candidate RP'
                            ;
                type uint8 {
                  range 0..255 ;
                }
                default 192 ;
              }
              leaf bidir-pim {
                description 'Group range treated in BIDIR-PIM'
                            ;
                type empty ;
              }
              leaf crp-holdtime {
                description 'Candidate RP holdtime'
                            ;
                type uint16 {
                  range 150..65535 ;
                }
                units second ;
                default 150 ;
                ncd:revise-date 2015-06-01 ;
              }
            }
          }
          container srps {
            description 'PIM static RP'
                        ;
            list srp {
              description 'PIM static RP'
                          ;
              key ip-addr ;
              leaf ip-addr {
                description 'IP address of static RP'
                            ;
                type ncd:ipv4-address ;
              }
              leaf prefix-list {
                description Group-list ;
                type string {
                  length 1..169 ;
                }
              }
              leaf priority {
                description 'Priority value for static RP'
                            ;
                type uint8 {
                  range 0..255 ;
                }
                default 192 ;
              }
              leaf bidir-pim {
                description 'Group range treated in BIDIR-PIM'
                            ;
                type empty ;
              }
            }
          }
          container arp-peers {
            description 'PIM anycast-RP peer'
                        ;
            list arp-peer {
              description 'PIM anycast-RP peer'
                          ;
              max-elements 200 ;
              key ip-addr ;
              leaf ip-addr {
                description 'IP address for communication between the RPs'
                            ;
                type ncd:ipv4-address ;
              }
            }
          }
          container groups {
            description 'PIM group'
                        ;
            list group {
              description 'PIM protect group'
                          ;
              max-elements 10 ;
              key name ;
              leaf name {
                description 'Group name (1-31 characters)'
                            ;
                type string {
                  length 1..31 ;
                }
              }
              container binds {
                description 'PIM bind interface'
                            ;
                list bind {
                  description 'PIM bind interface'
                              ;
                  max-elements 1000 ;
                  key intf-name ;
                  leaf intf-name {
                    description 'Interface name'
                                ;
                    type ncd:ifname {
                      length 1..31 ;
                    }
                  }
                  container bind-attrs {
                    description 'PIM bind interface attribute'
                                ;
                    choice bind-attr {
                      description 'PIM bind interface attribute'
                                  ;
                      mandatory true ;
                      case attr-active {
                        description 'PIM bind interface active'
                                    ;
                        leaf active {
                          description 'PIM bind interface active'
                                      ;
                          type empty ;
                        }
                      }
                      case attr-passive {
                        description 'PIM bind interface passive'
                                    ;
                        leaf passive {
                          description 'PIM bind interface passive'
                                      ;
                          type empty ;
                        }
                      }
                    }
                  }
                }
              }
            }
          }
          container arp-local {
            description 'PIM anycast-RP local interface'
                        ;
            leaf intf-name {
              description 'Interface name'
                          ;
              type ncd:ifname {
                length 1..31 ;
              }
            }
          }
          container reg-source {
            description 'Source address for PIM Register'
                        ;
            leaf intf-name {
              description 'Interface name'
                          ;
              type ncd:ifname {
                length 1..31 ;
              }
            }
          }
          container ssm-ranges {
            description 'SSM range'
                        ;
            choice ssm-range {
              description 'SSM range'
                          ;
              case range-default {
                description 'Use 232/8 group range for SSM'
                            ;
                leaf default {
                  description 'Use 232/8 group range for SSM'
                              ;
                  type empty ;
                }
              }
              case range-acl {
                description 'ACL for group range to be used for SSM'
                            ;
                leaf acl {
                  description 'ACL for group range to be used for SSM'
                              ;
                  type string {
                    length 1..31 ;
                  }
                }
              }
            }
          }
          container pfm {
            description 'PIM PFM commands.'
                        ;
            leaf gsh-enable {
              description 'GSH enable.'
                          ;
              type empty ;
            }
            leaf gsh-interval {
              description 'GSH interval.'
                          ;
              type uint16 {
                range 10..6000 ;
              }
              units second ;
              default 60 ;
            }
            leaf gsh-holdtime {
              description 'GSH holdtime.'
                          ;
              type uint16 {
                range 210..65535 ;
              }
              units second ;
              default 210 ;
            }
            leaf send-auto {
              description 'PFM messages send auto.'
                          ;
              type empty ;
            }
            leaf max-send-rate {
              description 'PFM messages max send rate.'
                          ;
              type uint16 {
                range 1..65535 ;
              }
              default 6 ;
            }
            leaf min-send-gap {
              description 'PFM messages min send gap.'
                          ;
              type uint16 {
                range 100..60000 ;
              }
              units millisecond ;
              default 1000 ;
            }
            container origin-ip {
              description 'PFM origin IP.'
                          ;
              leaf origin-ip {
                description 'PFM origin IP address.'
                            ;
                type ncd:ipv4-address ;
              }
            }
            ncd:revise-date 2019-07-15 ;
          }
          container trust-reg-sources {
            description 'PIM trustful source.'
                        ;
            list trust-reg-source {
              description 'PIM trustful source.'
                          ;
              key source-addr ;
              leaf source-addr {
                description 'IP source address for register packet.'
                            ;
                type ncd:ipv4-address ;
              }
            }
            ncd:revise-date 2019-11-12 ;
          }
        }
      }
      container pim {
        description 'Public mode of PIM module configure root node.'
                    ;
        presence 'Configure the command of router pim.'
                 ;
        container global {
          description 'Global commands'
                      ;
          leaf srp-override {
            description 'Static RP override'
                        ;
            type empty ;
          }
          leaf srp-smartswitch {
            description 'PIM RP smart switch'
                        ;
            type empty ;
          }
          leaf bsm-unicast {
            description 'PIM unicast bootstrap messages'
                        ;
            type empty ;
          }
          leaf ssm-enable {
            description 'SSM enable'
                        ;
            type empty ;
          }
          leaf dr-switch-delay-value {
            description 'PIM DR switch back delay'
                        ;
            type uint16 {
              range 1..300 ;
            }
            units second ;
          }
          leaf accept-rp-acl {
            description 'PIM RP accept filter'
                        ;
            type string {
              length 1..31 ;
            }
          }
          leaf reg-filter-acl {
            description 'PIM registers accept filter'
                        ;
            type string {
              length 1..31 ;
            }
          }
          leaf data-filter-acl {
            description 'PIM data filter'
                        ;
            type string {
              length 1..31 ;
            }
          }
          leaf jp-holdtime {
            description 'PIM router join-prune holdtime'
                        ;
            type uint16 {
              range 210..65535 ;
            }
            units second ;
            default 210 ;
          }
          leaf rp-proxy {
            description 'PIM RP proxy'
                        ;
            type empty ;
          }
          leaf reg-suppression-interval {
            description 'PIM router register suppression interval'
                        ;
            type uint16 {
              range 60..3600 ;
            }
            units second ;
            default 60 ;
          }
          leaf reg-probe-interval {
            description 'PIM router register probe interval'
                        ;
            type uint16 {
              range 1..210 ;
            }
            units second ;
            default 5 ;
          }
          leaf bidir-pim {
            description 'Enable BIDIR-PIM'
                        ;
            type empty ;
          }
          leaf jp-interval {
            description 'PIM router join-prune interval'
                        ;
            type uint16 {
              range 10..6000 ;
            }
            units second ;
            default 60 ;
          }
          leaf reg-holdtime {
            description 'Register holdtime without receiving register stop'
                        ;
            type uint16 {
              range 1..600 ;
            }
            units second ;
          }
          leaf mofrr-filter-acl {
            description 'PIM MoFRR filter'
                        ;
            type string {
              length 1..31 ;
            }
          }
          leaf mldp-signal-enable {
            description 'mldp-signal enable'
                        ;
            type empty ;
          }
          leaf mldp-signal-filter {
            description 'mldp-signal ACL'
                        ;
            type string {
              length 1..31 ;
            }
          }
          leaf assert-holdtime {
            description 'configure assert holdtime'
                        ;
            type uint16 {
              range 60..65535 ;
            }
            units second ;
            default 180 ;
          }
          leaf graft-retry-time {
            description 'configure graft retry time'
                        ;
            type uint16 {
              range 1..65535 ;
            }
            units second ;
            default 3 ;
          }
          leaf keepalive-period {
            // if-feature keepalive-period ;
            description "The configuration of keepalive period. It's validated "
                      + "minimum may be related to the performance of the  cert"
                      + "ain product."
                        ;
            type uint16 {
              range 60..65535 ;
            }
            units second ;
            default 210 ;
          }
          leaf join-prune-speed {
            description 'configure join prune speed'
                        ;
            type uint16 {
              range 1000..50000 ;
            }
            default 10000 ;
          }
          leaf cbsr-holdtime {
            description 'PIM router candidate BSR holdtime'
                        ;
            type uint16 {
              range 130..65535 ;
            }
            units second ;
            default 130 ;
            ncd:revise-date 2015-06-01 ;
          }
          leaf cbsr-interval {
            description 'PIM router candidate BSR interval'
                        ;
            type uint16 {
              range 10..65535 ;
            }
            units second ;
            default 60 ;
            ncd:revise-date 2015-06-01 ;
          }
          leaf pimdm-reg {
            description 'Send register packets when the PIM-DM interface receiv'
                      + 'es indirectly connected stream'
                        ;
            type empty ;
            ncd:revise-date 2015-09-23 ;
          }
          leaf pim-statistics-acl {
            // if-feature pim-statistics ;
            description 'PIM packet statistics filter.'
                        ;
            type string {
              length 1..31 ;
            }
            ncd:revise-date 2016-03-18 ;
          }
          leaf reg-data-forward {
            description 'PIM router register data forward.'
                        ;
            type empty ;
            ncd:revise-date 2019-07-15 ;
          }
          leaf bsr-policy-acl {
            description 'PIM BSR filter.'
                        ;
            type string {
              length 1..31 ;
            }
            ncd:revise-date 2019-07-15 ;
          }
          leaf interface-identifier {
            description 'Enable interface identifier option.'
                        ;
            type empty ;
            ncd:revise-date 2019-08-29 ;
          }
          leaf ecmp-redirect {
            description 'Enable ECMP redirect.'
                        ;
            type empty ;
            ncd:revise-date 2019-08-29 ;
          }
          leaf join-attribute {
            description 'Enable RPF vector join attribute option.'
                        ;
            type empty ;
            ncd:revise-date 2019-09-29 ;
          }
          leaf mvpn-signal-acl {
            description 'MVPN signal upstream filter.'
                        ;
            type string {
              length 1..31 ;
            }
            ncd:revise-date 2020-06-20 ;
          }
        }
        container bsr {
          description 'PIM candidate bootstrap router (candidate BSR)'
                      ;
          presence 'The leaf intf_name of this container should be mandatory, a'
                 + 'nd other leafs are not.'
                   ;
          leaf intf-name {
            description 'Interface name'
                        ;
            type ncd:ifname {
              length 1..31 ;
            }
            mandatory true ;
          }
          leaf priority {
            description 'Priority value for candidate BSR'
                        ;
            type uint8 {
              range 0..255 ;
            }
            default 0 ;
          }
          leaf hash-len {
            description 'Hash mask length for candidate BSR'
                        ;
            type uint8 {
              range 0..32 ;
            }
            default 30 ;
          }
        }
        container spt {
          description 'PIM source-tree switching threshold'
                      ;
          presence 'The leaf infinity of this container should be mandatory, an'
                 + 'd other leafs are not.'
                   ;
          leaf acl {
            description 'Access list name for group prefix'
                        ;
            type string {
              length 1..31 ;
            }
          }
          leaf infinity {
            description 'Never switch to source-tree'
                        ;
            type empty ;
            mandatory true ;
          }
        }
        container intfs {
          description 'PIM interface'
                      ;
          list intf {
            description 'PIM interface'
                        ;
            key intf-name ;
            leaf intf-name {
              description 'Interface name'
                          ;
              type ncd:ifname {
                length 1..31 ;
              }
            }
            leaf pimsm {
              description 'Enable PIM-SM operation on the interface'
                          ;
              type empty ;
            }
            leaf pimdm {
              description 'Enable PIM-DM operation on the interface'
                          ;
              type empty ;
            }
            leaf assert-disable {
              description 'PIM assert disable'
                          ;
              type empty ;
            }
            leaf bfd-enable {
              description 'PIM BFD enable'
                          ;
              type empty ;
            }
            leaf bfd-template {
              description 'Set template name for bfd'
                          ;
              type string {
                length 1..31 ;
              }
              ncd:revise-date 2020-05-19 ;
            }
            leaf bsr-border {
              description 'Border of PIM domain'
                          ;
              type empty ;
            }
            leaf dr-priority {
              description 'PIM router DR priority'
                          ;
              type uint32 {
                range 0..4294967295 ;
              }
              default 1 ;
            }
            leaf nbr-filter-acl {
              description 'PIM peering filter'
                          ;
              type string {
                length 1..31 ;
              }
            }
            leaf hello-interval {
              description 'PIM router hello interval'
                          ;
              type uint16 {
                range 1..65535 ;
              }
              units second ;
              default 30 ;
            }
            leaf silent {
              description 'PIM silent'
                          ;
              type empty ;
            }
            leaf dr-ignore {
              description 'PIM-SM DR ignore'
                          ;
              type empty ;
            }
            leaf frr-enable {
              description 'PIM FRR enable'
                          ;
              type empty ;
            }
            leaf propagation-delay {
              description 'PIM propagation delay'
                          ;
              type uint16 {
                range 1..100 ;
              }
              units 100millisecond ;
              default 5 ;
            }
            leaf override-interval {
              description 'PIM override interval'
                          ;
              type uint16 {
                range 1..600 ;
              }
              units 100millisecond ;
              default 25 ;
            }
            leaf jp-max-packet-length {
              description 'configure the max length of Join/Prune packet'
                          ;
              type uint16 {
                range 100..8100 ;
              }
              units byte ;
              default 1400 ;
            }
            leaf hello-dr-addr {
              description 'PIM hello packet sended with hello DR address'
                          ;
              type empty ;
              ncd:revise-date 2015-06-19 ;
            }
            leaf hello-track-support {
              // if-feature hello-track-support ;
              description "PIM hello packet sended with the T bit in the LAN Pr"
                        + "une Delay option, this indicates the neighbor's capa"
                        + "bility to disable Join message suppression."
                          ;
              type empty ;
              ncd:revise-date 2016-12-08 ;
            }
            leaf triggered-hello-delay {
              description 'Triggered hello delay time.'
                          ;
              type uint16 {
                range 1..5 ;
              }
              units second ;
              default 5 ;
              ncd:revise-date 2019-07-15 ;
            }
            leaf pfm-border {
              description 'PFM border.'
                          ;
              type empty ;
              ncd:revise-date 2019-07-15 ;
            }
            container ecmp-bundle {
              description 'ECMP bundle.'
                          ;
              presence ecmp-bundle ;
              leaf name {
                description 'ECMP bundle name.'
                            ;
                type string {
                  length 1..31 ;
                }
                mandatory true ;
              }
              leaf metric {
                description 'ECMP path metric.'
                            ;
                type uint64 {
                  range 1..18446744073709551615 ;
                }
                mandatory true ;
              }
              ncd:revise-date 2019-08-29 ;
            }
            leaf data-filter-acl {
              description 'PIM data filter'
                          ;
              type string {
                length 1..31 ;
              }
              ncd:revise-date 2020-09-22 ;
            }
          }
        }
        container crps {
          description 'PIM candidate RP'
                      ;
          list crp {
            description 'PIM candidate RP'
                        ;
            key intf-name ;
            leaf intf-name {
              description 'Interface name'
                          ;
              type ncd:ifname {
                length 1..31 ;
              }
            }
            leaf prefix-list {
              description Group-list ;
              type string {
                length 1..169 ;
              }
            }
            leaf priority {
              description 'Priority value for candidate RP'
                          ;
              type uint8 {
                range 0..255 ;
              }
              default 192 ;
            }
            leaf bidir-pim {
              description 'Group range treated in BIDIR-PIM'
                          ;
              type empty ;
            }
            leaf crp-holdtime {
              description 'Candidate RP holdtime'
                          ;
              type uint16 {
                range 150..65535 ;
              }
              units second ;
              default 150 ;
              ncd:revise-date 2015-06-01 ;
            }
          }
        }
        container srps {
          description 'PIM static RP'
                      ;
          list srp {
            description 'PIM static RP'
                        ;
            key ip-addr ;
            leaf ip-addr {
              description 'IP address of static RP'
                          ;
              type ncd:ipv4-address ;
            }
            leaf prefix-list {
              description Group-list ;
              type string {
                length 1..169 ;
              }
            }
            leaf priority {
              description 'Priority value for static RP'
                          ;
              type uint8 {
                range 0..255 ;
              }
              default 192 ;
            }
            leaf bidir-pim {
              description 'Group range treated in BIDIR-PIM'
                          ;
              type empty ;
            }
          }
        }
        container arp-peers {
          description 'PIM anycast-RP peer'
                      ;
          list arp-peer {
            description 'PIM anycast-RP peer'
                        ;
            key ip-addr ;
            leaf ip-addr {
              description 'IP address for communication between the RPs'
                          ;
              type ncd:ipv4-address ;
            }
          }
        }
        container groups {
          description 'PIM protect group'
                      ;
          list group {
            description 'PIM protect group'
                        ;
            key name ;
            leaf name {
              description 'Group name (1-31 characters)'
                          ;
              type string {
                length 1..31 ;
              }
            }
            container binds {
              description 'PIM bind interface'
                          ;
              list bind {
                description 'PIM bind interface'
                            ;
                key intf-name ;
                leaf intf-name {
                  description 'Interface name'
                              ;
                  type ncd:ifname {
                    length 1..31 ;
                  }
                }
                container bind-attrs {
                  description 'PIM bind interface attribute'
                              ;
                  choice bind-attr {
                    description 'PIM bind interface attribute'
                                ;
                    mandatory true ;
                    case attr-active {
                      description 'PIM bind interface active'
                                  ;
                      leaf active {
                        description 'PIM bind interface active'
                                    ;
                        type empty ;
                      }
                    }
                    case attr-passive {
                      description 'PIM bind interface passive'
                                  ;
                      leaf passive {
                        description 'PIM bind interface passive'
                                    ;
                        type empty ;
                      }
                    }
                  }
                }
              }
            }
          }
        }
        container arp-local {
          description 'PIM anycast-RP local interface'
                      ;
          leaf intf-name {
            description 'Interface name'
                        ;
            type ncd:ifname {
              length 1..31 ;
            }
          }
        }
        container reg-source {
          description 'Source address for PIM Register'
                      ;
          leaf intf-name {
            description 'Interface name'
                        ;
            type ncd:ifname {
              length 1..31 ;
            }
          }
        }
        container ssm-ranges {
          description 'SSM range'
                      ;
          choice ssm-range {
            description 'SSM range'
                        ;
            case range-default {
              description 'Use 232/8 group range for SSM'
                          ;
              leaf default {
                description 'Use 232/8 group range for SSM'
                            ;
                type empty ;
              }
            }
            case range-acl {
              description 'ACL for group range to be used for SSM'
                          ;
              leaf acl {
                description 'ACL for group range to be used for SSM'
                            ;
                type string {
                  length 1..31 ;
                }
              }
            }
          }
        }
        container pfm {
          description 'PIM PFM commands.'
                      ;
          leaf gsh-enable {
            description 'GSH enable.'
                        ;
            type empty ;
          }
          leaf gsh-interval {
            description 'GSH interval.'
                        ;
            type uint16 {
              range 10..6000 ;
            }
            units second ;
            default 60 ;
          }
          leaf gsh-holdtime {
            description 'GSH holdtime.'
                        ;
            type uint16 {
              range 210..65535 ;
            }
            units second ;
            default 210 ;
          }
          leaf send-auto {
            description 'PFM messages send auto.'
                        ;
            type empty ;
          }
          leaf max-send-rate {
            description 'PFM messages max send rate.'
                        ;
            type uint16 {
              range 1..65535 ;
            }
            default 6 ;
          }
          leaf min-send-gap {
            description 'PFM messages min send gap.'
                        ;
            type uint16 {
              range 100..60000 ;
            }
            units millisecond ;
            default 1000 ;
          }
          container origin-ip {
            description 'PFM origin IP.'
                        ;
            leaf origin-ip {
              description 'PFM origin IP address.'
                          ;
              type ncd:ipv4-address ;
            }
          }
          ncd:revise-date 2019-07-15 ;
        }
        container trust-reg-sources {
          description 'PIM trustful source.'
                      ;
          list trust-reg-source {
            description 'PIM trustful source.'
                        ;
            key source-addr ;
            leaf source-addr {
              description 'IP source address for register packet.'
                          ;
              type ncd:ipv4-address ;
            }
          }
          ncd:revise-date 2019-11-12 ;
        }
      }
    }
  }
  container state {
    config false ;
    description 'PIM module show information.'
                ;
    container pim {
      description 'PIM module show information.'
                  ;
      container public {
        description 'Public mode of PIM module.'
                    ;
        container intfs {
          description 'PIM interface information.'
                      ;
          list intf {
            description 'PIM interface information.'
                        ;
            key intf-name ;
            leaf intf-name {
              description 'Interface name'
                          ;
              type ncd:ifname {
                length 1..31 ;
              }
            }
            leaf nbr-count {
              description 'Neighbor count'
                          ;
              type int32 ;
            }
            leaf dr-priority {
              description 'PIM router DR priority'
                          ;
              type uint32 ;
            }
            leaf address {
              description 'Interface address'
                          ;
              type ncd:ipv4-address ;
            }
            leaf dr-addr {
              description 'DR address'
                          ;
              type ncd:ipv4-address ;
            }
            leaf hello-period {
              description 'PIM router hello interval'
                          ;
              type uint16 {
                range 1..65535 ;
              }
              units second ;
            }
            leaf state {
              description 'Interface state:1 is up;2 is down.'
                          ;
              type enumeration {
                enum up {
                  value 1 ;
                }
                enum down {
                  value 2 ;
                }
              }
            }
            leaf mode {
              description 'The mode used by the interface:'+"\n"
                        + '1 - PIM-SM protocol;'+"\n"
                        + '2 - PIM-DM protocol;'+"\n"
                        + '3 - PIM-SM and PIM-DM protocol.'
                          ;
              type enumeration {
                enum S {
                  value 1 ;
                }
                enum D {
                  value 2 ;
                }
                enum SD {
                  value 3 ;
                }
              }
            }
            leaf pim-silent {
              description 'Enable or disable PIM silent:'+"\n"
                        + '0 - Disable;'+"\n"
                        + '1 - Enable.'
                          ;
              type enumeration {
                enum Disable {
                  value 0 ;
                }
                enum Enable {
                  value 1 ;
                }
              }
            }
            ncd:select intf-name ;
          }
        }
        container bfds {
          description 'PIM BFD information.'
                      ;
          list bfd {
            description 'PIM BFD information.'
                        ;
            key 'intf-name local-addr peer-addr'
                ;
            leaf intf-name {
              description 'Interface name'
                          ;
              type ncd:ifname {
                length 1..31 ;
              }
            }
            leaf local-addr {
              description 'Local address'
                          ;
              type ncd:ipv4-address ;
            }
            leaf peer-addr {
              description 'Peer address'
                          ;
              type ncd:ipv4-address ;
            }
            leaf local-state {
              description 'Local state, including "DR","BDR".'
                          ;
              type ncd:string-all {
                length 0..7 ;
              }
            }
            leaf peer-state {
              description 'Peer state, including "DR","BDR".'
                          ;
              type ncd:string-all {
                length 0..7 ;
              }
            }
            leaf bfd-state {
              description 'BFD session state:'+"\n"
                        + '0 - INIT;'+"\n"
                        + '1 - CREATE;'+"\n"
                        + '2 - CONNECT;'+"\n"
                        + '3 - UP;'+"\n"
                        + '4 - DOWN;'+"\n"
                        + '5 - NOT SURPPORT;'+"\n"
                        + '6 - ADMIN DOWN;'+"\n"
                        + '7 - BFD_ERROR.'
                          ;
              type enumeration {
                enum INIT {
                  value 0 ;
                }
                enum CREATE {
                  value 1 ;
                }
                enum CONNECT {
                  value 2 ;
                }
                enum UP {
                  value 3 ;
                }
                enum DOWN {
                  value 4 ;
                }
                enum NOT-SUPPORT {
                  value 5 ;
                }
                enum ADMIN-DOWN {
                  value 6 ;
                }
                enum BFD-ERROR {
                  value 7 ;
                }
              }
            }
            ncd:select intf-name ;
          }
        }
        container bsr {
          description 'PIM BSR information.'
                      ;
          container ebsr {
            description 'E-BSR information'
                        ;
            leaf address {
              description 'E-BSR address'
                          ;
              type ncd:ipv4-address ;
            }
            leaf priority {
              description 'E-BSR priority'
                          ;
              type uint8 {
                range 0..255 ;
              }
            }
            leaf hash-mask {
              description 'E-BSR hash mask length'
                          ;
              type uint8 {
                range 0..32 ;
              }
            }
            leaf uptime {
              description 'E-BSR uptime'
                          ;
              type ncd:string-all {
                length 0..15 ;
              }
            }
            leaf expire-time {
              description 'E-BSR expire time'
                          ;
              type ncd:string-all {
                length 0..15 ;
              }
            }
          }
          container cbsr {
            description 'C-BSR information'
                        ;
            leaf address {
              description 'C-BSR address'
                          ;
              type ncd:ipv4-address ;
            }
            leaf intf-name {
              description 'C-BSR interface name.'
                          ;
              type ncd:ifname {
                length 0..31 ;
              }
            }
            leaf priority {
              description 'C-BSR priority'
                          ;
              type uint8 {
                range 0..255 ;
              }
            }
            leaf hash-mask {
              description 'C-BSR hash mask length'
                          ;
              type uint8 {
                range 0..32 ;
              }
            }
          }
          container crps {
            description 'C-RP information'
                        ;
            list crp {
              description 'C-RP information'
                          ;
              key intf-name ;
              leaf intf-name {
                description 'C-RP interface name'
                            ;
                type ncd:ifname {
                  length 0..31 ;
                }
              }
              leaf address {
                description 'C-RP address'
                            ;
                type ncd:ipv4-address ;
              }
              leaf priority {
                description 'C-RP priority'
                            ;
                type uint8 {
                  range 0..255 ;
                }
              }
              leaf group-list {
                description 'C-RP group list'
                            ;
                type ncd:string-all {
                  length 0..169 ;
                }
              }
              leaf intf-state {
                description 'C-RP interface state.When the interface is down or'
                          + ' does not have address,the state is invalid.'
                            ;
                type ncd:string-all {
                  length 0..7 ;
                }
              }
            }
          }
        }
        container neighbors {
          description 'PIM neighbor information.'
                      ;
          list nbr {
            description 'PIM neighbor information.'
                        ;
            key 'intf-name nbr-addr'
                ;
            leaf intf-name {
              description 'Interface name.'
                          ;
              type ncd:ifname {
                length 1..31 ;
              }
            }
            leaf nbr-addr {
              description 'IP address of neighbor.'
                          ;
              type ncd:ipv4-address ;
            }
            leaf uptime {
              description 'Uptime of neighbor.'
                          ;
              type string {
                length 1..15 ;
              }
            }
            leaf expire-time {
              description 'Expire time of neighbor.'
                          ;
              type string {
                length 1..15 ;
              }
            }
            leaf dr-priority {
              description 'DR priority of neighbor.'
                          ;
              type ncd:string-all {
                length 0..11 ;
              }
            }
            leaf join-attr {
              description 'Join attribute of neighbor: 
1 - P; 
2 - N/A.'
                          ;
              type enumeration {
                enum P {
                  value 1 ;
                }
                enum N/A {
                  value 2 ;
                }
              }
            }
            ncd:select intf-name ;
          }
        }
        container rp-hashs {
          description 'PIM RP-hash information.'
                      ;
          list rp-hash {
            description 'PIM RP-hash information.'
                        ;
            key group-addr ;
            leaf group-addr {
              description 'Group address.'
                          ;
              type ncd:ipv4-address ;
            }
            leaf rp-addr {
              description 'RP address.'
                          ;
              type ncd:ipv4-address ;
            }
            leaf srp-override {
              description 'Static RP is overriding in group-set.'
                          ;
              type boolean ;
            }
            ncd:select group-addr ;
          }
        }
        container rp-mappings {
          description 'PIM RP-mapping information.'
                      ;
          list rp-mapping {
            description 'RP-mapping information.'
                        ;
            key 'grp-addr gmask-addr rpset-type'
                ;
            leaf grp-addr {
              description 'Group address.'
                          ;
              type ncd:ipv4-address ;
            }
            leaf gmask-addr {
              description 'Group mask address.'
                          ;
              type ncd:ipv4-mask ;
            }
            leaf rpset-type {
              description 'The type of RP set node:'+"\n"
                        + '1 - Noused;'+"\n"
                        + '2 - Static;'+"\n"
                        + '3 - BSR.'
                          ;
              type enumeration {
                enum Noused {
                  value 1 ;
                }
                enum Static {
                  value 2 ;
                }
                enum BSR {
                  value 3 ;
                }
              }
            }
            leaf protocol {
              description 'The protocol of RP set node, including "NOUSED", "SM'
                        + '".'
                          ;
              type ncd:string-all {
                length 0..7 ;
              }
            }
            leaf srp-override {
              description 'Static RP is overriding in group-set.'
                          ;
              type boolean ;
            }
            container rp-infos {
              description 'RP information.'
                          ;
              list rp-info {
                description 'RP information.'
                            ;
                key rp-addr ;
                leaf rp-addr {
                  description 'RP address.'
                              ;
                  type ncd:ipv4-address ;
                }
                leaf bidir {
                  description 'The RP is enabled bidir PIM.'
                              ;
                  type empty ;
                }
                leaf rp-priority {
                  description 'RP priority.'
                              ;
                  type uint32 {
                    range 0..255 ;
                  }
                }
                leaf bsr-addr {
                  description 'BSR address.'
                              ;
                  type ncd:ipv4-address ;
                }
                leaf uptime {
                  description 'Uptime of RP.'
                              ;
                  type ncd:string-all {
                    length 0..15 ;
                  }
                }
                leaf expire-time {
                  description 'Expire time of RP.'
                              ;
                  type ncd:string-all {
                    length 0..15 ;
                  }
                }
                ncd:select rp-addr ;
              }
            }
            ncd:select grp-addr ;
          }
        }
        container nhps {
          description 'PIM nexthop information.'
                      ;
          list nhp {
            description 'PIM nexthop information.'
                        ;
            key dest-addr ;
            leaf dest-addr {
              description 'Destination address'
                          ;
              type ncd:ipv4-address ;
            }
            leaf type {
              description 'Nexthop state: R- Nexthop to RP,S- Nexthop to Source'
                        + ', O- Related with Unicast,U- No Unicast Route, L- Lo'
                        + 'cal Route,C- Connect to Destination address.'
                          ;
              type ncd:string-all {
                length 0..15 ;
              }
            }
            leaf expire-time {
              description 'Nexthop expire time'
                          ;
              type ncd:string-all {
                length 0..15 ;
              }
            }
            leaf metric {
              description 'Nexthop metric'
                          ;
              type uint32 ;
            }
            leaf preference {
              description 'Nexthop preference'
                          ;
              type uint32 ;
            }
            leaf fallback-vrf {
              description 'The VRF name of fallback nexthop.'
                          ;
              type string {
                length 0..32 ;
              }
              ncd:revise-date 2015-12-15 ;
            }
            container ecmps {
              description 'ECMP information'
                          ;
              list ecmp {
                description 'ECMP information'
                            ;
                key 'nhp-addr port-name'
                    ;
                leaf nhp-addr {
                  description 'Nexthop address'
                              ;
                  type ncd:ipv4-address ;
                }
                leaf port-name {
                  description 'Nexthop port name'
                              ;
                  type ncd:ifname {
                    length 0..31 ;
                  }
                }
                leaf nbr-addr {
                  description 'Neighbor address'
                              ;
                  type ncd:ipv4-address ;
                }
                leaf local-flag {
                  description 'Nexthop is local.'
                              ;
                  type ncd:string-all {
                    length 0..11 ;
                  }
                }
                ncd:select 'nhp-addr port-name'
                           ;
              }
            }
            ncd:select dest-addr ;
          }
        }
        container groups {
          description 'PIM group information.'
                      ;
          list group {
            description 'PIM group information.'
                        ;
            key group-name ;
            leaf group-name {
              description 'Group name.'
                          ;
              type string {
                length 1..31 ;
              }
            }
            leaf group-id {
              description 'Group ID.'
                          ;
              type uint32 ;
            }
            leaf bind-num {
              description 'Total bind interface number.'
                          ;
              type uint32 ;
            }
            container binds {
              description 'PIM bind interface information.'
                          ;
              list bind {
                description 'PIM bind interface information.'
                            ;
                key intf-name ;
                leaf intf-name {
                  description 'Bind interface name.'
                              ;
                  type ncd:ifname {
                    length 0..31 ;
                  }
                }
                leaf bind-state {
                  description 'Bind interface state:
1 - Active;
2 - Passive.'
                              ;
                  type enumeration {
                    enum Active {
                      value 1 ;
                    }
                    enum Passive {
                      value 2 ;
                    }
                  }
                }
                leaf forward-state {
                  description 'Interface forward state:
1 - TRUE;
2 - FALSE.'
                              ;
                  type boolean ;
                }
              }
            }
            ncd:select group-name ;
          }
        }
        container traffic {
          description 'PIM traffic information.'
                      ;
          list intf-traffic {
            description 'PIM interface traffic information.'
                        ;
            key intf-name ;
            leaf intf-name {
              description 'Interface name.'
                          ;
              type ncd:ifname {
                length 0..31 ;
              }
            }
            leaf hello-send {
              description 'The number of hello messages sent by a PIM interface.'
                          ;
              type uint32 ;
            }
            leaf hello-rcv {
              description 'The number of hello messages received by a PIM inter'
                        + 'face.'
                          ;
              type uint32 ;
            }
            leaf reg-send {
              description 'The number of register messages sent by a PIM interf'
                        + 'ace.'
                          ;
              type uint32 ;
            }
            leaf reg-rcv {
              description 'The number of register messages received by a PIM in'
                        + 'terface.'
                          ;
              type uint32 ;
            }
            leaf reg-stop-send {
              description 'The number of register-stop messages sent by a PIM i'
                        + 'nterface.'
                          ;
              type uint32 ;
            }
            leaf reg-stop-rcv {
              description 'The number of register-stop messages received by a P'
                        + 'IM interface.'
                          ;
              type uint32 ;
            }
            leaf jp-send {
              description 'The number of join/prune messages sent by a PIM inte'
                        + 'rface.'
                          ;
              type uint32 ;
            }
            leaf jp-rcv {
              description 'The number of join/prune messages received by a PIM '
                        + 'interface.'
                          ;
              type uint32 ;
            }
            leaf bsm-send {
              description 'The number of bootstrap messages sent by a PIM inter'
                        + 'face.'
                          ;
              type uint32 ;
            }
            leaf bsm-rcv {
              description 'The number of bootstrap messages received by a PIM i'
                        + 'nterface.'
                          ;
              type uint32 ;
            }
            leaf assert-send {
              description 'The number of assert messages sent by a PIM interfac'
                        + 'e.'
                          ;
              type uint32 ;
            }
            leaf assert-rcv {
              description 'The number of assert messages received by a PIM inte'
                        + 'rface.'
                          ;
              type uint32 ;
            }
            leaf graft-send {
              description 'The number of graft messages sent by a PIM interface.'
                          ;
              type uint32 ;
            }
            leaf graft-rcv {
              description 'The number of graft messages received by a PIM inter'
                        + 'face.'
                          ;
              type uint32 ;
            }
            leaf graft-ack-send {
              description 'The number of graft ack messages sent by a PIM inter'
                        + 'face.'
                          ;
              type uint32 ;
            }
            leaf graft-ack-rcv {
              description 'The number of graft ack messages received by a PIM i'
                        + 'nterface.'
                          ;
              type uint32 ;
            }
            leaf crp-adv-send {
              description 'The number of candidate-RP-advertisement messages se'
                        + 'nt by a PIM interface.'
                          ;
              type uint32 ;
            }
            leaf crp-adv-rcv {
              description 'The number of candidate-RP-advertisement messages re'
                        + 'ceived by a PIM interface.'
                          ;
              type uint32 ;
            }
            leaf sr-send {
              description 'The number of state refresh messages sent by a PIM i'
                        + 'nterface.'
                          ;
              type uint32 ;
            }
            leaf sr-rcv {
              description 'The number of state refresh messages received by a P'
                        + 'IM interface.'
                          ;
              type uint32 ;
            }
            leaf df-elct-send {
              description 'The number of DF election messages sent by a PIM int'
                        + 'erface.'
                          ;
              type uint32 ;
            }
            leaf df-elct-rcv {
              description 'The number of DF election messages received by a PIM'
                        + ' interface.'
                          ;
              type uint32 ;
            }
            ncd:select intf-name ;
          }
          container total {
            description 'Total traffic in current PIM instance.'
                        ;
            leaf total-pkt-rcv {
              description 'The number of protocol messages received by a PIM in'
                        + 'stance.'
                          ;
              type uint32 ;
            }
            leaf total-pkt-send {
              description 'The number of protocol messages sent by a PIM instan'
                        + 'ce.'
                          ;
              type uint32 ;
            }
            leaf pkt-rcv-error {
              description 'The number of error protocol messages received by a '
                        + 'PIM instance.'
                          ;
              type uint32 ;
            }
            leaf hello-send {
              description 'The number of hello messages sent by a PIM instance.'
                          ;
              type uint32 ;
            }
            leaf hello-rcv {
              description 'The number of hello messages received by a PIM insta'
                        + 'nce.'
                          ;
              type uint32 ;
            }
            leaf reg-send {
              description 'The number of register messages sent by a PIM instan'
                        + 'ce.'
                          ;
              type uint32 ;
            }
            leaf reg-rcv {
              description 'The number of register messages received by a PIM in'
                        + 'stance.'
                          ;
              type uint32 ;
            }
            leaf reg-stop-send {
              description 'The number of register-stop messages sent by a PIM i'
                        + 'nstance.'
                          ;
              type uint32 ;
            }
            leaf reg-stop-rcv {
              description 'The number of register-stop messages received by a P'
                        + 'IM instance.'
                          ;
              type uint32 ;
            }
            leaf jp-send {
              description 'The number of join/prune messages sent by a PIM inst'
                        + 'ance.'
                          ;
              type uint32 ;
            }
            leaf jp-rcv {
              description 'The number of join/prune messages received by a PIM '
                        + 'instance.'
                          ;
              type uint32 ;
            }
            leaf bsm-send {
              description 'The number of bootstrap messages sent by a PIM insta'
                        + 'nce.'
                          ;
              type uint32 ;
            }
            leaf bsm-rcv {
              description 'The number of bootstrap messages received by a PIM i'
                        + 'nstance.'
                          ;
              type uint32 ;
            }
            leaf assert-send {
              description 'The number of assert messages sent by a PIM instance.'
                          ;
              type uint32 ;
            }
            leaf assert-rcv {
              description 'The number of assert messages received by a PIM inst'
                        + 'ance.'
                          ;
              type uint32 ;
            }
            leaf graft-send {
              description 'The number of graft messages sent by a PIM instance.'
                          ;
              type uint32 ;
            }
            leaf graft-rcv {
              description 'The number of graft messages received by a PIM insta'
                        + 'nce.'
                          ;
              type uint32 ;
            }
            leaf graft-ack-send {
              description 'The number of graft ack messages sent by a PIM insta'
                        + 'nce.'
                          ;
              type uint32 ;
            }
            leaf graft-ack-rcv {
              description 'The number of graft ack messages received by a PIM i'
                        + 'nstance.'
                          ;
              type uint32 ;
            }
            leaf crp-adv-send {
              description 'The number of candidate-RP-advertisement messages se'
                        + 'nt by a PIM instance.'
                          ;
              type uint32 ;
            }
            leaf crp-adv-rcv {
              description 'The number of candidate-RP-advertisement messages re'
                        + 'ceived by a PIM instance.'
                          ;
              type uint32 ;
            }
            leaf sr-send {
              description 'The number of state refresh messages sent by a PIM i'
                        + 'nstance.'
                          ;
              type uint32 ;
            }
            leaf sr-rcv {
              description 'The number of state refresh messages received by a P'
                        + 'IM instance.'
                          ;
              type uint32 ;
            }
            leaf df-elct-send {
              description 'The number of DF election messages sent by a PIM ins'
                        + 'tance.'
                          ;
              type uint32 ;
            }
            leaf df-elct-rcv {
              description 'The number of DF election messages received by a PIM'
                        + ' instance.'
                          ;
              type uint32 ;
            }
          }
        }
        container dfs {
          description 'PIM designated forwarder information.'
                      ;
          list df {
            description 'PIM designated forwarder information.'
                        ;
            key rp-addr ;
            leaf rp-addr {
              description 'Rendezvous Point address.'
                          ;
              type ncd:ipv4-address ;
            }
            container rpa-states {
              description 'The DF election information.'
                          ;
              list rpa-state {
                description 'The DF election information.'
                            ;
                key intf-name ;
                leaf intf-name {
                  description 'DF interface name.'
                              ;
                  type ncd:ifname {
                    length 0..31 ;
                  }
                }
                leaf state {
                  description 'DF election state,including "OFFER","LOSE","WIN"'
                            + ',"BACKOFF","NONE(RPL)".'
                              ;
                  type ncd:string-all {
                    length 0..15 ;
                  }
                }
                leaf timeout {
                  description 'DF election-Timer expire time.'
                              ;
                  type ncd:string-all {
                    length 0..15 ;
                  }
                }
                leaf message-count {
                  description 'The number of times an Offer or Winner message h'
                            + 'as been transmitted.'
                              ;
                  type uint32 ;
                }
                leaf local-addr {
                  description 'Local DF address.'
                              ;
                  type ncd:ipv4-address ;
                }
                leaf local-metric {
                  description 'Local DF metric.'
                              ;
                  type uint32 ;
                }
                leaf local-pref {
                  description 'Local DF preference.'
                              ;
                  type uint32 ;
                }
                leaf acting-addr {
                  description 'Acting DF address.'
                              ;
                  type ncd:ipv4-address ;
                }
                leaf acting-metric {
                  description 'Acting DF metric.'
                              ;
                  type uint32 ;
                }
                leaf acting-pref {
                  description 'Acting DF preference.'
                              ;
                  type uint32 ;
                }
                leaf last-addr {
                  description 'The address of the router that made the last Off'
                            + 'er.'
                              ;
                  type ncd:ipv4-address ;
                }
                leaf last-metric {
                  description 'The unicast routing table metric used by the rou'
                            + 'ter that made the last Offer to reach the RPA.'
                              ;
                  type uint32 ;
                }
                leaf last-pref {
                  description 'Preference value assigned to the unicast routing'
                            + ' protocol used by the router that made the last '
                            + 'Offer to obtain the route to the RPA.'
                              ;
                  type uint32 ;
                }
              }
            }
            ncd:select rp-addr ;
          }
        }
        container summary {
          description 'The statistics information of the IP multicast PIM route'
                    + ' table.'
                      ;
          container mr-num {
            description 'The number of PIM route.'
                        ;
            leaf xg {
              description 'The number of (*, G) route.'
                          ;
              type uint32 ;
            }
            leaf sg {
              description 'The number of (S, G) route.'
                          ;
              type uint32 ;
            }
            leaf sgrpt {
              description 'The number of (S, G, rpt) route.'
                          ;
              type uint32 ;
            }
            leaf reg {
              description 'The number of register route.'
                          ;
              type uint32 ;
            }
          }
          list mr-state {
            description 'The summary state of PIM mroute.'
                        ;
            key 'group-addr source-addr'
                ;
            leaf group-addr {
              description 'Group address.'
                          ;
              type ncd:ipv4-address ;
            }
            leaf source-addr {
              description 'Source address.'
                          ;
              type ncd:ipv4-address ;
            }
            leaf rp-addr {
              description 'RP address.'
                          ;
              type ncd:ipv4-address ;
            }
            leaf xg-us-state {
              description 'Upstream (*,G) join/prune state,including "NOT JOINE'
                        + 'D","JOINED".'
                          ;
              type ncd:string-all {
                length 0..11 ;
              }
            }
            leaf sg-us-state {
              description 'Upstream (S,G) join/prune state,including "NOT JOINE'
                        + 'D","JOINED".'
                          ;
              type ncd:string-all {
                length 0..11 ;
              }
            }
            leaf sgrpt-us-state {
              description 'Upstream (S,G,rpt) join/prune state,including "RPT N'
                        + 'OT JOINED","PRUNED","NOT PRUNED".'
                          ;
              type ncd:string-all {
                length 0..15 ;
              }
            }
            ncd:select group-addr ;
            ncd:select 'group-addr source-addr'
                       ;
          }
        }
        container mroutes {
          description 'PIM mroute information.'
                      ;
          list mroute {
            description 'PIM mroute information.'
                        ;
            key 'source group'
                ;
            leaf source {
              description 'Source address information'
                          ;
              type ncd:ipv4-address ;
            }
            leaf group {
              description 'Group address information'
                          ;
              type ncd:ipv4-address ;
            }
            leaf rp-address {
              description 'RP address information.'
                          ;
              type ncd:ipv4-address ;
              mandatory true ;
            }
            leaf rpf-nbr {
              description 'RPF neighbor address.'
                          ;
              type ncd:ipv4-address ;
            }
            leaf reg-state {
              description 'Register state, "NO INFO","JOIN","PRUNE","JOIN PENDI'
                        + 'NG".'
                          ;
              type ncd:string-all {
                length 0..15 ;
              }
            }
            leaf reg-tunnel {
              description 'Register tunnel information.'
                          ;
              type ncd:ifname {
                length 0..31 ;
              }
            }
            leaf uptime {
              description 'Mroute uptime.'
                          ;
              type ncd:string-all {
                length 0..15 ;
              }
            }
            leaf kat {
              description 'Keepalive timer.'
                          ;
              type ncd:string-all {
                length 0..15 ;
              }
            }
            leaf jp-expire-time {
              description 'Upstream join/prune expire timer.'
                          ;
              type ncd:string-all {
                length 0..15 ;
              }
            }
            leaf msdp-state {
              description 'MSDP state information, "SA CREATE", "TO BE ADV".'
                          ;
              type ncd:string-all {
                length 0..15 ;
              }
            }
            leaf iif-name {
              description 'Mroute incoming interface.'
                          ;
              type ncd:ifname {
                length 0..31 ;
              }
            }
            leaf upstream-state {
              description 'Upstream state information, "NOT JOINED","JOINED".'
                          ;
              type ncd:string-all {
                length 0..15 ;
              }
            }
            leaf state-statistics {
              description 'Mroute state statistics information:'+"\n"
                        + 'Ind-Pim Include macro,'+"\n"
                        + 'Exd-Pim Exclude macro, '+"\n"
                        + 'Jns-Pim Joins macro,'+"\n"
                        + 'LAst-Pim Lost_assert macro, '+"\n"
                        + 'Imo-Pim Immediate_olist macro,'+"\n"
                        + 'Ino-Pim Inherited_olist macro, '+"\n"
                        + 'Lcd-Pim Local_receiver_include macro, '+"\n"
                        + 'Fbk-Fallback_extranet_receiver_number.'
                          ;
              type ncd:string-all {
                length 0..71 ;
              }
            }
            leaf dm-upstream-state {
              description 'Upstream PIM-DM state information, "FORWARD", "PRUNE'
                        + 'D","ACK_PENDING".'
                          ;
              type ncd:string-all {
                length 0..15 ;
              }
            }
            leaf dm-rpf-nbr {
              description 'PIM-DM RPF neighbor address'
                          ;
              type ncd:ipv4-address ;
            }
            leaf flags {
              description 'Mroute flags, "A", "T", "U", "J".'
                          ;
              type ncd:string-all {
                length 0..7 ;
              }
            }
            leaf prune-limit-timer {
              description 'PIM-DM prune limit timer'
                          ;
              type ncd:string-all {
                length 0..15 ;
              }
            }
            leaf vector-address {
              description 'Vector address information'
                          ;
              type ncd:ipv4-address ;
            }
            leaf mofrr-iif {
              description 'MoFRR incoming interface information'
                          ;
              type ncd:ifname {
                length 0..31 ;
              }
            }
            leaf mofrr-rpf-nbr {
              description 'MoFRR RPF neighbor address'
                          ;
              type ncd:ipv4-address ;
            }
            leaf sg-rpt-uptime {
              description 'SG-RPT uptime'
                          ;
              type ncd:string-all {
                length 0..15 ;
              }
            }
            leaf sg-rpt-ov-time {
              description 'SG-RPT override timer'
                          ;
              type ncd:string-all {
                length 0..15 ;
              }
            }
            leaf sg-rpt-rpf-nbr {
              description 'SG-RPT RPF neighbor address'
                          ;
              type ncd:ipv4-address ;
            }
            leaf sg-rpt-iif-name {
              description 'SG-RPT incoming interface information'
                          ;
              type ncd:ifname {
                length 0..31 ;
              }
            }
            leaf sg-rpt-upstream-state {
              description 'SG-RPT upstream state information, "RPT NOT JOINED",'
                        + '"PRUNED","NOT PRUNED".'
                          ;
              type ncd:string-all {
                length 0..15 ;
              }
            }
            leaf sg-rpt-state-statistics {
              description 'SG-RPT state statistics information:'+"\n"
                        + 'Ind-Pim Include macro,'+"\n"
                        + 'Exd-Pim Exclude macro, '+"\n"
                        + 'Jns-Pim Joins macro,'+"\n"
                        + 'LAst-Pim Lost_assert macro, '+"\n"
                        + 'Imo-Pim Immediate_olist macro,'+"\n"
                        + 'Ino-Pim Inherited_olist macro, '+"\n"
                        + 'Lcd-Pim Local_receiver_include macro.'
                          ;
              type ncd:string-all {
                length 0..39 ;
              }
            }
            leaf sg-rpt-flags {
              description 'SG-RPT mroute flags information, "A".'
                          ;
              type ncd:string-all {
                length 0..7 ;
              }
            }
            leaf fallback-vrf {
              description 'The upstream VRF name of mroute.'
                          ;
              type string {
                length 0..32 ;
              }
              ncd:revise-date 2015-12-15 ;
            }
            container oif-lists {
              description 'Outcoming interface list'
                          ;
              list oif-list {
                description 'Outcoming interface list'
                            ;
                key intf-name ;
                leaf intf-name {
                  description 'Outcoming interface name'
                              ;
                  type ncd:ifname {
                    length 0..31 ;
                  }
                }
                leaf oif-macro {
                  description 'Outcoming interface macro information:'+"\n"
                            + 'LocalIn-Local include join,'+"\n"
                            + 'AstW-Assert winner state,'+"\n"
                            + 'AstL-Assert loser state,'+"\n"
                            + 'LostAst-LostAssert macro,'+"\n"
                            + 'ImoXG-ImmediateOlist XG macro,'+"\n"
                            + 'Bidir-RPF-Bidir RPF RP macro,'+"\n"
                            + 'JoinsSG-Pim JoinsSG Macro,'+"\n"
                            + 'PrunesSGRpt-PrunesSGRpt macro,'+"\n"
                            + 'LocalInSG-Local include join SG,'+"\n"
                            + 'LocalExSG-Local exclude join SG,'+"\n"
                            + 'AstWSG-Assert winner SG state,'+"\n"
                            + 'AstLSG-Assert loser SG state,'+"\n"
                            + 'LostAstSG-LostAssert SG macro,'+"\n"
                            + 'LostAstSGRpt-LostAssert SG-RPT macro,'+"\n"
                            + 'InheritedFromXG-ImmediateOlistXG macro,'+"\n"
                            + 'InoSGRpt-InheritedOlistSGRpt macro,'+"\n"
                            + 'InoSG-InheritedOlistSG macro,'+"\n"
                            + 'DenseAstWSG-PIM-DM assert winner state,'+"\n"
                            + 'DenseAstLSG-PIM-DM lost assert SG state,'+"\n"
                            + 'DensePruneSG-PIM-DM pruned state,'+"\n"
                            + 'DenseLostAst-PIM-DM lost assert SG macro,'+"\n"
                            + 'DenseOlist-PIM-DM OlistSG macro.'
                              ;
                  type ncd:string-all {
                    length 0..255 ;
                  }
                }
              }
            }
            ncd:select 'source group'
                       ;
            ncd:select group ;
          }
        }
        container statistics {
          // if-feature pim-statistics ;
          description 'PIM packet statistics information.'
                      ;
          list statistic {
            description 'PIM packet statistics information.'
                        ;
            key 'source group'
                ;
            leaf source {
              description 'Source address.'
                          ;
              type ncd:ipv4-address ;
            }
            leaf group {
              description 'Group address.'
                          ;
              type ncd:ipv4-address ;
            }
            leaf in-bytes {
              description 'Byte count of received multicast packet.'
                          ;
              type string {
                length 0..23 ;
              }
            }
            leaf in-packets {
              description 'Received multicast packet count.'
                          ;
              type string {
                length 0..23 ;
              }
            }
            leaf in-byte-rate {
              description '120s input rate(Bps).'
                          ;
              type string {
                length 0..23 ;
              }
            }
            leaf in-packet-rate {
              description '120s input rate(pps).'
                          ;
              type string {
                length 0..23 ;
              }
            }
            leaf counter-state {
              description 'Hardware counter state.If the hardware counter is no'
                        + 't working, the value of the node is not working.'
                          ;
              type ncd:string-all {
                length 0..23 ;
              }
            }
            leaf join-sent {
              description 'The count of (*,G) or (S,G) join message sent.'
                          ;
              type uint32 ;
            }
            leaf prune-sent {
              description 'The count of (*,G) or (S,G) prune message sent.'
                          ;
              type uint32 ;
            }
            leaf sgrpt-join-sent {
              description 'The count of (S,G,rpt) join message sent.'
                          ;
              type uint32 ;
            }
            leaf sgrpt-prune-sent {
              description 'The count of (S,G,rpt) prune message sent.'
                          ;
              type uint32 ;
            }
            ncd:select group ;
            ncd:select 'source group'
                       ;
          }
          ncd:revise-date 2016-03-18 ;
        }
        container intf-brief {
          description 'PIM interface brief information.'
                      ;
          container total-num {
            description 'The total number of PIM interface.'
                        ;
            leaf intf-num {
              description 'The number of PIM interface.'
                          ;
              type uint32 ;
            }
          }
          list intf-info {
            description 'PIM interface brief information.'
                        ;
            key intf-name ;
            leaf intf-name {
              description 'Interface name'
                          ;
              type ncd:ifname {
                length 1..31 ;
              }
            }
            leaf nbr-count {
              description 'Neighbor count'
                          ;
              type int32 ;
            }
            leaf dr-priority {
              description 'PIM router DR priority'
                          ;
              type uint32 ;
            }
            leaf dr-addr {
              description 'DR address'
                          ;
              type ncd:ipv4-address ;
            }
            leaf hello-period {
              description 'PIM router hello interval'
                          ;
              type uint16 {
                range 1..65535 ;
              }
              units second ;
            }
            leaf state {
              description 'Interface state:1 is up;2 is down.'
                          ;
              type enumeration {
                enum up {
                  value 1 ;
                }
                enum down {
                  value 2 ;
                }
              }
            }
            ncd:select intf-name ;
          }
          ncd:revise-date 2019-01-15 ;
        }
        container pfm-instance {
          description 'PFM instance information.'
                      ;
          container instance {
            description 'PFM instance information.'
                        ;
            leaf send-auto {
              description 'PFM messages send auto.
0:Disable
1:Enable'
                          ;
              type enumeration {
                enum Disable {
                  value 0 ;
                }
                enum Enable {
                  value 1 ;
                }
              }
            }
            leaf max-send-rate {
              description 'PFM messages max send rate.'
                          ;
              type uint16 {
                range 1..65535 ;
              }
            }
            leaf min-send-gap {
              description 'PFM messages min send gap.'
                          ;
              type uint16 {
                range 100..60000 ;
              }
            }
            leaf gsh-state {
              description 'GSH state.
0:Disable
1:Enable'
                          ;
              type enumeration {
                enum Disable {
                  value 0 ;
                }
                enum Enable {
                  value 1 ;
                }
              }
            }
            leaf gsh-interval {
              description 'GSH TLV interval.'
                          ;
              type uint16 {
                range 10..6000 ;
              }
            }
            leaf gsh-holdtime {
              description 'GSH TLV holdtime.'
                          ;
              type uint16 {
                range 210..65535 ;
              }
            }
            leaf local-origin {
              description 'Local origin IP address.'
                          ;
              type ncd:ipv4-address ;
            }
            leaf local-origin-state {
              description 'Local origin state.'
                          ;
              type ncd:string-with-blank {
                length 0..15 ;
              }
            }
          }
          container remote-origins {
            description 'Remote origin IP address.'
                        ;
            list remote-origin {
              description 'Remote origin IP address.'
                          ;
              key origin-ip ;
              leaf origin-ip {
                description 'Remote origin IP address.'
                            ;
                type ncd:ipv4-address ;
              }
              leaf up-time {
                description 'Remote origin up time.'
                            ;
                type string ;
              }
              ncd:select origin-ip ;
            }
          }
          ncd:revise-date 2019-07-15 ;
        }
        container pfm-gsh-summary {
          description 'PFM GSH TLV summary.'
                      ;
          container total-sum {
            description 'Total summary.'
                        ;
            leaf local-gsh-count {
              description 'Local GSH TLV total count.'
                          ;
              type uint32 ;
            }
            leaf remote-gsh-count {
              description 'Remote GSH TLV total count.'
                          ;
              type uint32 ;
            }
          }
          container remote-sums {
            description 'Remote GSH TLV summary.'
                        ;
            list remote-sum {
              description 'Remote GSH TLV summary.'
                          ;
              key origin-ip ;
              leaf origin-ip {
                description 'Remote origin IP address.'
                            ;
                type ncd:ipv4-address ;
              }
              leaf gsh-count {
                description 'GSH TLV count.'
                            ;
                type uint32 ;
              }
              ncd:select origin-ip ;
            }
          }
          ncd:revise-date 2019-07-15 ;
        }
        container pfm-gsh-caches {
          description 'PFM GSH TLV caches.'
                      ;
          list pfm-gsh-cache {
            description 'PFM GSH TLV caches.'
                        ;
            key 'origin-ip group source gsh-type'
                ;
            leaf group {
              description 'Group address.'
                          ;
              type ncd:ipv4-address ;
            }
            leaf source {
              description 'Source address.'
                          ;
              type ncd:ipv4-address ;
            }
            leaf origin-ip {
              description 'Origin IP address.'
                          ;
              type ncd:ipv4-address ;
            }
            leaf gsh-type {
              description 'GSH type.
1:Local
2:Remote'
                          ;
              type enumeration {
                enum Local {
                  value 1 ;
                }
                enum Remote {
                  value 2 ;
                }
              }
            }
            leaf expire-time {
              description 'Expire time.'
                          ;
              type string {
                length 1..31 ;
              }
            }
            leaf up-time {
              description 'Up time.'
                          ;
              type string {
                length 1..31 ;
              }
            }
            ncd:select group ;
            ncd:select 'group source'
                       ;
          }
          ncd:revise-date 2019-07-15 ;
        }
      }
      container private {
        description 'Private mode of PIM module.'
                    ;
        container intfs {
          description 'PIM interface information.'
                      ;
          list intf {
            description 'PIM interface information.'
                        ;
            key 'intf-name vrf-name'
                ;
            leaf intf-name {
              description 'Interface name'
                          ;
              type ncd:ifname {
                length 1..31 ;
              }
            }
            leaf vrf-name {
              description 'VPN Routing/Forwarding instance name'
                          ;
              type string {
                length 1..32 ;
              }
            }
            leaf nbr-count {
              description 'Neighbor count'
                          ;
              type int32 ;
            }
            leaf dr-priority {
              description 'PIM router DR priority'
                          ;
              type uint32 ;
            }
            leaf address {
              description 'Interface address'
                          ;
              type ncd:ipv4-address ;
            }
            leaf dr-addr {
              description 'DR address'
                          ;
              type ncd:ipv4-address ;
            }
            leaf hello-period {
              description 'PIM router hello interval'
                          ;
              type uint16 {
                range 1..65535 ;
              }
              units second ;
            }
            leaf state {
              description 'Interface state:1 is up;2 is down.'
                          ;
              type enumeration {
                enum up {
                  value 1 ;
                }
                enum down {
                  value 2 ;
                }
              }
            }
            leaf mode {
              description 'The mode used by the interface:'+"\n"
                        + '1 - PIM-SM protocol;'+"\n"
                        + '2 - PIM-DM protocol;'+"\n"
                        + '3 - PIM-SM and PIM-DM protocol.'
                          ;
              type enumeration {
                enum S {
                  value 1 ;
                }
                enum D {
                  value 2 ;
                }
                enum SD {
                  value 3 ;
                }
              }
            }
            leaf pim-silent {
              description 'Enable or disable PIM silent:'+"\n"
                        + '0 - Disable;'+"\n"
                        + '1 - Enable.'
                          ;
              type enumeration {
                enum Disable {
                  value 0 ;
                }
                enum Enable {
                  value 1 ;
                }
              }
            }
            ncd:select vrf-name ;
            ncd:select intf-name ;
            ncd:select 'intf-name vrf-name'
                       ;
          }
        }
        container bfds {
          description 'PIM BFD information.'
                      ;
          list bfd {
            description 'PIM BFD information.'
                        ;
            key 'intf-name local-addr peer-addr vrf-name'
                ;
            leaf intf-name {
              description 'Interface name'
                          ;
              type ncd:ifname {
                length 1..31 ;
              }
            }
            leaf local-addr {
              description 'Local address'
                          ;
              type ncd:ipv4-address ;
            }
            leaf peer-addr {
              description 'Peer address'
                          ;
              type ncd:ipv4-address ;
            }
            leaf vrf-name {
              description 'VPN Routing/Forwarding instance name'
                          ;
              type string {
                length 1..32 ;
              }
            }
            leaf local-state {
              description 'Local state, including "DR","BDR".'
                          ;
              type ncd:string-all {
                length 0..7 ;
              }
            }
            leaf peer-state {
              description 'Peer state, including "DR","BDR".'
                          ;
              type ncd:string-all {
                length 0..7 ;
              }
            }
            leaf bfd-state {
              description 'BFD session state:'+"\n"
                        + '0 - INIT;'+"\n"
                        + '1 - CREATE;'+"\n"
                        + '2 - CONNECT;'+"\n"
                        + '3 - UP;'+"\n"
                        + '4 - DOWN;'+"\n"
                        + '5 - NOT SURPPORT;'+"\n"
                        + '6 - ADMIN DOWN;'+"\n"
                        + '7 - BFD_ERROR.'
                          ;
              type enumeration {
                enum INIT {
                  value 0 ;
                }
                enum CREATE {
                  value 1 ;
                }
                enum CONNECT {
                  value 2 ;
                }
                enum UP {
                  value 3 ;
                }
                enum DOWN {
                  value 4 ;
                }
                enum NOT-SUPPORT {
                  value 5 ;
                }
                enum ADMIN-DOWN {
                  value 6 ;
                }
                enum BFD-ERROR {
                  value 7 ;
                }
              }
            }
            ncd:select intf-name ;
            ncd:select vrf-name ;
            ncd:select 'intf-name vrf-name'
                       ;
          }
        }
        container bsrs {
          description 'PIM BSR information.'
                      ;
          list bsr {
            description 'PIM BSR information.'
                        ;
            key vrf-name ;
            leaf vrf-name {
              description 'VPN Routing/Forwarding instance name'
                          ;
              type string {
                length 1..32 ;
              }
            }
            container ebsr {
              description 'E-BSR information'
                          ;
              leaf address {
                description 'E-BSR address'
                            ;
                type ncd:ipv4-address ;
              }
              leaf priority {
                description 'E-BSR priority'
                            ;
                type uint8 {
                  range 0..255 ;
                }
              }
              leaf hash-mask {
                description 'E-BSR hash mask length'
                            ;
                type uint8 {
                  range 0..32 ;
                }
              }
              leaf uptime {
                description 'E-BSR uptime'
                            ;
                type ncd:string-all {
                  length 0..15 ;
                }
              }
              leaf expire-time {
                description 'E-BSR expire time'
                            ;
                type ncd:string-all {
                  length 0..15 ;
                }
              }
            }
            container cbsr {
              description 'C-BSR information.'
                          ;
              leaf address {
                description 'C-BSR address'
                            ;
                type ncd:ipv4-address ;
              }
              leaf intf-name {
                description 'C-BSR interface name'
                            ;
                type ncd:ifname {
                  length 0..31 ;
                }
              }
              leaf priority {
                description 'C-BSR priority'
                            ;
                type uint8 {
                  range 0..255 ;
                }
              }
              leaf hash-mask {
                description 'C-BSR hash mask length'
                            ;
                type uint8 {
                  range 0..32 ;
                }
              }
            }
            container crps {
              description 'C-RP information'
                          ;
              list crp {
                description 'C-RP information'
                            ;
                key intf-name ;
                leaf intf-name {
                  description 'C-RP interface name'
                              ;
                  type ncd:ifname {
                    length 0..31 ;
                  }
                }
                leaf address {
                  description 'C-RP address'
                              ;
                  type ncd:ipv4-address ;
                }
                leaf priority {
                  description 'C-RP priority'
                              ;
                  type uint8 {
                    range 0..255 ;
                  }
                }
                leaf group-list {
                  description 'C-RP group list'
                              ;
                  type ncd:string-all {
                    length 0..169 ;
                  }
                }
                leaf intf-state {
                  description 'C-RP interface state.When the interface is down '
                            + 'or does not have address,the state is invalid.'
                              ;
                  type ncd:string-all {
                    length 0..7 ;
                  }
                }
              }
            }
            ncd:select vrf-name ;
          }
        }
        container neighbors {
          description 'PIM neighbor information.'
                      ;
          list nbr {
            description 'PIM neighbor information.'
                        ;
            key 'vrf-name intf-name nbr-addr'
                ;
            leaf vrf-name {
              description 'VPN Routing/Forwarding instance name.'
                          ;
              type string {
                length 1..32 ;
              }
            }
            leaf intf-name {
              description 'Interface name.'
                          ;
              type ncd:ifname {
                length 1..31 ;
              }
            }
            leaf nbr-addr {
              description 'IP address of neighbor.'
                          ;
              type ncd:ipv4-address ;
            }
            leaf uptime {
              description 'Uptime of neighbor.'
                          ;
              type string {
                length 1..15 ;
              }
            }
            leaf expire-time {
              description 'Expire time of neighbor.'
                          ;
              type string {
                length 1..15 ;
              }
            }
            leaf dr-priority {
              description 'DR priority of neighbor.'
                          ;
              type ncd:string-all {
                length 0..11 ;
              }
            }
            leaf join-attr {
              description 'Join attribute of neighbor: 
1 - P; 
2 - N/A.'
                          ;
              type enumeration {
                enum P {
                  value 1 ;
                }
                enum N/A {
                  value 2 ;
                }
              }
            }
            ncd:select vrf-name ;
            ncd:select intf-name ;
            ncd:select 'vrf-name intf-name'
                       ;
          }
        }
        container rp-hashs {
          description 'PIM RP-hash information.'
                      ;
          list rp-hash {
            description 'PIM RP-hash information.'
                        ;
            key 'group-addr vrf-name'
                ;
            leaf vrf-name {
              description 'VPN Routing/Forwarding instance name.'
                          ;
              type string {
                length 1..32 ;
              }
            }
            leaf group-addr {
              description 'Group address.'
                          ;
              type ncd:ipv4-address ;
            }
            leaf rp-addr {
              description 'RP address.'
                          ;
              type ncd:ipv4-address ;
            }
            leaf srp-override {
              description 'Static RP is overriding in group-set.'
                          ;
              type boolean ;
            }
            ncd:select 'vrf-name group-addr'
                       ;
          }
        }
        container rp-mappings {
          description 'PIM RP-mapping information.'
                      ;
          list rp-mapping {
            description 'PIM RP-mapping information.'
                        ;
            key 'vrf-name grp-addr gmask-addr rpset-type'
                ;
            leaf vrf-name {
              description 'VPN Routing/Forwarding instance name.'
                          ;
              type string {
                length 1..32 ;
              }
            }
            leaf grp-addr {
              description 'Group address.'
                          ;
              type ncd:ipv4-address ;
            }
            leaf gmask-addr {
              description 'Group mask address.'
                          ;
              type ncd:ipv4-mask ;
            }
            leaf rpset-type {
              description 'The type of RP set node:'+"\n"
                        + '1 - Noused;'+"\n"
                        + '2 - Static;'+"\n"
                        + '3 - BSR.'
                          ;
              type enumeration {
                enum Noused {
                  value 1 ;
                }
                enum Static {
                  value 2 ;
                }
                enum BSR {
                  value 3 ;
                }
              }
            }
            leaf protocol {
              description 'The protocol of RP set node, including "NOUSED", "SM'
                        + '".'
                          ;
              type ncd:string-all {
                length 0..7 ;
              }
            }
            leaf srp-override {
              description 'Static RP is overriding in group-set.'
                          ;
              type boolean ;
            }
            container rp-infos {
              description 'RP information.'
                          ;
              list rp-info {
                description 'RP information.'
                            ;
                key rp-addr ;
                leaf rp-addr {
                  description 'RP address.'
                              ;
                  type ncd:ipv4-address ;
                }
                leaf bidir {
                  description 'The RP is enabled bidir PIM.'
                              ;
                  type empty ;
                }
                leaf rp-priority {
                  description 'RP priority.'
                              ;
                  type uint32 {
                    range 0..255 ;
                  }
                }
                leaf bsr-addr {
                  description 'BSR address.'
                              ;
                  type ncd:ipv4-address ;
                }
                leaf uptime {
                  description 'Uptime of RP.'
                              ;
                  type ncd:string-all {
                    length 0..15 ;
                  }
                }
                leaf expire-time {
                  description 'Expire time of RP.'
                              ;
                  type ncd:string-all {
                    length 0..15 ;
                  }
                }
                ncd:select rp-addr ;
              }
            }
            ncd:select vrf-name ;
            ncd:select grp-addr ;
            ncd:select 'vrf-name grp-addr'
                       ;
          }
        }
        container nhps {
          description 'PIM nexthop information.'
                      ;
          list nhp {
            description 'PIM nexthop information.'
                        ;
            key 'vrf-name dest-addr'
                ;
            leaf vrf-name {
              description 'VPN Routing/Forwarding instance name'
                          ;
              type string {
                length 1..32 ;
              }
            }
            leaf dest-addr {
              description 'Destination address'
                          ;
              type ncd:ipv4-address ;
            }
            leaf type {
              description 'Nexthop state: R- Nexthop to RP,S- Nexthop to Source'
                        + ', O- Related with Unicast,U- No Unicast Route, L- Lo'
                        + 'cal Route,C- Connect to Destination address.'
                          ;
              type ncd:string-all {
                length 0..15 ;
              }
            }
            leaf expire-time {
              description 'Nexthop expire time'
                          ;
              type ncd:string-all {
                length 0..15 ;
              }
            }
            leaf metric {
              description 'Nexthop metric'
                          ;
              type uint32 ;
            }
            leaf preference {
              description 'Nexthop preference'
                          ;
              type uint32 ;
            }
            leaf fallback-vrf {
              description 'The instance name of fallback nexthop.If the instanc'
                        + 'e of nexthop is public, the value of the node is IP '
                        + 'global, else is VRF name.'
                          ;
              type ncd:string-all {
                length 0..32 ;
              }
              ncd:revise-date 2015-12-15 ;
            }
            container ecmps {
              description 'ECMP information'
                          ;
              list ecmp {
                description 'ECMP information'
                            ;
                key 'nhp-addr port-name'
                    ;
                leaf nhp-addr {
                  description 'Nexthop address'
                              ;
                  type ncd:ipv4-address ;
                }
                leaf port-name {
                  description 'Nexthop port name'
                              ;
                  type ncd:ifname {
                    length 0..31 ;
                  }
                }
                leaf nbr-addr {
                  description 'Neighbor address'
                              ;
                  type ncd:ipv4-address ;
                }
                leaf local-flag {
                  description 'Nexthop is local.'
                              ;
                  type ncd:string-all {
                    length 0..11 ;
                  }
                }
                ncd:select 'nhp-addr port-name'
                           ;
              }
            }
            ncd:select vrf-name ;
            ncd:select dest-addr ;
            ncd:select 'vrf-name dest-addr'
                       ;
          }
        }
        container groups {
          description 'PIM group information.'
                      ;
          list group {
            description 'PIM group information.'
                        ;
            key 'vrf-name group-name'
                ;
            leaf vrf-name {
              description 'VPN Routing/Forwarding instance name'
                          ;
              type string {
                length 1..32 ;
              }
            }
            leaf group-name {
              description 'Group name.'
                          ;
              type string {
                length 1..31 ;
              }
            }
            leaf group-id {
              description 'Group ID.'
                          ;
              type uint32 ;
            }
            leaf bind-num {
              description 'Total bind interfaces.'
                          ;
              type uint32 ;
            }
            container binds {
              description 'PIM bind interface information.'
                          ;
              list bind {
                description 'PIM bind interface information.'
                            ;
                key intf-name ;
                leaf intf-name {
                  description 'Bind interface name.'
                              ;
                  type ncd:ifname {
                    length 0..31 ;
                  }
                }
                leaf bind-state {
                  description 'Bind interface state:
1 - Active;
2 - Passive.'
                              ;
                  type enumeration {
                    enum Active {
                      value 1 ;
                    }
                    enum Passive {
                      value 2 ;
                    }
                  }
                }
                leaf forward-state {
                  description 'Interface forward state:
1 - TRUE;
2 - FALSE.'
                              ;
                  type boolean ;
                }
              }
            }
            ncd:select vrf-name ;
            ncd:select group-name ;
            ncd:select 'vrf-name group-name'
                       ;
          }
        }
        container traffics {
          description 'PIM traffic information.'
                      ;
          list traffic {
            description 'PIM traffic information.'
                        ;
            key vrf-name ;
            leaf vrf-name {
              description 'VPN Routing/Forwarding instance name.'
                          ;
              type string {
                length 1..32 ;
              }
            }
            list intf-traffic {
              description 'PIM interface traffic information.'
                          ;
              key intf-name ;
              leaf intf-name {
                description 'Interface name.'
                            ;
                type ncd:ifname {
                  length 0..31 ;
                }
              }
              leaf hello-send {
                description 'The number of hello messages sent by a PIM interfa'
                          + 'ce.'
                            ;
                type uint32 ;
              }
              leaf hello-rcv {
                description 'The number of hello messages received by a PIM int'
                          + 'erface.'
                            ;
                type uint32 ;
              }
              leaf reg-send {
                description 'The number of register messages sent by a PIM inte'
                          + 'rface.'
                            ;
                type uint32 ;
              }
              leaf reg-rcv {
                description 'The number of register messages received by a PIM '
                          + 'interface.'
                            ;
                type uint32 ;
              }
              leaf reg-stop-send {
                description 'The number of register-stop messages sent by a PIM'
                          + ' interface.'
                            ;
                type uint32 ;
              }
              leaf reg-stop-rcv {
                description 'The number of register-stop messages received by a'
                          + ' PIM interface.'
                            ;
                type uint32 ;
              }
              leaf jp-send {
                description 'The number of join/prune messages sent by a PIM in'
                          + 'terface.'
                            ;
                type uint32 ;
              }
              leaf jp-rcv {
                description 'The number of join/prune messages received by a PI'
                          + 'M interface.'
                            ;
                type uint32 ;
              }
              leaf bsm-send {
                description 'The number of bootstrap messages sent by a PIM int'
                          + 'erface.'
                            ;
                type uint32 ;
              }
              leaf bsm-rcv {
                description 'The number of bootstrap messages received by a PIM'
                          + ' interface.'
                            ;
                type uint32 ;
              }
              leaf assert-send {
                description 'The number of assert messages sent by a PIM interf'
                          + 'ace.'
                            ;
                type uint32 ;
              }
              leaf assert-rcv {
                description 'The number of assert messages received by a PIM in'
                          + 'terface.'
                            ;
                type uint32 ;
              }
              leaf graft-send {
                description 'The number of graft messages sent by a PIM interfa'
                          + 'ce.'
                            ;
                type uint32 ;
              }
              leaf graft-rcv {
                description 'The number of graft messages received by a PIM int'
                          + 'erface.'
                            ;
                type uint32 ;
              }
              leaf graft-ack-send {
                description 'The number of graft ack messages sent by a PIM int'
                          + 'erface.'
                            ;
                type uint32 ;
              }
              leaf graft-ack-rcv {
                description 'The number of graft ack messages received by a PIM'
                          + ' interface.'
                            ;
                type uint32 ;
              }
              leaf crp-adv-send {
                description 'The number of candidate-RP-advertisement messages '
                          + 'sent by a PIM interface.'
                            ;
                type uint32 ;
              }
              leaf crp-adv-rcv {
                description 'The number of candidate-RP-advertisement messages '
                          + 'received by a PIM interface.'
                            ;
                type uint32 ;
              }
              leaf sr-send {
                description 'The number of state refresh messages sent by a PIM'
                          + ' interface.'
                            ;
                type uint32 ;
              }
              leaf sr-rcv {
                description 'The number of state refresh messages received by a'
                          + ' PIM interface.'
                            ;
                type uint32 ;
              }
              leaf df-elct-send {
                description 'The number of DF election messages sent by a PIM i'
                          + 'nterface.'
                            ;
                type uint32 ;
              }
              leaf df-elct-rcv {
                description 'The number of DF election messages received by a P'
                          + 'IM interface.'
                            ;
                type uint32 ;
              }
              ncd:select intf-name ;
            }
            container total {
              description 'Total traffic in current PIM instance.'
                          ;
              leaf total-pkt-rcv {
                description 'The number of protocol messages received by a PIM '
                          + 'instance.'
                            ;
                type uint32 ;
              }
              leaf total-pkt-send {
                description 'The number of protocol messages sent by a PIM inst'
                          + 'ance.'
                            ;
                type uint32 ;
              }
              leaf pkt-rcv-error {
                description 'The number of error protocol messages received by '
                          + 'a PIM instance.'
                            ;
                type uint32 ;
              }
              leaf hello-send {
                description 'The number of hello messages sent by a PIM instanc'
                          + 'e.'
                            ;
                type uint32 ;
              }
              leaf hello-rcv {
                description 'The number of hello messages received by a PIM ins'
                          + 'tance.'
                            ;
                type uint32 ;
              }
              leaf reg-send {
                description 'The number of register messages sent by a PIM inst'
                          + 'ance.'
                            ;
                type uint32 ;
              }
              leaf reg-rcv {
                description 'The number of register messages received by a PIM '
                          + 'instance.'
                            ;
                type uint32 ;
              }
              leaf reg-stop-send {
                description 'The number of register-stop messages sent by a PIM'
                          + ' instance.'
                            ;
                type uint32 ;
              }
              leaf reg-stop-rcv {
                description 'The number of register-stop messages received by a'
                          + ' PIM instance.'
                            ;
                type uint32 ;
              }
              leaf jp-send {
                description 'The number of join/prune messages sent by a PIM in'
                          + 'stance.'
                            ;
                type uint32 ;
              }
              leaf jp-rcv {
                description 'The number of join/prune messages received by a PI'
                          + 'M instance.'
                            ;
                type uint32 ;
              }
              leaf bsm-send {
                description 'The number of bootstrap messages sent by a PIM ins'
                          + 'tance.'
                            ;
                type uint32 ;
              }
              leaf bsm-rcv {
                description 'The number of bootstrap messages received by a PIM'
                          + ' instance.'
                            ;
                type uint32 ;
              }
              leaf assert-send {
                description 'The number of assert messages sent by a PIM instan'
                          + 'ce.'
                            ;
                type uint32 ;
              }
              leaf assert-rcv {
                description 'The number of assert messages received by a PIM in'
                          + 'stance.'
                            ;
                type uint32 ;
              }
              leaf graft-send {
                description 'The number of graft messages sent by a PIM instanc'
                          + 'e.'
                            ;
                type uint32 ;
              }
              leaf graft-rcv {
                description 'The number of graft messages received by a PIM ins'
                          + 'tance.'
                            ;
                type uint32 ;
              }
              leaf graft-ack-send {
                description 'The number of graft ack messages sent by a PIM ins'
                          + 'tance.'
                            ;
                type uint32 ;
              }
              leaf graft-ack-rcv {
                description 'The number of graft ack messages received by a PIM'
                          + ' instance.'
                            ;
                type uint32 ;
              }
              leaf crp-adv-send {
                description 'The number of candidate-RP-advertisement messages '
                          + 'sent by a PIM instance.'
                            ;
                type uint32 ;
              }
              leaf crp-adv-rcv {
                description 'The number of candidate-RP-advertisement messages '
                          + 'received by a PIM instance.'
                            ;
                type uint32 ;
              }
              leaf sr-send {
                description 'The number of state refresh messages sent by a PIM'
                          + ' instance.'
                            ;
                type uint32 ;
              }
              leaf sr-rcv {
                description 'The number of state refresh messages received by a'
                          + ' PIM instance.'
                            ;
                type uint32 ;
              }
              leaf df-elct-send {
                description 'The number of DF election messages sent by a PIM i'
                          + 'nstance.'
                            ;
                type uint32 ;
              }
              leaf df-elct-rcv {
                description 'The number of DF election messages received by a P'
                          + 'IM instance.'
                            ;
                type uint32 ;
              }
            }
            ncd:select vrf-name ;
          }
        }
        container dfs {
          description 'PIM designated forwarder information.'
                      ;
          list df {
            description 'PIM designated forwarder information.'
                        ;
            key 'vrf-name rp-addr'
                ;
            leaf vrf-name {
              description 'VPN Routing/Forwarding instance name.'
                          ;
              type string {
                length 1..32 ;
              }
            }
            leaf rp-addr {
              description 'Rendezvous Point Address.'
                          ;
              type ncd:ipv4-address ;
            }
            container rpa-states {
              description 'The DF election information.'
                          ;
              list rpa-state {
                description 'The DF election information.'
                            ;
                key intf-name ;
                leaf intf-name {
                  description 'DF interface name.'
                              ;
                  type ncd:ifname {
                    length 0..31 ;
                  }
                }
                leaf state {
                  description 'DF election state,including "OFFER","LOSE","WIN"'
                            + ',"BACKOFF","NONE(RPL)".'
                              ;
                  type ncd:string-all {
                    length 0..15 ;
                  }
                }
                leaf timeout {
                  description 'DF election-Timer expire time.'
                              ;
                  type ncd:string-all {
                    length 0..15 ;
                  }
                }
                leaf message-count {
                  description 'The number of times an Offer or Winner message h'
                            + 'as been transmitted.'
                              ;
                  type uint32 ;
                }
                leaf local-addr {
                  description 'Local DF address.'
                              ;
                  type ncd:ipv4-address ;
                }
                leaf local-metric {
                  description 'Local DF metric.'
                              ;
                  type uint32 ;
                }
                leaf local-pref {
                  description 'Local DF preference.'
                              ;
                  type uint32 ;
                }
                leaf acting-addr {
                  description 'Acting DF address.'
                              ;
                  type ncd:ipv4-address ;
                }
                leaf acting-metric {
                  description 'Acting DF metric.'
                              ;
                  type uint32 ;
                }
                leaf acting-pref {
                  description 'Acting DF preference.'
                              ;
                  type uint32 ;
                }
                leaf last-addr {
                  description 'The address of the router that made the last Off'
                            + 'er.'
                              ;
                  type ncd:ipv4-address ;
                }
                leaf last-metric {
                  description 'The unicast routing table metric used by the rou'
                            + 'ter that made the last Offer to reach the RPA.'
                              ;
                  type uint32 ;
                }
                leaf last-pref {
                  description 'Preference value assigned to the unicast routing'
                            + ' protocol used by the router that made the last '
                            + 'Offer to obtain the route to the RPA.'
                              ;
                  type uint32 ;
                }
              }
            }
            ncd:select vrf-name ;
            ncd:select rp-addr ;
            ncd:select 'vrf-name rp-addr'
                       ;
          }
        }
        container summarys {
          description 'The statistics information of the IP multicast PIM route'
                    + ' table.'
                      ;
          list summary {
            description 'The statistics information of the IP multicast PIM rou'
                      + 'te table.'
                        ;
            key vrf-name ;
            leaf vrf-name {
              description 'VPN Routing/Forwarding instance name.'
                          ;
              type string {
                length 1..32 ;
              }
            }
            container mr-num {
              description 'The number of PIM route.'
                          ;
              leaf xg {
                description 'The number of (*, G) route.'
                            ;
                type uint32 ;
              }
              leaf sg {
                description 'The number of (S, G) route.'
                            ;
                type uint32 ;
              }
              leaf sgrpt {
                description 'The number of (S, G, rpt) route.'
                            ;
                type uint32 ;
              }
              leaf reg {
                description 'The number of register route.'
                            ;
                type uint32 ;
              }
            }
            list mr-state {
              description 'The summary state of PIM mroute.'
                          ;
              key 'group-addr source-addr'
                  ;
              leaf group-addr {
                description 'Group address.'
                            ;
                type ncd:ipv4-address ;
              }
              leaf source-addr {
                description 'Source address.'
                            ;
                type ncd:ipv4-address ;
              }
              leaf rp-addr {
                description 'RP address.'
                            ;
                type ncd:ipv4-address ;
              }
              leaf xg-us-state {
                description 'Upstream (*,G) join/prune state,including "NOT JOI'
                          + 'NED","JOINED".'
                            ;
                type ncd:string-all {
                  length 0..11 ;
                }
              }
              leaf sg-us-state {
                description 'Upstream (S,G) join/prune state,including "NOT JOI'
                          + 'NED","JOINED".'
                            ;
                type ncd:string-all {
                  length 0..11 ;
                }
              }
              leaf sgrpt-us-state {
                description 'Upstream (S,G,rpt) join/prune state,including "RPT'
                          + ' NOT JOINED","PRUNED","NOT PRUNED".'
                            ;
                type ncd:string-all {
                  length 0..15 ;
                }
              }
              ncd:select group-addr ;
              ncd:select 'group-addr source-addr'
                         ;
            }
            ncd:select vrf-name ;
          }
        }
        container mroutes {
          description 'PIM mroute information.'
                      ;
          list mroute {
            description 'PIM mroute information.'
                        ;
            key 'vrf-name source group'
                ;
            leaf vrf-name {
              description 'VPN Routing/Forwarding instance name.'
                          ;
              type ncd:string-all {
                length 1..32 ;
              }
            }
            leaf source {
              description 'Source address information'
                          ;
              type ncd:ipv4-address ;
            }
            leaf group {
              description 'Group address information'
                          ;
              type ncd:ipv4-address ;
            }
            leaf rp-address {
              description 'RP address information'
                          ;
              type ncd:ipv4-address ;
              mandatory true ;
            }
            leaf rpf-nbr {
              description 'RPF neighbor address.'
                          ;
              type ncd:ipv4-address ;
            }
            leaf reg-state {
              description 'Register state, "NO INFO","JOIN","PRUNE","JOIN PENDI'
                        + 'NG".'
                          ;
              type ncd:string-all {
                length 0..15 ;
              }
            }
            leaf reg-tunnel {
              description 'Register tunnel information'
                          ;
              type ncd:ifname {
                length 0..31 ;
              }
            }
            leaf uptime {
              description 'Mroute uptime'
                          ;
              type ncd:string-all {
                length 0..15 ;
              }
            }
            leaf kat {
              description 'Keepalive timer'
                          ;
              type ncd:string-all {
                length 0..15 ;
              }
            }
            leaf jp-expire-time {
              description 'Upstream join/prune expire timer'
                          ;
              type ncd:string-all {
                length 0..15 ;
              }
            }
            leaf msdp-state {
              description 'MSDP state information, "SA CREATE", "TO BE ADV".'
                          ;
              type ncd:string-all {
                length 0..15 ;
              }
            }
            leaf iif-name {
              description 'Mroute incoming interface information'
                          ;
              type ncd:ifname {
                length 0..31 ;
              }
            }
            leaf upstream-state {
              description 'Upstream state information, "NOT JOINED","JOINED".'
                          ;
              type ncd:string-all {
                length 0..15 ;
              }
            }
            leaf state-statistics {
              description 'Mroute state statistics information:'+"\n"
                        + 'Ind-Pim Include macro,'+"\n"
                        + 'Exd-Pim Exclude macro, '+"\n"
                        + 'Jns-Pim Joins macro,'+"\n"
                        + 'LAst-Pim Lost_assert macro, '+"\n"
                        + 'Imo-Pim Immediate_olist macro,'+"\n"
                        + 'Ino-Pim Inherited_olist macro, '+"\n"
                        + 'Lcd-Pim Local_receiver_include macro, '+"\n"
                        + 'Fbk-Fallback_extranet_receiver_number.'
                          ;
              type ncd:string-all {
                length 0..71 ;
              }
            }
            leaf dm-upstream-state {
              description 'Upstream PIM-DM state information, "FORWARD", "PRUNE'
                        + 'D","ACK_PENDING".'
                          ;
              type ncd:string-all {
                length 0..15 ;
              }
            }
            leaf dm-rpf-nbr {
              description 'PIM-DM RPF neighbor address'
                          ;
              type ncd:ipv4-address ;
            }
            leaf flags {
              description 'Mroute flags, "A", "T", "U", "J".'
                          ;
              type ncd:string-all {
                length 0..7 ;
              }
            }
            leaf prune-limit-timer {
              description 'PIM-DM prune limit timer'
                          ;
              type ncd:string-all {
                length 0..15 ;
              }
            }
            leaf vector-address {
              description 'Vector address information'
                          ;
              type ncd:ipv4-address ;
            }
            leaf mofrr-iif {
              description 'MoFRR incoming interface information'
                          ;
              type ncd:ifname {
                length 0..31 ;
              }
            }
            leaf mofrr-rpf-nbr {
              description 'MoFRR RPF neighbor address'
                          ;
              type ncd:ipv4-address ;
            }
            leaf sg-rpt-uptime {
              description 'SG-RPT uptime'
                          ;
              type ncd:string-all {
                length 0..15 ;
              }
            }
            leaf sg-rpt-ov-time {
              description 'SG-RPT override timer'
                          ;
              type ncd:string-all {
                length 0..15 ;
              }
            }
            leaf sg-rpt-rpf-nbr {
              description 'SG-RPT RPF neighbor address'
                          ;
              type ncd:ipv4-address ;
            }
            leaf sg-rpt-iif-name {
              description 'SG-RPT incoming interface information'
                          ;
              type ncd:ifname {
                length 0..31 ;
              }
            }
            leaf sg-rpt-upstream-state {
              description 'SG-RPT upstream state information, "RPT NOT JOINED",'
                        + '"PRUNED","NOT PRUNED".'
                          ;
              type ncd:string-all {
                length 0..15 ;
              }
            }
            leaf sg-rpt-state-statistics {
              description 'SG-RPT state statistics information:'+"\n"
                        + 'Ind-Pim Include macro,'+"\n"
                        + 'Exd-Pim Exclude macro, '+"\n"
                        + 'Jns-Pim Joins macro,'+"\n"
                        + 'LAst-Pim Lost_assert macro, '+"\n"
                        + 'Imo-Pim Immediate_olist macro,'+"\n"
                        + 'Ino-Pim Inherited_olist macro, '+"\n"
                        + 'Lcd-Pim Local_receiver_include macro.'
                          ;
              type ncd:string-all {
                length 0..39 ;
              }
            }
            leaf sg-rpt-flags {
              description 'SG-RPT mroute flags information, "A".'
                          ;
              type ncd:string-all {
                length 0..7 ;
              }
            }
            leaf fallback-vrf {
              description 'The upstream instance name of mroute.If the instance'
                        + ' of upstream is public, the value of the node is IP '
                        + 'global, else is VRF name.'
                          ;
              type ncd:string-all {
                length 0..32 ;
              }
              ncd:revise-date 2015-12-15 ;
            }
            container oif-lists {
              description 'Outcoming interface list'
                          ;
              list oif-list {
                description 'Outcoming interface list'
                            ;
                key intf-name ;
                leaf intf-name {
                  description 'Outcoming interface name'
                              ;
                  type ncd:ifname {
                    length 0..31 ;
                  }
                }
                leaf oif-macro {
                  description 'Outcoming interface macro information:'+"\n"
                            + 'LocalIn-Local include join,'+"\n"
                            + 'AstW-Assert winner state,'+"\n"
                            + 'AstL-Assert loser state,'+"\n"
                            + 'LostAst-LostAssert macro,'+"\n"
                            + 'ImoXG-ImmediateOlist XG macro,'+"\n"
                            + 'Bidir-RPF-Bidir RPF RP macro,'+"\n"
                            + 'JoinsSG-Pim JoinsSG Macro,'+"\n"
                            + 'PrunesSGRpt-PrunesSGRpt macro,'+"\n"
                            + 'LocalInSG-Local include join SG,'+"\n"
                            + 'LocalExSG-Local exclude join SG,'+"\n"
                            + 'AstWSG-Assert winner SG state,'+"\n"
                            + 'AstLSG-Assert loser SG state,'+"\n"
                            + 'LostAstSG-LostAssert SG macro,'+"\n"
                            + 'LostAstSGRpt-LostAssert SG-RPT macro,'+"\n"
                            + 'InheritedFromXG-ImmediateOlistXG macro,'+"\n"
                            + 'InoSGRpt-InheritedOlistSGRpt macro,'+"\n"
                            + 'InoSG-InheritedOlistSG macro,'+"\n"
                            + 'DenseAstWSG-PIM-DM assert winner state,'+"\n"
                            + 'DenseAstLSG-PIM-DM lost assert SG state,'+"\n"
                            + 'DensePruneSG-PIM-DM pruned state,'+"\n"
                            + 'DenseLostAst-PIM-DM lost assert SG macro,'+"\n"
                            + 'DenseOlist-PIM-DM OlistSG macro.'
                              ;
                  type ncd:string-all {
                    length 0..255 ;
                  }
                }
                ncd:select intf-name ;
              }
            }
            ncd:select 'vrf-name source group'
                       ;
            ncd:select 'vrf-name group'
                       ;
            ncd:select vrf-name ;
          }
        }
        container statistics {
          // if-feature pim-statistics ;
          description 'PIM packet statistics information.'
                      ;
          list statistic {
            description 'PIM packet statistics information.'
                        ;
            key 'vrf-name source group'
                ;
            leaf vrf-name {
              description 'VPN Routing/Forwarding instance name.'
                          ;
              type string {
                length 1..32 ;
              }
            }
            leaf source {
              description 'Source address.'
                          ;
              type ncd:ipv4-address ;
            }
            leaf group {
              description 'Group address.'
                          ;
              type ncd:ipv4-address ;
            }
            leaf in-bytes {
              description 'Byte count of received multicast packet.'
                          ;
              type string {
                length 0..23 ;
              }
            }
            leaf in-packets {
              description 'Received multicast packet count.'
                          ;
              type string {
                length 0..23 ;
              }
            }
            leaf in-byte-rate {
              description '120s input rate(Bps).'
                          ;
              type string {
                length 0..23 ;
              }
            }
            leaf in-packet-rate {
              description '120s input rate(pps).'
                          ;
              type string {
                length 0..23 ;
              }
            }
            leaf counter-state {
              description 'Hardware counter state.If the hardware counter is no'
                        + 't working, the value of the node is not working.'
                          ;
              type ncd:string-all {
                length 0..23 ;
              }
            }
            leaf join-sent {
              description 'The count of (*,G) or (S,G) join message sent.'
                          ;
              type uint32 ;
            }
            leaf prune-sent {
              description 'The count of (*,G) or (S,G) prune message sent.'
                          ;
              type uint32 ;
            }
            leaf sgrpt-join-sent {
              description 'The count of (S,G,rpt) join message sent.'
                          ;
              type uint32 ;
            }
            leaf sgrpt-prune-sent {
              description 'The count of (S,G,rpt) prune message sent.'
                          ;
              type uint32 ;
            }
            ncd:select vrf-name ;
            ncd:select 'vrf-name group'
                       ;
            ncd:select 'vrf-name source group'
                       ;
          }
          ncd:revise-date 2016-03-18 ;
        }
        container intf-briefs {
          description 'PIM interface brief information.'
                      ;
          list intf-brief {
            description 'PIM interface brief information.'
                        ;
            key vrf-name ;
            leaf vrf-name {
              description 'VPN Routing/Forwarding instance name.'
                          ;
              type string {
                length 1..32 ;
              }
            }
            container total-num {
              description 'The total number of PIM interface.'
                          ;
              leaf intf-num {
                description 'The number of PIM interface.'
                            ;
                type uint32 ;
              }
            }
            list intf-info {
              description 'PIM interface brief information.'
                          ;
              key intf-name ;
              leaf intf-name {
                description 'Interface name'
                            ;
                type ncd:ifname {
                  length 1..31 ;
                }
              }
              leaf nbr-count {
                description 'Neighbor count'
                            ;
                type int32 ;
              }
              leaf dr-priority {
                description 'PIM router DR priority'
                            ;
                type uint32 ;
              }
              leaf dr-addr {
                description 'DR address'
                            ;
                type ncd:ipv4-address ;
              }
              leaf hello-period {
                description 'PIM router hello interval'
                            ;
                type uint16 {
                  range 1..65535 ;
                }
                units second ;
              }
              leaf state {
                description 'Interface state:1 is up;2 is down.'
                            ;
                type enumeration {
                  enum up {
                    value 1 ;
                  }
                  enum down {
                    value 2 ;
                  }
                }
              }
              ncd:select intf-name ;
            }
            ncd:select vrf-name ;
          }
          ncd:revise-date 2019-01-15 ;
        }
        container pfm-instances {
          description 'PFM instance information.'
                      ;
          list pfm-instance {
            description 'PFM instance information.'
                        ;
            key vrf-name ;
            leaf vrf-name {
              description 'VPN Routing/Forwarding instance name.'
                          ;
              type string {
                length 1..32 ;
              }
            }
            leaf send-auto {
              description 'PFM messages send auto.
0:Disable
1:Enable'
                          ;
              type enumeration {
                enum Disable {
                  value 0 ;
                }
                enum Enable {
                  value 1 ;
                }
              }
            }
            leaf max-send-rate {
              description 'PFM messages max send rate.'
                          ;
              type uint16 {
                range 1..65535 ;
              }
            }
            leaf min-send-gap {
              description 'PFM messages min send gap.'
                          ;
              type uint16 {
                range 100..60000 ;
              }
            }
            leaf gsh-state {
              description 'GSH state.
0:Disable
1:Enable'
                          ;
              type enumeration {
                enum Disable {
                  value 0 ;
                }
                enum Enable {
                  value 1 ;
                }
              }
            }
            leaf gsh-interval {
              description 'GSH TLV interval.'
                          ;
              type uint16 {
                range 10..6000 ;
              }
            }
            leaf gsh-holdtime {
              description 'GSH TLV holdtime.'
                          ;
              type uint16 {
                range 210..65535 ;
              }
            }
            leaf local-origin {
              description 'Local origin IP address.'
                          ;
              type ncd:ipv4-address ;
            }
            leaf local-origin-state {
              description 'Local origin state.'
                          ;
              type ncd:string-with-blank {
                length 0..15 ;
              }
            }
            container remote-origins {
              description 'Remote origin IP address.'
                          ;
              list remote-origin {
                description 'Remote origin IP address.'
                            ;
                key origin-ip ;
                leaf origin-ip {
                  description 'Remote origin IP address.'
                              ;
                  type ncd:ipv4-address ;
                }
                leaf up-time {
                  description 'Remote origin up time.'
                              ;
                  type string ;
                }
                ncd:select origin-ip ;
              }
            }
            ncd:select vrf-name ;
          }
          ncd:revise-date 2019-07-15 ;
        }
        container pfm-gsh-summarys {
          description 'PFM GSH TLV summary.'
                      ;
          list pfm-gsh-summary {
            description 'PFM GSH TLV summary.'
                        ;
            key vrf-name ;
            leaf vrf-name {
              description 'VPN Routing/Forwarding instance name.'
                          ;
              type string {
                length 1..32 ;
              }
            }
            leaf local-gsh-count {
              description 'Local GSH TLV total count.'
                          ;
              type uint32 ;
            }
            leaf remote-gsh-count {
              description 'Remote GSH TLV total count.'
                          ;
              type uint32 ;
            }
            container remote-sums {
              description 'Remote GSH TLV summary.'
                          ;
              list remote-sum {
                description 'Remote GSH TLV summary.'
                            ;
                key origin-ip ;
                leaf origin-ip {
                  description 'Remote origin IP address.'
                              ;
                  type ncd:ipv4-address ;
                }
                leaf gsh-count {
                  description 'GSH TLV count.'
                              ;
                  type uint32 ;
                }
                ncd:select origin-ip ;
              }
            }
            ncd:select vrf-name ;
          }
          ncd:revise-date 2019-07-15 ;
        }
        container pfm-gsh-caches {
          description 'PFM GSH TLV caches.'
                      ;
          list pfm-gsh-cache {
            description 'PFM GSH TLV caches.'
                        ;
            key 'vrf-name group source origin-ip gsh-type'
                ;
            leaf vrf-name {
              description 'VPN Routing/Forwarding instance name.'
                          ;
              type string {
                length 1..32 ;
              }
            }
            leaf group {
              description 'Group address.'
                          ;
              type ncd:ipv4-address ;
            }
            leaf source {
              description 'Source address.'
                          ;
              type ncd:ipv4-address ;
            }
            leaf origin-ip {
              description 'Origin IP address.'
                          ;
              type ncd:ipv4-address ;
            }
            leaf gsh-type {
              description 'GSH type.
1:Local
2:Remote'
                          ;
              type enumeration {
                enum Local {
                  value 1 ;
                }
                enum Remote {
                  value 2 ;
                }
              }
            }
            leaf expire-time {
              description 'Expire time.'
                          ;
              type string {
                length 1..31 ;
              }
            }
            leaf up-time {
              description 'Up time.'
                          ;
              type string {
                length 1..31 ;
              }
            }
            ncd:select vrf-name ;
            ncd:select 'vrf-name group'
                       ;
            ncd:select 'vrf-name group source'
                       ;
          }
          ncd:revise-date 2019-07-15 ;
        }
      }
    }
    ncd:revise-date 2015-03-31 ;
  }
  container operation {
    config false ;
    description 'PIM module operation info.'
                ;
    container pim {
      description 'PIM module operation info.'
                  ;
      container public {
        description 'Public mode of PIM module.'
                    ;
        container clear {
          description 'Clear PIM traffic statistics.'
                      ;
          container traffic {
            description 'Clear PIM traffic information.'
                        ;
            container intfs {
              description 'Clear the traffic information of the PIM interface.'
                          ;
              list intf {
                description 'Clear the traffic information of the PIM interface.'
                            ;
                key intf-name ;
                leaf intf-name {
                  description 'Interface name.'
                              ;
                  type ncd:ifname {
                    length 1..31 ;
                  }
                }
              }
            }
            container instance {
              description 'Clear all traffic information of the PIM public inst'
                        + 'ance.'
                          ;
              leaf all {
                description 'Clear all traffic information of the PIM public in'
                          + 'stance.'
                            ;
                type empty ;
              }
            }
          }
          container statistics {
            // if-feature pim-statistics ;
            description 'Clear PIM packet statistics information.'
                        ;
            list source-group {
              description 'Clear PIM packet statistics of the designed source a'
                        + 'nd group address.'
                          ;
              key 'group source'
                  ;
              leaf group {
                description 'Group address.'
                            ;
                type ncd:ipv4-address ;
              }
              leaf source {
                description 'Source address.'
                            ;
                type ncd:ipv4-address ;
              }
            }
            list group {
              description 'Clear PIM packet statistics of the designed group ad'
                        + 'dress.'
                          ;
              key group ;
              leaf group {
                description 'Group address.'
                            ;
                type ncd:ipv4-address ;
              }
            }
            container instance {
              description 'Clear PIM packet statistics of public instance.'
                          ;
              leaf all {
                description 'Clear PIM statistic information of the public inst'
                          + 'ance.'
                            ;
                type empty ;
              }
            }
            ncd:revise-date 2016-03-18 ;
          }
          container pfm-gsh-caches {
            description 'Clear PFM GSH caches information.'
                        ;
            list source-group {
              description 'Clear PFM GSH caches of the designed source and grou'
                        + 'p address.'
                          ;
              key 'group source'
                  ;
              leaf group {
                description 'Group address.'
                            ;
                type ncd:ipv4-address ;
              }
              leaf source {
                description 'Source address.'
                            ;
                type ncd:ipv4-address ;
              }
            }
            list group {
              description 'Clear PFM GSH caches of the designed group address.'
                          ;
              key group ;
              leaf group {
                description 'Group address.'
                            ;
                type ncd:ipv4-address ;
              }
            }
            container instance {
              description 'Clear PFM GSH caches of public instance.'
                          ;
              leaf all {
                description 'Clear PFM GSH caches of the public instance.'
                            ;
                type empty ;
              }
            }
            ncd:revise-date 2019-07-15 ;
          }
        }
      }
      container private {
        description 'Private mode of PIM module.'
                    ;
        container clear {
          description 'Clear PIM traffic statistics.'
                      ;
          container traffic {
            description 'Clear PIM traffic information.'
                        ;
            container intfs {
              description 'Clear the traffic information of the PIM interface.'
                          ;
              list intf {
                description 'Clear the traffic information of the PIM interface.'
                            ;
                key 'vrf-name intf-name'
                    ;
                leaf vrf-name {
                  description 'VPN Routing/Forwarding instance name.'
                              ;
                  type string {
                    length 1..32 ;
                  }
                }
                leaf intf-name {
                  description 'Interface name.'
                              ;
                  type ncd:ifname {
                    length 1..31 ;
                  }
                }
              }
            }
            container instances {
              description 'Clear all traffic information of the designed PIM pr'
                        + 'ivate instance.'
                          ;
              list instance {
                description 'Clear all traffic information of the designed PIM '
                          + 'private instance.'
                            ;
                key vrf-name ;
                leaf vrf-name {
                  description 'VPN Routing/Forwarding instance name.'
                              ;
                  type string {
                    length 1..32 ;
                  }
                }
              }
            }
          }
          container statistics {
            // if-feature pim-statistics ;
            description 'Clear PIM packet statistics information.'
                        ;
            list source-group {
              description 'Clear PIM packet statistics of the designed source a'
                        + 'nd group address.'
                          ;
              key 'group vrf-name source'
                  ;
              leaf vrf-name {
                description 'VPN Routing/Forwarding instance name.'
                            ;
                type string {
                  length 1..32 ;
                }
              }
              leaf group {
                description 'Group address.'
                            ;
                type ncd:ipv4-address ;
              }
              leaf source {
                description 'Source address.'
                            ;
                type ncd:ipv4-address ;
              }
            }
            list group {
              description 'Clear PIM packet statistics of the designed group ad'
                        + 'dress.'
                          ;
              key 'vrf-name group'
                  ;
              leaf vrf-name {
                description 'VPN Routing/Forwarding instance name.'
                            ;
                type string {
                  length 1..32 ;
                }
              }
              leaf group {
                description 'Group address.'
                            ;
                type ncd:ipv4-address ;
              }
            }
            list instance {
              description 'Clear PIM statistics information of the designed pri'
                        + 'vate instance.'
                          ;
              key vrf-name ;
              leaf vrf-name {
                description 'VPN Routing/Forwarding instance name.'
                            ;
                type string {
                  length 1..32 ;
                }
              }
            }
            ncd:revise-date 2016-03-18 ;
          }
          container pfm-gsh-caches {
            description 'Clear PFM GSH caches information.'
                        ;
            list source-group {
              description 'Clear PFM GSH caches of the designed source and grou'
                        + 'p address.'
                          ;
              key 'group vrf-name source'
                  ;
              leaf vrf-name {
                description 'VPN Routing/Forwarding instance name.'
                            ;
                type string {
                  length 1..32 ;
                }
              }
              leaf group {
                description 'Group address.'
                            ;
                type ncd:ipv4-address ;
              }
              leaf source {
                description 'Source address.'
                            ;
                type ncd:ipv4-address ;
              }
            }
            list group {
              description 'Clear PFM GSH caches of the designed group address.'
                          ;
              key 'vrf-name group'
                  ;
              leaf vrf-name {
                description 'VPN Routing/Forwarding instance name.'
                            ;
                type string {
                  length 1..32 ;
                }
              }
              leaf group {
                description 'Group address.'
                            ;
                type ncd:ipv4-address ;
              }
            }
            list instance {
              description 'Clear PFM GSH caches of the designed private instanc'
                        + 'e.'
                          ;
              key vrf-name ;
              leaf vrf-name {
                description 'VPN Routing/Forwarding instance name.'
                            ;
                type string {
                  length 1..32 ;
                }
              }
            }
            ncd:revise-date 2019-07-15 ;
          }
        }
      }
    }
    ncd:revise-date 2015-03-31 ;
  }
}
