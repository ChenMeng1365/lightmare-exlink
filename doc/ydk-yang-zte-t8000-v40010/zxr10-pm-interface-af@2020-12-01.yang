module zxr10-pm-interface-af {
  namespace 'http://www.zte.com.cn/zxr10/netconf/schema/rosng/pm-interface-af'
            ;
  prefix pm-interface-af ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2020-12-01 {
    description af-config ;
  }
  container configuration {
    container pm-if {
      container eths {
        list eth {
          description 'Ethernet interface mode.'
                      ;
          key if-name ;
          leaf if-name {
            description 'Interface name.'
                        ;
            type ncd:ifname {
              length 1..31 {
                description Ifname ;
              }
            }
          }
          leaf negotiation {
            description 'Configures the port negotiation mode.'
                        ;
            type enumeration {
              enum negotiation-force {
                value 1 ;
                description 'Force negotiation mode.'
                            ;
              }
              enum negotiation-auto {
                value 2 ;
                description 'Auto negotiation mode.'
                            ;
              }
            }
            default negotiation-auto ;
          }
          leaf speed {
            description 'Configures the rate of a port.'
                        ;
            type enumeration {
              enum speed-10M {
                value 1 ;
                description 'Port speed is 10M.'
                            ;
              }
              enum speed-100M {
                value 2 ;
                description 'Port speed is 100M.'
                            ;
              }
              enum speed-1G {
                value 3 ;
                description 'Port speed is 1G.'
                            ;
              }
              enum speed-10G {
                value 4 ;
                description 'Port speed is 10G.'
                            ;
              }
              enum speed-25G {
                value 10 ;
                description 'Port speed is 25G.'
                            ;
              }
              enum speed-40G {
                value 5 ;
                description 'Port speed is 40G.'
                            ;
              }
              enum speed-50G {
                value 11 ;
                description 'Port speed is 50G.'
                            ;
              }
              enum speed-100G {
                value 6 ;
                description 'Port speed is 100G.'
                            ;
              }
              enum speed-200G {
                value 12 ;
                description 'Port speed is 200G.'
                            ;
              }
              enum speed-400G {
                value 13 ;
                description 'Port speed is 400G.'
                            ;
              }
              enum speed-auto {
                value 15 ;
                description 'Port speed is configured to auto, the real speed d'
                          + 'epend on optical module.'
                            ;
              }
            }
            default speed-1G ;
          }
          leaf pemode {
            description 'Configures the copper-fiber attribute of a port.'
                        ;
            type enumeration {
              enum media-copper {
                value 1 ;
                description 'The PEMode of the port is electric.'
                            ;
              }
              enum media-fiber {
                value 2 ;
                description 'The PEMode of the port is optical.'
                            ;
              }
            }
            default media-fiber ;
          }
        }
      }
    }
  }
}
