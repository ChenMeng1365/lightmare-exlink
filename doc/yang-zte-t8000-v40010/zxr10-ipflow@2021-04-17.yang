module zxr10-ipflow {
  namespace 'http://www.zte.com.cn/zxr10/netconf/schema/rosng/ipflow'
            ;
  prefix ipflow ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe IPFLOW'
              ;
  revision 2021-04-17 {
    description 'Add enumeration value:dot1qVlanId and dot1qCustomerVlanId for'+"\n"
              + '/ipflow:configuration/ipflow:ipflow/ipflow:records/ipflow:reco'
              + 'rd/ipflow:common-fields/ipflow:common-field/ipflow:field-type.'
                ;
  }
  revision 2021-01-04 {
    description 'Add enumeration value:ipDiffServCodePoint for'+"\n"
              + '/ipflow:configuration/ipflow:ipflow/ipflow:records/ipflow:reco'
              + 'rd/ipflow:common-fields/ipflow:common-field/ipflow:field-type.'
                ;
  }
  revision 2020-12-21 {
    description 'add these features: ipv4-bgp-flowspec-sample and ipv6-bgp-flow'
              + 'spec-sample'+"\n"
              + 'add /ipflow:configuration/ipflow:ipflow/ipflow:methods/ipflow:'
              + 'ipv4-flowspec-monitors'+"\n"
              + 'add /ipflow:configuration/ipflow:ipflow/ipflow:methods/ipflow:'
              + 'ipv6-flowspec-monitors'+"\n"
              + 'add ipv4-bgp-flowspec-sample feature for the node of /ipflow:c'
              + 'onfiguration/ipflow:ipflow/ipflow:methods/ipflow:ipv4-flowspec'
              + '-monitors'+"\n"
              + 'add ipv6-bgp-flowspec-sample feature for the node of /ipflow:c'
              + 'onfiguration/ipflow:ipflow/ipflow:methods/ipflow:ipv6-flowspec'
              + '-monitors'
                ;
  }
  revision 2020-06-04 {
    description 'These feartures are included for PTN products:interface-mpls-s'
              + 'ample,flow-distributions and interface-acl-sample.'
                ;
  }
  revision 2020-03-05 {
    description "Add choice node mode:/ipflow:configuration/ipflow:ipflow/ipflo"
              + "'w:exporters/ipflow:exporter/ipflow:destination/ipflow:vrf-mod"
              + "e
\nAdd case mode:/ipflow:configuration/ipflow:ipflow/ipflo'w:"
              + "exporters/ipflow:exporter/ipflow:destination/ipflow:vrf-mode/i"
              + "pflow:vrf-common
\nAdd case mode:/ipflow:configuration/ipflow:"
              + "ipflow/ipflo'w:exporters/ipflow:exporter/ipflow:destination/ip"
              + "flow:vrf-mode/ipflow:vrf-dcn
\nAdd leaf mode:/ipflow:configura"
              + "tion/ipflow:ipflow/ipflo'w:exporters/ipflow:exporter/ipflow:de"
              + "stination/ipflow:vrf-mode/ipflow:vrf-dcn/ipflow:dcn"
                ;
  }
  revision 2019-05-14 {
    description '1. Add choice node mode:'+"\n"
              + '/ipflow:configuration/ipflow:ipflow/ipflow:samplers/ipflow:sam'
              + 'pler/ipflow:mode.'+"\n"
              + '2. Obsolete leaf node sampler-rate and sampler-mode:'+"\n"
              + '/ipflow:configuration/ipflow:ipflow/ipflow:samplers/ipflow:sam'
              + 'pler/ipflow:sample-rate;'+"\n"
              + '/ipflow:configuration/ipflow:ipflow/ipflow:samplers/ipflow:sam'
              + 'pler/ipflow:sample-mode.'+"\n"
              + '3. Add enumeration value:'+"\n"
              + '/ipflow:configuration/ipflow:ipflow/ipflow:records/ipflow:reco'
              + 'rd/ipflow:common-fields/ipflow:common-field/ipflow:field-type.'
                ;
  }
  revision 2015-06-05 {
    description 'remove unsupported value 48(flowSamplerId) and 210(paddingOcte'
              + 'ts) and 234(ingressVRFID) and 235(egressVRFID)of /ipflow:confi'
              + 'guration/ipflow:ipflow/ipflow:records/ipflow:record/ipflow:com'
              + 'mon-fields/ipflow:common-field/ipflow:field-type'+"\n"
              + 'add these features: interface-mpls-sample and interface-acl-sa'
              + 'mpl and flow-distributions'+"\n"
              + 'add interface-mpls-sample feature for the node of /ipflow:conf'
              + 'iguration/ipflow:ipflow/ipflow:methods/ipflow:interface-monito'
              + 'rs/ipflow:mpls-flow-monitors'+"\n"
              + 'add interface-acl-sample feature for the node of /ipflow:confi'
              + 'guration/ipflow:ipflow/ipflow:methods/ipflow:interface-acl-mon'
              + 'itors'+"\n"
              + 'add flow-distributions feature for the node of /ipflow:configu'
              + 'ration/ipflow:ipflow/ipflow:flow-distributions'
                ;
  }
  revision 2015-01-15 {
    description 'remove unsupported value 32(icmpTypeCodeIPv4) and 33(igmpType)'
              + ' of /ipflow:configuration/ipflow:ipflow/ipflow:records/ipflow:'
              + 'record/ipflow:common-fields/ipflow:common-field/ipflow:field-t'
              + 'ype'+"\n"
              + 'change length of /ipflow:configuration/ipflow:ipflow/ipflow:me'
              + 'thods/ipflow:interface-acl-monitors/ipflow:ip-flow-monitors/ip'
              + 'flow:custom-samplers/ipflow:custom-sampler/ipflow:sampler-name'
              + ' to 1..32'
                ;
  }
  revision 2014-09-11 {
    description 'add /ipflow:state'
                ;
  }
  revision 2014-08-14 {
    description 'modify the length of these nodes from 35 to 32:'+"\n"
              + '/ipflow:configuration/ipflow:ipflow/ipflow:records/ipflow:reco'
              + 'rd/ipflow:record-name'+"\n"
              + '/ipflow:configuration/ipflow:ipflow/ipflow:samplers/ipflow:sam'
              + 'pler/ipflow:sampler-name'+"\n"
              + '/ipflow:configuration/ipflow:ipflow/ipflow:exporters/ipflow:ex'
              + 'porter/ipflow:exporter-name'+"\n"
              + '/ipflow:configuration/ipflow:ipflow/ipflow:exporters/ipflow:ex'
              + 'porter/ipflow:destination/ipflow:vrf'+"\n"
              + '/ipflow:configuration/ipflow:ipflow/ipflow:monitors/ipflow:mon'
              + 'itor/ipflow:monitor-name'+"\n"
              + '/ipflow:configuration/ipflow:ipflow/ipflow:monitors/ipflow:mon'
              + 'itor/ipflow:record/ipflow:record-name'+"\n"
              + '/ipflow:configuration/ipflow:ipflow/ipflow:monitors/ipflow:mon'
              + 'itor/ipflow:exporters/ipflow:exporter/ipflow:exporter-name'+"\n"
              + '/ipflow:configuration/ipflow:ipflow/ipflow:methods/ipflow:inte'
              + 'rface-monitors/ipflow:ip-flow-monitors/ipflow:custom-samplers/'
              + 'ipflow:custom-sampler/ipflow:monitor-name'+"\n"
              + '/ipflow:configuration/ipflow:ipflow/ipflow:methods/ipflow:inte'
              + 'rface-monitors/ipflow:ip-flow-monitors/ipflow:custom-samplers/'
              + 'ipflow:custom-sampler/ipflow:sampler-name'+"\n"
              + '/ipflow:configuration/ipflow:ipflow/ipflow:methods/ipflow:inte'
              + 'rface-monitors/ipflow:ip-flow-monitors/ipflow:default-samplers'
              + '/ipflow:default-sampler/ipflow:monitor-name'+"\n"
              + '/ipflow:configuration/ipflow:ipflow/ipflow:methods/ipflow:inte'
              + 'rface-monitors/ipflow:mpls-flow-monitors/ipflow:default-sample'
              + 'rs/ipflow:default-sampler/ipflow:monitor-name'+"\n"
              + '/ipflow:configuration/ipflow:ipflow/ipflow:methods/ipflow:inte'
              + 'rface-monitors/ipflow:mpls-flow-monitors/ipflow:custom-sampler'
              + 's/ipflow:custom-sampler/ipflow:monitor-name'+"\n"
              + '/ipflow:configuration/ipflow:ipflow/ipflow:methods/ipflow:inte'
              + 'rface-monitors/ipflow:mpls-flow-monitors/ipflow:custom-sampler'
              + 's/ipflow:custom-sampler/ipflow:sampler-name'+"\n"
              + '/ipflow:configuration/ipflow:ipflow/ipflow:methods/ipflow:inte'
              + 'rface-acl-monitors/ipflow:ip-flow-monitors/ipflow:default-samp'
              + 'lers/ipflow:default-sampler/ipflow:monitor-name'+"\n"
              + '/ipflow:configuration/ipflow:ipflow/ipflow:methods/ipflow:inte'
              + 'rface-acl-monitors/ipflow:ip-flow-monitors/ipflow:custom-sampl'
              + 'ers/ipflow:custom-sampler/ipflow:monitor-name'+"\n"
              + '/ipflow:configuration/ipflow:ipflow/ipflow:methods/ipflow:inte'
              + 'rface-acl-monitors/ipflow:ip-flow-monitors/ipflow:custom-sampl'
              + 'ers/ipflow:custom-sampler/ipflow:sampler-name'
                ;
  }
  revision 2014-02-28 {
    description 'Initial version'
                ;
  }
  feature interface-mpls-sample {
    description 'Sample mpls packets on one interface'
                ;
  }
  feature interface-acl-sample {
    description 'User ACL to filter packets sampled on one interface'
                ;
  }
  feature flow-distributions {
    description 'Set the policy of distributing flows'
                ;
  }
  feature ipv4-bgp-flowspec-sample {
    description 'Sample ipv4 bgp flowspec flows.'
                ;
  }
  feature ipv6-bgp-flowspec-sample {
    description 'Sample ipv6 bgp flowspec flows.'
                ;
  }
  container configuration {
    description 'IPFLOW module configuration model'
                ;
    container ipflow {
      description 'IPFLOW module configuration root node'
                  ;
      container records {
        description 'IPFLOW record information'
                    ;
        list record {
          description 'IPFLOW record information'
                      ;
          key record-name ;
          leaf record-name {
            description 'IPFLOW record name'
                        ;
            type string {
              length 1..32 ;
            }
          }
          container counter-fields {
            description 'IPFLOW counter field'
                        ;
            list counter-field {
              description 'IPFLOW counter field'
                          ;
              key field-type ;
              leaf field-type {
                description 'IPFLOW field type'
                            ;
                type enumeration {
                  enum octetDeltaCount {
                    value 1 ;
                  }
                  enum packetDeltaCount {
                    value 2 ;
                  }
                }
              }
              leaf field-size {
                description 'IPFLOW field size'
                            ;
                type enumeration {
                  enum default {
                    value 0 ;
                  }
                  enum long {
                    value 8 ;
                  }
                }
                default default ;
              }
            }
          }
          container time-fields {
            description 'IPFLOW time field'
                        ;
            list time-field {
              description 'IPFLOW time field'
                          ;
              key field-type ;
              leaf field-type {
                description 'IPFLOW field type'
                            ;
                type enumeration {
                  enum flowEndSysUpTime {
                    value 21 ;
                  }
                  enum flowStartSysUpTime {
                    value 22 ;
                  }
                  enum flowStartMilliseconds {
                    value 152 ;
                  }
                  enum flowEndMilliseconds {
                    value 153 ;
                  }
                }
              }
            }
          }
          container ipv4-prefix-fields {
            description 'IPFLOW IPv4 address prefix field'
                        ;
            list ipv4-prefix-field {
              description 'IPFLOW IPv4 address prefix field'
                          ;
              key 'field-type field-attr'
                  ;
              leaf field-type {
                description 'IPFLOW field type'
                            ;
                type enumeration {
                  enum sourceIPv4Prefix {
                    value 44 ;
                  }
                  enum destinationIPv4Prefix {
                    value 45 ;
                  }
                }
              }
              leaf field-attr {
                description 'IPFLOW is key feild'
                            ;
                type enumeration {
                  enum match {
                    value 1 ;
                  }
                  enum collect {
                    value 2 ;
                  }
                }
              }
              leaf field-info {
                description 'IPFLOW field information'
                            ;
                type uint8 {
                  range 1..32 ;
                }
                mandatory true ;
              }
            }
          }
          container ipv6-prefix-fields {
            description 'IPFLOW IPv6 address prefix field'
                        ;
            list ipv6-prefix-field {
              description 'IPFLOW IPv6 address prefix field'
                          ;
              key 'field-type field-attr'
                  ;
              leaf field-type {
                description 'IPFLOW field type'
                            ;
                type enumeration {
                  enum destinationIPv6Prefix {
                    value 169 ;
                  }
                  enum sourceIPv6Prefix {
                    value 170 ;
                  }
                }
              }
              leaf field-attr {
                description 'IPFLOW is key feild'
                            ;
                type enumeration {
                  enum match {
                    value 1 ;
                  }
                  enum collect {
                    value 2 ;
                  }
                }
              }
              leaf field-info {
                description 'IPFLOW field information'
                            ;
                type uint8 {
                  range 1..128 ;
                }
                mandatory true ;
              }
            }
          }
          container common-fields {
            description 'IPFLOW common field'
                        ;
            list common-field {
              description 'IPFLOW common field'
                          ;
              key 'field-type field-attr'
                  ;
              leaf field-type {
                description 'IPFLOW field type'
                            ;
                type enumeration {
                  enum protocolIdentifier {
                    value 4 ;
                  }
                  enum ipClassOfService {
                    value 5 ;
                  }
                  enum tcpControlBits {
                    value 6 ;
                  }
                  enum sourceTransportPort {
                    value 7 ;
                  }
                  enum sourceIPv4Address {
                    value 8 ;
                  }
                  enum sourceIPv4PrefixLength {
                    value 9 ;
                  }
                  enum ingressInterface {
                    value 10 ;
                  }
                  enum destinationTransportPort {
                    value 11 ;
                  }
                  enum destinationIPv4Address {
                    value 12 ;
                  }
                  enum destinationIPv4PrefixLength {
                    value 13 ;
                  }
                  enum egressInterface {
                    value 14 ;
                  }
                  enum ipNextHopIPv4Address {
                    value 15 ;
                  }
                  enum bgpSourceAsNumber {
                    value 16 ;
                  }
                  enum bgpDestinationAsNumber {
                    value 17 ;
                  }
                  enum bgpNextHopIPv4Address {
                    value 18 ;
                  }
                  enum sourceIPv6Address {
                    value 27 ;
                  }
                  enum destinationIPv6Address {
                    value 28 ;
                  }
                  enum sourceIPv6PrefixLength {
                    value 29 ;
                  }
                  enum destinationIPv6PrefixLength {
                    value 30 ;
                  }
                  enum flowLabelIPv6 {
                    value 31 ;
                  }
                  enum samplingInverval {
                    value 34 ;
                  }
                  enum sourceMacAddress {
                    value 56 ;
                  }
                  enum destinationMacAddress {
                    value 57 ;
                  }
                  enum ipVersion {
                    value 60 ;
                  }
                  enum flowDirection {
                    value 61 ;
                  }
                  enum ipNextHopIPv6Address {
                    value 62 ;
                  }
                  enum bgpNextHopIPv6Address {
                    value 63 ;
                  }
                  enum mplsTopLabelStackSection {
                    value 70 ;
                  }
                  enum mplsLabelStackSection2 {
                    value 71 ;
                  }
                  enum mplsLableStackSection3 {
                    value 72 ;
                  }
                  enum mplsLableStackSection4 {
                    value 73 ;
                  }
                  enum mplsLableStackSection5 {
                    value 74 ;
                  }
                  enum bgpNextAdjacentAsNumber {
                    value 128 ;
                  }
                  enum bgpPrevAdjacentAsNumber {
                    value 129 ;
                  }
                  enum icmpTypeIPv4 {
                    value 176 ;
                  }
                  enum icmpCodeIPv4 {
                    value 177 ;
                  }
                  enum icmpTypeIPv6 {
                    value 178 ;
                  }
                  enum icmpCodeIPv6 {
                    value 179 ;
                  }
                  enum ipDiffServCodePoint {
                    value 195 ;
                  }
                  enum samplingAlgorithm {
                    value 304 ;
                  }
                  enum samplingTimeInterval {
                    value 307 ;
                  }
                  enum samplingTimeSpace {
                    value 308 ;
                  }
                  enum samplingRandomSize {
                    value 309 ;
                  }
                  enum samplingRandomPopulation {
                    value 310 ;
                  }
                  enum dot1qVlanId {
                    value 243 ;
                  }
                  enum dot1qCustomerVlanId {
                    value 245 ;
                  }
                }
              }
              leaf field-attr {
                description 'IPFLOW is key feild'
                            ;
                type enumeration {
                  enum match {
                    value 1 ;
                  }
                  enum collect {
                    value 2 ;
                  }
                }
              }
            }
          }
        }
      }
      container samplers {
        description 'IPFLOW flow sampler information'
                    ;
        list sampler {
          description 'IPFLOW flow sampler information'
                      ;
          key sampler-name ;
          leaf sampler-name {
            description 'IPFLOW sampler name'
                        ;
            type string {
              length 1..32 ;
            }
          }
          leaf sample-rate {
            status obsolete {
              ncd:revise-date 2019-05-14 ;
            }
            description 'IPFLOW sampling rate'
                        ;
            type uint32 {
              range 0..4294967295 ;
            }
            default 1000 ;
          }
          leaf sample-mode {
            status obsolete {
              ncd:revise-date 2019-05-14 ;
            }
            description 'IPFLOW sampling mode'
                        ;
            type enumeration {
              enum deterministic {
                value 1 ;
              }
            }
            default deterministic ;
          }
          choice mode {
            description 'Specify the type of sampling and the sampling interval.'
                        ;
            default deterministic ;
            case deterministic {
              description 'Enable deterministic mode sampling.'
                          ;
              container deterministic {
                description 'Enable deterministic mode sampling.'
                            ;
                leaf sample-rate {
                  description 'IPFLOW sampling rate.'
                              ;
                  type uint32 {
                    range 0..4294967295 ;
                  }
                  default 1000 ;
                }
              }
            }
            case time-deterministic {
              description 'Enable time-deterministic mode sampling.'
                          ;
              container time-deterministic {
                description 'Enable time-deterministic mode sampling.'
                            ;
                presence 'time deterministic'
                         ;
                leaf time-space {
                  description 'Sampling time space.'
                              ;
                  type uint32 {
                    range 1..30000000 ;
                  }
                  mandatory true ;
                }
              }
            }
            case random {
              description 'Enable random mode sampling.'
                          ;
              container random {
                description 'Enable random mode sampling.'
                            ;
                presence random ;
                leaf random-size {
                  description 'Random sampling size.'
                              ;
                  type uint32 {
                    range 1..65535 ;
                  }
                  mandatory true ;
                }
                leaf random-population {
                  description 'Random sampling population.'
                              ;
                  type uint32 {
                    range 1..65535 ;
                  }
                  mandatory true ;
                }
              }
            }
            ncd:revise-date 2019-05-14 ;
          }
        }
      }
      container exporters {
        description 'IPFLOW flow exporter'
                    ;
        list exporter {
          description 'IPFLOW flow exporter'
                      ;
          key exporter-name ;
          leaf exporter-name {
            description 'IPFLOW exporter name'
                        ;
            type string {
              length 1..32 ;
            }
          }
          leaf export-protocol {
            description 'IPFLOW exporter format'
                        ;
            type enumeration {
              enum netflow-v5 {
                value 5 ;
              }
              enum netflow-v8 {
                value 8 ;
              }
              enum netflow-v9 {
                value 9 ;
              }
              enum ipfix {
                value 10 ;
              }
            }
            default netflow-v9 ;
          }
          leaf transport-protocol {
            description 'IPFLOW transport protocol'
                        ;
            type enumeration {
              enum udp {
                value 1 ;
              }
            }
            default udp ;
          }
          leaf port-num {
            description 'IPFLOW transport port number'
                        ;
            type uint16 {
              range 1..65535 ;
            }
            default 2055 ;
          }
          leaf template-resend-timeout {
            description 'IPFLOW template resend timeout'
                        ;
            type uint32 {
              range 1..86400 ;
            }
            units second ;
            default 600 ;
          }
          leaf template-resend-pkt-num {
            description 'IPFLOW template refresh rate'
                        ;
            type uint32 {
              range 1..600 ;
            }
            default 20 ;
          }
          leaf dscp {
            description 'IPFLOW exporter DSCP value'
                        ;
            type uint8 {
              range 0..63 ;
            }
            default 0 ;
          }
          container destination {
            description 'IPFLOW destination information'
                        ;
            choice ip-type {
              description 'IPFLOW destination address type'
                          ;
              case ipv4 {
                description 'IPFLOW IPv4 type'
                            ;
                leaf ipv4-addr {
                  description 'IPFLOW IPv4 address'
                              ;
                  type ncd:ipv4-address ;
                  mandatory true ;
                }
              }
              case ipv6 {
                description 'IPFLOW IPv6 type'
                            ;
                leaf ipv6-addr {
                  description 'IPFLOW IPv6 address'
                              ;
                  type ncd:ipv6-address ;
                  mandatory true ;
                }
              }
            }
            choice vrf-mode {
              description 'Specify the type and name of vrf.'
                          ;
              case vrf-common {
                description 'Specify vrf name which is not reserved.'
                            ;
                leaf vrf {
                  description 'IPFLOW vrf name'
                              ;
                  type string {
                    length 1..32 ;
                  }
                }
              }
              case vrf-dcn {
                description 'Specify dcn vrf.'
                            ;
                leaf dcn {
                  description 'Specify dcn vrf.'
                              ;
                  type empty ;
                }
              }
              ncd:revise-date 2020-03-05 ;
            }
          }
          container source {
            description 'IPFLOW source information'
                        ;
            choice source-type {
              description 'IPFLOW source type'
                          ;
              case address-type {
                description 'IPFLOW source address'
                            ;
                container address {
                  description 'IPFLOW source address'
                              ;
                  choice ip-type {
                    description 'IPFLOW source address type'
                                ;
                    case ipv4 {
                      description 'IPFLOW IPv4 type'
                                  ;
                      leaf ipv4-addr {
                        description 'IPFLOW IPv4 address'
                                    ;
                        type ncd:ipv4-address ;
                        mandatory true ;
                      }
                    }
                    case ipv6 {
                      description 'IPFLOW IPv6 type'
                                  ;
                      leaf ipv6-addr {
                        description 'IPFLOW IPv6 address'
                                    ;
                        type ncd:ipv6-address ;
                        mandatory true ;
                      }
                    }
                  }
                }
              }
              case interface-type {
                description 'IPFLOW source interface'
                            ;
                container interface {
                  description 'IPFLOW source interface'
                              ;
                  leaf interface-name {
                    description 'IPFLOW source interface name'
                                ;
                    type ncd:ifname ;
                    mandatory true ;
                  }
                }
              }
            }
          }
        }
      }
      container monitors {
        description 'IPFLOW monitor information'
                    ;
        list monitor {
          description 'IPFLOW monitor information'
                      ;
          key monitor-name ;
          leaf monitor-name {
            description 'IPFLOW monitor name'
                        ;
            type string {
              length 1..32 ;
            }
          }
          leaf cache-entry-num {
            description 'The maximum number of cache entries'
                        ;
            type uint32 {
              range 16..4294967295 ;
            }
            default 4096 ;
          }
          leaf cache-active-timeout {
            description 'IPFLOW active flow timeout'
                        ;
            type uint32 {
              range 0..604800 ;
            }
            units second ;
            default 1800 ;
          }
          leaf cache-inactive-timeout {
            description 'IPFLOW inactive flow timeout'
                        ;
            type uint32 {
              range 0..604800 ;
            }
            units second ;
            default 600 ;
          }
          container record {
            description 'IPFLOW record information'
                        ;
            choice record-in-monitor {
              description 'IPFLOW template type'
                          ;
              case custom {
                description 'IPFLOW user-defined template'
                            ;
                leaf record-name {
                  description 'IPFLOW record name'
                              ;
                  type string {
                    length 1..32 ;
                  }
                  mandatory true ;
                }
              }
              case pre-define {
                description 'IPFLOW predefined record'
                            ;
                leaf pre-define-type {
                  description 'IPFLOW predefined template type'
                              ;
                  type enumeration {
                    enum netflow-original {
                      value 1 ;
                    }
                    enum netflow-protocol-port {
                      value 2 ;
                    }
                    enum netflow-ipv4-original-input {
                      value 3 ;
                    }
                    enum netflow-ipv4-original-output {
                      value 4 ;
                    }
                  }
                  mandatory true ;
                }
              }
            }
          }
          container exporters {
            list exporter {
              description 'IPFLOW flow exporter'
                          ;
              key exporter-name ;
              leaf exporter-name {
                description 'IPFLOW exporter name'
                            ;
                type string {
                  length 1..32 ;
                }
              }
            }
          }
        }
      }
      container methods {
        description 'IPFLOW monitor method'
                    ;
        container interface-monitors {
          description 'IPFLOW interface monitor method'
                      ;
          container ip-flow-monitors {
            description 'IPFLOW interface monitor method'
                        ;
            container default-samplers {
              description 'IPFLOW default sampler'
                          ;
              list default-sampler {
                description 'IPFLOW default sampler'
                            ;
                key 'if-name ip-type sample-dir sample-pkt-type monitor-name'
                    ;
                leaf if-name {
                  description 'IPFLOW interface name'
                              ;
                  type ncd:ifname ;
                }
                leaf ip-type {
                  description 'IPFLOW flow type'
                              ;
                  type enumeration {
                    enum ipv4 {
                      value 4 ;
                    }
                    enum ipv6 {
                      value 6 ;
                    }
                  }
                }
                leaf sample-dir {
                  description 'IPFLOW sampling direction'
                              ;
                  type enumeration {
                    enum input {
                      value 0 ;
                    }
                    enum output {
                      value 1 ;
                    }
                  }
                }
                leaf sample-pkt-type {
                  description 'IPFLOW interface monitor type'
                              ;
                  type enumeration {
                    enum multicast {
                      value 0 ;
                    }
                    enum unicast {
                      value 1 ;
                    }
                    enum all {
                      value 2 ;
                    }
                  }
                }
                leaf monitor-name {
                  description 'IPFLOW monitor name'
                              ;
                  type string {
                    length 1..32 ;
                  }
                }
              }
            }
            container custom-samplers {
              description 'IPFLOW custom sampler'
                          ;
              list custom-sampler {
                description 'IPFLOW custom sampler'
                            ;
                key 'if-name ip-type sample-dir sample-pkt-type monitor-name sa'
                  + 'mpler-name'
                    ;
                leaf if-name {
                  description 'IPFLOW interface name'
                              ;
                  type ncd:ifname ;
                }
                leaf ip-type {
                  description 'IPFLOW flow type'
                              ;
                  type enumeration {
                    enum ipv4 {
                      value 4 ;
                    }
                    enum ipv6 {
                      value 6 ;
                    }
                  }
                }
                leaf sample-dir {
                  description 'IPFLOW sampling direction'
                              ;
                  type enumeration {
                    enum input {
                      value 0 ;
                    }
                    enum output {
                      value 1 ;
                    }
                  }
                }
                leaf sample-pkt-type {
                  description 'IPFLOW interface monitor type'
                              ;
                  type enumeration {
                    enum multicast {
                      value 0 ;
                    }
                    enum unicast {
                      value 1 ;
                    }
                    enum all {
                      value 2 ;
                    }
                  }
                }
                leaf monitor-name {
                  description 'IPFLOW monitor name'
                              ;
                  type string {
                    length 1..32 ;
                  }
                }
                leaf sampler-name {
                  description 'IPFLOW sampler name'
                              ;
                  type string {
                    length 1..32 ;
                  }
                }
              }
            }
          }
          container mpls-flow-monitors {
            if-feature interface-mpls-sample ;
            description 'IPFLOW mpls flow interface monitor method'
                        ;
            container default-samplers {
              description 'IPFLOW default sampler'
                          ;
              list default-sampler {
                description 'IPFLOW default sampler'
                            ;
                key 'if-name sample-dir monitor-name'
                    ;
                leaf if-name {
                  description 'IPFLOW interface name'
                              ;
                  type ncd:ifname ;
                }
                leaf sample-dir {
                  description 'IPFLOW sampling direction'
                              ;
                  type enumeration {
                    enum input {
                      value 0 ;
                    }
                    enum output {
                      value 1 ;
                    }
                  }
                }
                leaf monitor-name {
                  description 'IPFLOW monitor name'
                              ;
                  type string {
                    length 1..32 ;
                  }
                }
              }
            }
            container custom-samplers {
              description 'IPFLOW custom sampler'
                          ;
              list custom-sampler {
                description 'IPFLOW custom sampler'
                            ;
                key 'if-name sample-dir monitor-name sampler-name'
                    ;
                leaf if-name {
                  description 'IPFLOW interface name'
                              ;
                  type ncd:ifname ;
                }
                leaf sample-dir {
                  description 'IPFLOW sampling direction'
                              ;
                  type enumeration {
                    enum input {
                      value 0 ;
                    }
                    enum output {
                      value 1 ;
                    }
                  }
                }
                leaf monitor-name {
                  description 'IPFLOW monitor name'
                              ;
                  type string {
                    length 1..32 ;
                  }
                }
                leaf sampler-name {
                  description 'IPFLOW sampler name'
                              ;
                  type string {
                    length 1..32 ;
                  }
                }
              }
            }
          }
        }
        container interface-acl-monitors {
          if-feature interface-acl-sample ;
          description 'IPFLOW interface ACL monitor method'
                      ;
          container ip-flow-monitors {
            description 'IPFLOW ip flow monitor method'
                        ;
            container default-samplers {
              description 'IPFLOW default sampler'
                          ;
              list default-sampler {
                description 'IPFLOW default sampler'
                            ;
                key 'if-name ip-type sample-dir acl-name monitor-name'
                    ;
                leaf if-name {
                  description 'IPFLOW interface name'
                              ;
                  type ncd:ifname ;
                }
                leaf ip-type {
                  description 'IPFLOW flow type'
                              ;
                  type enumeration {
                    enum ipv4 {
                      value 4 ;
                    }
                    enum ipv6 {
                      value 6 ;
                    }
                  }
                }
                leaf sample-dir {
                  description 'IPFLOW sampling direction'
                              ;
                  type enumeration {
                    enum input {
                      value 0 ;
                    }
                    enum output {
                      value 1 ;
                    }
                  }
                }
                leaf acl-name {
                  description 'IPFLOW ACL name'
                              ;
                  type string {
                    length 1..31 ;
                  }
                }
                leaf monitor-name {
                  description 'IPFLOW monitor name'
                              ;
                  type string {
                    length 1..32 ;
                  }
                }
              }
            }
            container custom-samplers {
              description 'IPFLOW custom sampler'
                          ;
              list custom-sampler {
                description 'IPFLOW custom sampler'
                            ;
                key 'if-name ip-type sample-dir acl-name monitor-name sampler-n'
                  + 'ame'
                    ;
                leaf if-name {
                  description 'IPFLOW interface name'
                              ;
                  type ncd:ifname ;
                }
                leaf ip-type {
                  description 'IPFLOW flow type'
                              ;
                  type enumeration {
                    enum ipv4 {
                      value 4 ;
                    }
                    enum ipv6 {
                      value 6 ;
                    }
                  }
                }
                leaf sample-dir {
                  description 'IPFLOW sampling direction'
                              ;
                  type enumeration {
                    enum input {
                      value 0 ;
                    }
                    enum output {
                      value 1 ;
                    }
                  }
                }
                leaf acl-name {
                  description 'IPFLOW ACL name'
                              ;
                  type string {
                    length 1..31 ;
                  }
                }
                leaf monitor-name {
                  description 'IPFLOW monitor name'
                              ;
                  type string {
                    length 1..32 ;
                  }
                }
                leaf sampler-name {
                  description 'IPFLOW sampler name'
                              ;
                  type string {
                    length 1..32 ;
                  }
                }
              }
            }
          }
        }
        container ipv4-flowspec-monitors {
          if-feature ipv4-bgp-flowspec-sample ;
          description 'IPFLOW ipv4 bgp flowspec monitor method'
                      ;
          container global-monitor {
            description 'IPFLOW global IPV4 flow monitor method'
                        ;
            presence prevent ;
            leaf monitor-name {
              description 'IPFLOW monitor name'
                          ;
              type string {
                length 1..32 ;
              }
              mandatory true ;
            }
            leaf sampler-name {
              description 'IPFLOW sampler name'
                          ;
              type string {
                length 1..32 ;
              }
            }
          }
          container vrf-monitors {
            description 'IPFLOW vrf IPV4 flow monitor method'
                        ;
            list vrf-monitor {
              description 'IPFLOW vrf monitor'
                          ;
              key vrf-name ;
              leaf vrf-name {
                description 'IPFLOW VRF name'
                            ;
                type string {
                  length 1..32 ;
                }
              }
              leaf monitor-name {
                description 'IPFLOW monitor name'
                            ;
                type string {
                  length 1..32 ;
                }
                mandatory true ;
              }
              leaf sampler-name {
                description 'IPFLOW sampler name'
                            ;
                type string {
                  length 1..32 ;
                }
              }
            }
          }
          ncd:revise-date 2020-12-21 ;
        }
        container ipv6-flowspec-monitors {
          if-feature ipv6-bgp-flowspec-sample ;
          description 'IPFLOW ipv6 bgp flowspec monitor method'
                      ;
          container global-monitor {
            description 'IPFLOW global IPV6 flow monitor method'
                        ;
            presence prevent ;
            leaf monitor-name {
              description 'IPFLOW monitor name'
                          ;
              type string {
                length 1..32 ;
              }
              mandatory true ;
            }
            leaf sampler-name {
              description 'IPFLOW sampler name'
                          ;
              type string {
                length 1..32 ;
              }
            }
          }
          container vrf-monitors {
            description 'IPFLOW vrf IPV6 flow monitor method'
                        ;
            list vrf-monitor {
              description 'IPFLOW vrf monitor'
                          ;
              key vrf-name ;
              leaf vrf-name {
                description 'IPFLOW VRF name'
                            ;
                type string {
                  length 1..32 ;
                }
              }
              leaf monitor-name {
                description 'IPFLOW monitor name'
                            ;
                type string {
                  length 1..32 ;
                }
                mandatory true ;
              }
              leaf sampler-name {
                description 'IPFLOW sampler name'
                            ;
                type string {
                  length 1..32 ;
                }
              }
            }
          }
          ncd:revise-date 2020-12-21 ;
        }
      }
      container flow-distributions {
        if-feature flow-distributions ;
        description 'IPFLOW flow distribution'
                    ;
        list flow-distribution {
          description 'IPFLOW flow distribution'
                      ;
          key board-name ;
          leaf board-name {
            description 'IPFLOW board name'
                        ;
            type ncd:board ;
          }
          leaf dst-processor-type {
            description 'IPFLOW processer type'
                        ;
            type enumeration {
              enum self {
                value 1 ;
              }
              enum spu {
                value 2 ;
              }
            }
            mandatory true ;
          }
        }
      }
    }
  }
  container state {
    config false ;
    description 'To get state of IPFLOW module'
                ;
    container ipflow {
      container monitor-statistics {
        description 'The statistics of flow monitors'
                    ;
        list monitor-statistic {
          description 'The statistic of flow monitor'
                      ;
          key 'monitor-name cpu-name'
              ;
          leaf monitor-name {
            description 'IPFLOW monitor name'
                        ;
            type string {
              length 1..32 ;
            }
          }
          leaf cpu-name {
            description 'The name of the cpu where the IPFLOW is running'
                        ;
            type ncd:cpu ;
          }
          leaf max-cache-entry-num {
            description 'The maximum cache entries number'
                        ;
            type uint32 ;
          }
          leaf alloced-cache-entry-num {
            description 'The number of cache entries which have been allocated '
                      + 'aleady'
                        ;
            type uint32 ;
          }
          leaf active-cache-entry-num {
            description 'The number of flows in the cache'
                        ;
            type uint32 ;
          }
          leaf active-aged-flows {
            description 'The number of active aged flows since the flow monitor'
                      + ' was created'
                        ;
            type uint64 ;
          }
          leaf inactive-aged-flows {
            description 'The number of inactive aged flows since the flow monit'
                      + 'or was created'
                        ;
            type uint64 ;
          }
          leaf emergency-aged-flows {
            description 'The number of emergency aged flows since the flow moni'
                      + 'tor was created'
                        ;
            type uint64 ;
          }
          leaf counter-wrap-aged-flows {
            description 'The number of aged flows because of counter wrapped si'
                      + 'nce the flow monitor was created'
                        ;
            type uint64 ;
          }
          leaf force-aged-flows {
            description 'The number of flows which are forced to aged since the'
                      + ' flow monitor was created'
                        ;
            type uint64 ;
          }
        }
      }
      container exporter-statistics {
        description 'The statistics of flow exporters'
                    ;
        list exporter-statistic {
          description 'The statistic of flow exporter'
                      ;
          key 'exporter-name cpu-name'
              ;
          leaf exporter-name {
            description 'IPFLOW exporter name'
                        ;
            type string {
              length 1..32 ;
            }
          }
          leaf cpu-name {
            description 'The name of the cpu where the IPFLOW is running'
                        ;
            type ncd:cpu ;
          }
          leaf transmitted-messages {
            description 'The number of transmitted ipflow messages'
                        ;
            type uint64 ;
          }
          leaf transmitted-octets {
            description 'The number of octets of transmitted ipflow messages'
                        ;
            type uint64 ;
          }
          leaf discarded-messages {
            description 'The number of discarded ipflow messages'
                        ;
            type uint64 ;
          }
          leaf discarded-octets {
            description 'The number of octets of discarded ipflow messages'
                        ;
            type uint64 ;
          }
          leaf transmitted-data-records {
            description 'The number of transmitted data records'
                        ;
            type uint64 ;
          }
          leaf transmitted-templates {
            description 'The number of transmitted templates'
                        ;
            type uint64 ;
          }
          leaf transmitted-octets-rate-in-5-min {
            description 'The transmitted octets rate in 5 miniute'
                        ;
            type uint32 ;
            units Bps ;
          }
          leaf transmitted-messages-rate-in-5-min {
            description 'The transmitted message rate in 5 minute'
                        ;
            type uint32 ;
            units pps ;
          }
          leaf transmitted-octes-rate-in-1-hour {
            description 'The transmitted octets rate in 1 hour'
                        ;
            type uint32 ;
            units Bps ;
          }
          leaf transmitted-messages-rate-in-1-hour {
            description 'The transmitted message rate in 1 hour'
                        ;
            type uint32 ;
            units pps ;
          }
        }
      }
      container cpu-statistics {
        description 'The statistics of all CPUs'
                    ;
        list cpu-statistic {
          description 'The statistic of CPU'
                      ;
          key cpu-name ;
          leaf cpu-name {
            description 'The name of the cpu where the IPFLOW is running'
                        ;
            type ncd:cpu ;
          }
          leaf ipv4-ingress-pkts {
            description 'The number of sampled IPv4 ingress packets on the cpu'
                        ;
            type uint64 ;
          }
          leaf ipv4-egress-pkts {
            description 'The number of sampled IPv4 egress packets on the cpu'
                        ;
            type uint64 ;
          }
          leaf ipv6-ingress-pkts {
            description 'The number of sampled IPv6 ingress packets on the cpu'
                        ;
            type uint64 ;
          }
          leaf ipv6-egress-pkts {
            description 'The number of sampled IPv6 egress packets on the cpu'
                        ;
            type uint64 ;
          }
          leaf mpls-ingress-pkts {
            description 'The number of sampled MPLS ingress packets on the cpu'
                        ;
            type uint64 ;
          }
          leaf mpls-egress-pkts {
            description 'The number of sampled MPLS egress packets on the cpu'
                        ;
            type uint64 ;
          }
          leaf other-ingress-pkts {
            description 'The number of sampled ingress packets except IPv4 IPv6'
                      + ' and MPLS on the cpu'
                        ;
            type uint64 ;
          }
          leaf other-egress-pkts {
            description 'The number of sampled egress packets except IPv4 IPv6 '
                      + 'and MPLS on the cpu'
                        ;
            type uint64 ;
          }
          leaf parse-error-pkts {
            description 'The number of sampled packets which are dropped due to'
                      + ' error parsing on the cpu'
                        ;
            type uint64 ;
          }
          leaf other-error-pkts {
            description 'The number of sampled packets which are dropped due to'
                      + ' other reasons on the cpu'
                        ;
            type uint64 ;
          }
          leaf max-cache-entries {
            description 'The maximum cache entries that can be used by the cpu'
                        ;
            type uint32 ;
          }
          leaf total-cache-entries {
            description 'The total cache entries that are in use by the cpu'
                        ;
            type uint32 ;
          }
        }
      }
    }
  }
}
