module zxr10-trace {
  namespace 'http://www.zte.com.cn/zxr10/netconf/schema/rosng/trace'
            ;
  prefix trace ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe TRACE. Trace is typically used to'
            + ' find out all routers between two hosts.'
              ;
  revision 2021-03-30 {
    description '1) Add Feature /trace:uni-nni-trace-ipv6'+"\n"
              + '2) Add Choice /trace:operation/trace:trace/trace:ip-type/trace'
              + ':ipv6/trace:trace6s/trace:trace6/trace:status/trace:enable/tra'
              + 'ce:trace6-data/trace:trace6-type/trace:uni'+"\n"
              + '3) Add Choice /trace:operation/trace:trace/trace:ip-type/trace'
              + ':ipv6/trace:trace6s/trace:trace6/trace:status/trace:enable/tra'
              + 'ce:trace6-data/trace:trace6-type/trace:nni'
                ;
  }
  revision 2021-03-03 {
    description '1) Add Choice /trace/ip-type/ipv4/trace4S/trace4/status/enable'
              + '/trace4-data/normal/normal-opt/next-hop-option;'+"\n"
              + '2) Add Case /trace/ip-type/ipv4/trace4S/trace4/status/enable/t'
              + 'race4-data/normal/normal-opt/ipv4-next-hop;'+"\n"
              + '3) Add Case /trace/ip-type/ipv4/trace4S/trace4/status/enable/t'
              + 'race4-data/normal/normal-opt/ipv6-next-hop;'+"\n"
              + '4) Add Leaf /trace/ip-type/ipv4/trace4S/trace4/status/enable/t'
              + 'race4-data/normal/normal-opt/ipv4-next-hop/ipv4-next-hop;'+"\n"
              + '5) Add Leaf /trace/ip-type/ipv4/trace4S/trace4/status/enable/t'
              + 'race4-data/normal/normal-opt/ipv6-next-hop/ipv6-next-hop;'+"\n"
              + '6) Add Leaf /trace/ip-type/ipv6/trace6S/trace6/status/enable/t'
              + 'race6-data/normal/normal-opt/interface;'+"\n"
              + '7) Add Choice /trace/ip-type/ipv6/trace6S/trace6/status/enable'
              + '/trace6-data/normal/normal-opt/next-hop-option;'+"\n"
              + '8) Add Case /trace/ip-type/ipv6/trace6S/trace6/status/enable/t'
              + 'race6-data/normal/normal-opt/ipv4-next-hop;'+"\n"
              + '9) Add Case /trace/ip-type/ipv6/trace6S/trace6/status/enable/t'
              + 'race6-data/normal/normal-opt/ipv6-next-hop;'+"\n"
              + '10) Add Leaf /trace/ip-type/ipv6/trace6S/trace6/status/enable/'
              + 'trace6-data/normal/normal-opt/ipv4-next-hop/ipv4-next-hop;'+"\n"
              + '11) Add Leaf /trace/ip-type/ipv6/trace6S/trace6/status/enable/'
              + 'trace6-data/normal/normal-opt/ipv6-next-hop/ipv6-next-hop;'
                ;
  }
  revision 2020-08-11 {
    description '1) Add Choice /trace/ip-type/ipv4/trace4S/trace4/status/enable'
              + '/common-opt/pkt-priority;'+"\n"
              + '2) Add Case  /trace/ip-type/ipv4/trace4S/trace4/status/enable/'
              + 'common-opt/pkt-priority/dscp;'+"\n"
              + '3) Add Case  /trace/ip-type/ipv4/trace4S/trace4/status/enable/'
              + 'common-opt/pkt-priority/tos;'+"\n"
              + '4) Add Leaf  /trace/ip-type/ipv4/trace4S/trace4/status/enable/'
              + 'common-opt/pkt-priority/dscp/dscp;'+"\n"
              + '5) Add Leaf  /trace/ip-type/ipv4/trace4S/trace4/status/enable/'
              + 'common-opt/pkt-priority/tos/tos; '+"\n"
              + '6) Add Choice /trace/ip-type/ipv6/trace6S/trace6/status/enable'
              + '/common-opt/pkt-priority;'+"\n"
              + '7) Add Case  /trace/ip-type/ipv6/trace6S/trace6/status/enable/'
              + 'common-opt/pkt-priority/tc;'+"\n"
              + '8) Add Case  /trace/ip-type/ipv6/trace6S/trace6/status/enable/'
              + 'common-opt/pkt-priority/dscp;'+"\n"
              + '9) Add Leaf  /trace/ip-type/ipv6/trace6S/trace6/status/enable/'
              + 'common-opt/pkt-priority/tc/tc;'+"\n"
              + '10) Add Leaf /trace/ip-type/ipv6/trace6S/trace6/status/enable/'
              + 'common-opt/pkt-priority/dscp/dscp;'
                ;
  }
  revision 2020-07-16 {
    description '1.Add feature uni-nni-trace'
                ;
  }
  revision 2020-06-23 {
    description '1 Add leaf /trace:operation/trace:trace/trace:ip-type/trace:ip'
              + 'v6/trace:trace6s/trace:trace6/trace:status/trace:enable/trace:'
              + 'trace6-data/trace:trace6-type/trace:srv6/trace:srv6/trace:dest'
              + '-type/trace:sid/trace:end-op.'
                ;
  }
  revision 2020-05-15 {
    description '1 Add operation of srv6-policy'+"\n"
              + '2 Add some leaves in notification-hop-result about srv6-policy'
                ;
  }
  revision 2020-05-11 {
    description '1) Add leaf:/state/traces/trace/segments-left'+"\n"
              + '2) Add leaf-list:/state/traces/trace/segment-list'+"\n"
              + '3) Add leaf:/notification-hop-results/trace-hop-results/trace-'
              + 'hop-result/segments-left'+"\n"
              + '4) Add leaf-list:/notification-hop-results/trace-hop-results/t'
              + 'race-hop-result/segment-list'
                ;
  }
  revision 2020-04-07 {
    description '1:Add      case:/operation/trace/ip-type/ipv4/trace4s/trace4/s'
              + 'tatus/enable/trace-data/trace4-type/vxlan/vxlan-option/underla'
              + 'y/ipv6-dynamic'+"\n"
              + '2:Add      leaf:/operation/trace/ip-type/ipv4/trace4s/trace4/s'
              + 'tatus/enable/trace-data/trace4-type/vxlan/vxlan-option/underla'
              + 'y/ipv6-dynamic/ipv6-local'+"\n"
              + '3:Add      leaf:/operation/trace/ip-type/ipv4/trace4s/trace4/s'
              + 'tatus/enable/trace-data/trace4-type/vxlan/vxlan-option/underla'
              + 'y/ipv6-dynamic/ipv6-remote'+"\n"
              + '4:Add container:/trace:operation/trace:trace-vxlan-vni,and all'
              + ' nodes under it.'+"\n"
              + '5:Add ecmp in operation/trace/ipv6/trace6s/trace6/trace6-data/'
              + 'mormal-opt'+"\n"
              + '6:Add SRv6 operation'
                ;
  }
  revision 2020-02-22 {
    description '1:/trace:operation/trace:trace/trace:trace4s/trace:trace4/trac'
              + 'e:trace-data/trace:vxlan/trace:vxlans add dst-address and vrf-'
              + 'name leaf.'+"\n"
              + '2:/trace:operation/trace:trace/trace:trace4s/trace:trace4/trac'
              + 'e:trace-data/trace:vxlan-option add source/size/ttl-mode/local'
              + '-ip/remote-ip/vxlan-interface leaf.'
                ;
  }
  revision 2019-07-10 {
    description '1:/trace:operation/trace:trace/trace:trace4s/trace:trace4/trac'
              + 'e:common-opt add pattern leaf'+"\n"
              + '2:/trace:operation/trace:trace/trace:trace6s/trace:trace6/trac'
              + 'e:common-opt add pattern leaf'
                ;
  }
  revision 2018-10-10 {
    description 'Add label-list leaf to notification-hop-results/trace-hop-resu'
              + 'lts/trace-hop-result and state/tracee/trace'
                ;
  }
  revision 2016-06-23 {
    description '1/trace:operation/trace:trace/trace:trace4s/trace:trace4/trace'
              + ':trace-data/trace:unisadd vrf-name leaf'+"\n"
              + '2 /trace:operation/trace:trace/trace:trace4s/trace:trace4/trac'
              + 'e:trace-data/trace:nnis add vrf-name leaf'
                ;
  }
  revision 2016-06-22 {
    description 'add leaf /operation/trace/trace6s/trace6/trace6-data/normal/no'
              + 'rmal-opt/dcn'
                ;
  }
  revision 2015-07-28 {
    description '1. Node notification-hop-results and state add leafes: hop-ip-'
              + 'type,label-count,label-stack1,label-stack2,label-stack3,label-'
              + 'stack4,label-stack5.'+"\n"
              + '2. Node /operation/trace/ip-type/ipv4/trace4s/trace4/status/en'
              + 'able/trace-data/trace4-type/normal/normal-opt add leaf ttl-mod'
              + 'e.'+"\n"
              + '3. NOde /operation/trace/ip-type/ipv6/trace6s/trace6/status/en'
              + 'able/trace6-data/trace6-type/normal/normal-opt add leaf ttl-mo'
              + 'de.'
                ;
  }
  revision 2015-06-08 {
    description '1.Split notification to notification-hop-results,notification-'
              + 'results.'
                ;
  }
  revision 2014-12-18 {
    description 'Add TRACE netconf notification report function.'
                ;
  }
  revision 2014-07-17 {
    description 'Initial version.'
                ;
  }
  feature vxlan ;
  feature srv6 ;
  feature uni-nni-trace {
    description 'UNI and NNI trace'
                ;
  }
  feature uni-nni-trace-ipv6 {
    description 'UNI and NNI trace IPv6'
                ;
  }
  container operation {
    config false ;
    description 'TRACE operation model info.'
                ;
    container trace {
      description 'TRACE operation parameters.'
                  ;
      presence trace ;
      choice ip-type {
        description 'The type of TRACE operation, IPV4 or IPV6.'
                    ;
        mandatory true ;
        case ipv4 {
          description 'IPv4 TRACE operation parameters.'
                      ;
          container trace4s {
            description 'IPv4 TRACE operation parameters.'
                        ;
            list trace4 {
              description 'IPv4 TRACE operation parameters.'
                          ;
              key serial-num ;
              leaf serial-num {
                description 'IPv4 TRACE serial number.'
                            ;
                type uint64 ;
              }
              choice status {
                description 'The switch for turning on/off IPv4 TRACE.'
                            ;
                mandatory true ;
                case enable {
                  description 'Start IPv4 TRACE function.'
                              ;
                  leaf trace-enable {
                    description 'Start IPv4 TRACE function.'
                                ;
                    type empty ;
                    mandatory true ;
                  }
                  container trace-data {
                    description 'Parameters for IPv4 TRACE.'
                                ;
                    choice trace4-type {
                      description 'The type of IPv4 TRACE.'
                                  ;
                      mandatory true ;
                      case normal {
                        description 'Normal IP TRACE operation.'
                                    ;
                        container normals {
                          description 'Normal IP TRACE operation.'
                                      ;
                          choice dest-type {
                            description 'The type of normal TRACE.'
                                        ;
                            mandatory true ;
                            case ip {
                              description 'The destination of TRACE is IP address.'
                                          ;
                              leaf dst-address {
                                description 'The destination IPv4 address.'
                                            ;
                                type ncd:ipv4-address ;
                                mandatory true ;
                              }
                            }
                            case domain {
                              description 'The destination of TRACE is domain name.'
                                          ;
                              leaf domain-name {
                                description 'The domain name.'
                                            ;
                                type string {
                                  length 1..128 {
                                    description 'The domain name.'
                                                ;
                                  }
                                }
                                mandatory true ;
                              }
                            }
                          }
                        }
                        container normal-opt {
                          description 'Option parameters for normal TRACE.'
                                      ;
                          choice vrf {
                            description 'The VRF type.'
                                        ;
                            case normal-vrf {
                              description 'The normal VRF.'
                                          ;
                              leaf vrf-name {
                                description 'The VRF name.'
                                            ;
                                type string {
                                  length 1..32 {
                                    description 'The VRF name.'
                                                ;
                                  }
                                }
                              }
                            }
                            case dcn-vrf {
                              description 'The DCN VRF.'
                                          ;
                              leaf dcn {
                                description 'Whether DCN VRF or not.'
                                            ;
                                type empty ;
                              }
                            }
                          }
                          leaf out-if {
                            description 'The interface of sending packets.'
                                        ;
                            type ncd:ifname {
                              length 1..31 {
                                description 'The interface of sending packets.'
                                            ;
                              }
                            }
                          }
                          leaf source {
                            description 'The source IP address of the packet.'
                                        ;
                            type ncd:ipv4-address ;
                          }
                          choice next-hop-option {
                            description 'The next hop address.'
                                        ;
                            case ipv4-next-hop {
                              description 'The next hop address.'
                                          ;
                              leaf ipv4-next-hop {
                                description 'The Ipv4 next hop address.'
                                            ;
                                type ncd:ipv4-address-none-zero ;
                              }
                            }
                            case ipv6-next-hop {
                              description 'The next hop address.'
                                          ;
                              leaf ipv6-next-hop {
                                description 'The Ipv6 next hop address.'
                                            ;
                                type ncd:ipv6-address-none-zero ;
                              }
                            }
                            ncd:revise-date 2021-03-03 ;
                          }
                          leaf size {
                            description 'The packet size.'
                                        ;
                            type int16 {
                              range 36..8192 {
                                description 'The packet size, include IP header.'
                                            ;
                              }
                            }
                            default 100 ;
                          }
                          leaf ttl-mode {
                            description 'The TTL mode.'
                                        ;
                            type enumeration {
                              enum uniform {
                                value 0 ;
                                description 'Uniform TTL mode.'
                                            ;
                              }
                              enum pipe {
                                value 1 ;
                                description 'Pipe TTL mode.'
                                            ;
                              }
                            }
                            default uniform ;
                          }
                        }
                      }
                      case uni {
                        // if-feature uni-nni-trace ;
                        description UNI-TRACE. ;
                        container unis {
                          description UNI-TRACE. ;
                          leaf dst-address {
                            description 'The destination IPv4 address.'
                                        ;
                            type ncd:ipv4-address ;
                            mandatory true ;
                          }
                          leaf vrf-name {
                            description 'The VRF name.'
                                        ;
                            type string {
                              length 1..32 {
                                description 'The VRF name.'
                                            ;
                              }
                            }
                          }
                        }
                      }
                      case nni {
                        // if-feature uni-nni-trace ;
                        description NNI-TRACE. ;
                        container nnis {
                          description NNI-TRACE. ;
                          leaf dst-address {
                            description 'The destination IPv4 address.'
                                        ;
                            type ncd:ipv4-address ;
                            mandatory true ;
                          }
                          leaf next-hop {
                            description 'The next hop address for NNI-TRACE.'
                                        ;
                            type ncd:ipv4-address ;
                            mandatory true ;
                          }
                          leaf vrf-name {
                            description 'The VRF name.'
                                        ;
                            type string {
                              length 1..32 {
                                description 'The VRF name.'
                                            ;
                              }
                            }
                          }
                        }
                      }
                      case vxlan {
                        // if-feature vxlan ;
                        description VXLAN-TRACE. ;
                        container vxlans {
                          description VXLAN-TRACE. ;
                          leaf dst-address {
                            description 'The destination IPv4 address.'
                                        ;
                            type ncd:ipv4-address ;
                            mandatory true ;
                          }
                          leaf vrf-name {
                            description 'The VRF name.'
                                        ;
                            type string {
                              length 1..32 {
                                description 'The VRF name.'
                                            ;
                              }
                            }
                          }
                        }
                        container vxlan-option {
                          description 'Optional parameters of VXLAN TRACE.'
                                      ;
                          leaf source {
                            description 'The source IP address of the packet.'
                                        ;
                            type ncd:ipv4-address ;
                          }
                          leaf size {
                            description 'The packet size.'
                                        ;
                            type int16 {
                              range 36..8192 {
                                description 'The packet size, include IP header.'
                                            ;
                              }
                            }
                            default 100 ;
                          }
                          leaf ttl-mode {
                            description 'The TTL mode.'
                                        ;
                            type enumeration {
                              enum uniform {
                                value 0 ;
                                description 'Uniform TTL mode.'
                                            ;
                              }
                              enum pipe {
                                value 1 ;
                                description 'Pipe TTL mode.'
                                            ;
                              }
                            }
                            default uniform ;
                          }
                          choice underlay {
                            description 'underlay VXLAN information.'
                                        ;
                            case dynamic {
                              description 'Dynamic VXLAN Tunnel.'
                                          ;
                              leaf local-ip {
                                description 'The local IPv4 address.'
                                            ;
                                type ncd:ipv4-address ;
                                mandatory true ;
                              }
                              leaf remote-ip {
                                description 'The remote IPv4 address.'
                                            ;
                                type ncd:ipv4-address ;
                                mandatory true ;
                              }
                            }
                            case static {
                              description 'Static VXLAN Tunnel.'
                                          ;
                              leaf vxlan-interface {
                                description 'The VXLAN interface of sending packets.'
                                            ;
                                type ncd:ifname {
                                  length 1..31 {
                                    description 'The VXLAN interface of sending packets.'
                                                ;
                                  }
                                }
                              }
                            }
                            case ipv6-dynamic {
                              description 'Dynamic VXLAN IPv6 address.'
                                          ;
                              container ipv6-dynamics {
                                description 'Dynamic VXLAN IPv6 address.'
                                            ;
                                leaf ipv6-local {
                                  description 'The local IPv6 address.'
                                              ;
                                  type ncd:ipv6-address ;
                                  mandatory true ;
                                }
                                leaf ipv6-remote {
                                  description 'The remote IPv6 address.'
                                              ;
                                  type ncd:ipv6-address ;
                                  mandatory true ;
                                }
                              }
                              ncd:revise-date 2020-04-07 ;
                            }
                          }
                        }
                        ncd:revise-date 2020-02-22 ;
                      }
                    }
                  }
                  container common-opt {
                    description 'Option parameters for IPv4 TRACE.'
                                ;
                    leaf max-ttl {
                      description 'The maximum of time to live.'
                                  ;
                      type uint8 {
                        range 1..255 {
                          description 'The maximum of time to live.'
                                      ;
                        }
                      }
                      default 30 ;
                    }
                    leaf time-out {
                      description Timeout. ;
                      type uint8 {
                        range 1..20 {
                          description Timeout. ;
                        }
                      }
                      default 3 ;
                    }
                    leaf pattern {
                      description 'The pad bytes.'
                                  ;
                      type string {
                        length 4 {
                          description 'The pattern string.'
                                      ;
                        }
                      }
                      ncd:revise-date 2019-07-10 ;
                    }
                    choice pkt-priority {
                      description 'The priority of sending packets.'
                                  ;
                      case dscp {
                        description 'Differentiated Services Code Point.'
                                    ;
                        leaf dscp {
                          description 'Differentiated Services Code Point.'
                                      ;
                          type uint8 {
                            range 0..63 {
                              description 'Differentiated Services Code Point.'
                                          ;
                            }
                          }
                        }
                      }
                      case tos {
                        description 'Type of service.'
                                    ;
                        leaf tos {
                          description 'Type of services.'
                                      ;
                          type uint8 {
                            range 0..255 {
                              description 'Type of services.'
                                          ;
                            }
                          }
                        }
                      }
                      ncd:revise-date 2020-08-11 ;
                    }
                  }
                }
                case disable {
                  description 'Stop IPv4 TRACE function.'
                              ;
                  leaf trace-disable {
                    description 'Stop IPv4 TRACE function.'
                                ;
                    type empty ;
                    mandatory true ;
                  }
                }
              }
            }
          }
        }
        case ipv6 {
          description 'IPv6 TRACE operation parameters.'
                      ;
          container trace6s {
            description 'IPv6 TRACE operation parameters.'
                        ;
            list trace6 {
              description 'IPv6 TRACE operation parameters.'
                          ;
              key serial-num ;
              leaf serial-num {
                description 'IPv6 TRACE serial number.'
                            ;
                type uint64 ;
              }
              choice status {
                description 'The switch for turning on/off IPv6 TRACE.'
                            ;
                mandatory true ;
                case enable {
                  description 'Start IPv6 TRACE function.'
                              ;
                  leaf trace6-enable {
                    description 'Start IPv6 TRACE function.'
                                ;
                    type empty ;
                    mandatory true ;
                  }
                  container trace6-data {
                    description 'Parameters for IPv6 TRACE.'
                                ;
                    choice trace6-type {
                      description 'The type of IPv6 TRACE.'
                                  ;
                      mandatory true ;
                      case normal {
                        description 'Normal IPv6 TRACE operation.'
                                    ;
                        container normals {
                          description 'Normal IPv6 TRACE operation.'
                                      ;
                          choice dest-type {
                            description 'The type of IPv6 TRACE.'
                                        ;
                            mandatory true ;
                            case ip {
                              description 'The destination of TRACE is IP address.'
                                          ;
                              leaf dst-address {
                                description 'The destination IPv6 address.'
                                            ;
                                type ncd:ipv6-address ;
                                mandatory true ;
                              }
                            }
                            case domain {
                              description 'The destination of TRACE is domain name.'
                                          ;
                              leaf domain-name {
                                description 'The domain name.'
                                            ;
                                type string {
                                  length 1..128 {
                                    description 'The domain name.'
                                                ;
                                  }
                                }
                                mandatory true ;
                              }
                            }
                          }
                        }
                        container normal-opt {
                          description 'Option parameters for normal TRACE.'
                                      ;
                          choice vrf {
                            description 'The VRF type.'
                                        ;
                            case normal-vrf {
                              description 'The normal VRF.'
                                          ;
                              leaf vrf-name {
                                description 'The VRF name.'
                                            ;
                                type string {
                                  length 1..32 {
                                    description 'The VRF name.'
                                                ;
                                  }
                                }
                              }
                            }
                            case dcn-vrf {
                              description 'The DCN VRF.'
                                          ;
                              leaf dcn {
                                description 'Whether DCN VRF or not.'
                                            ;
                                type empty ;
                              }
                            }
                          }
                          leaf size {
                            description 'The packet size.'
                                        ;
                            type int16 {
                              range 64..8192 {
                                description 'The packet size.'
                                            ;
                              }
                            }
                            default 100 ;
                          }
                          leaf interface {
                            description 'The interface of sending packets.'
                                        ;
                            type ncd:ifname {
                              length 1..31 {
                                description 'The interface of sending packets.'
                                            ;
                              }
                            }
                            ncd:revise-date 2021-03-03 ;
                          }
                          leaf source {
                            description 'The source IPv6 address of the packet.'
                                        ;
                            type ncd:ipv6-address ;
                          }
                          choice next-hop-option {
                            description 'The next hop address.'
                                        ;
                            case ipv4-next-hop {
                              description 'The next hop address.'
                                          ;
                              leaf ipv4-next-hop {
                                description 'The Ipv4 next hop address.'
                                            ;
                                type ncd:ipv4-address-none-zero ;
                              }
                            }
                            case ipv6-next-hop {
                              description 'The next hop address.'
                                          ;
                              leaf ipv6-next-hop {
                                description 'The Ipv6 next hop address.'
                                            ;
                                type ncd:ipv6-address-none-zero ;
                              }
                            }
                            ncd:revise-date 2021-03-03 ;
                          }
                          leaf ttl-mode {
                            description 'The TTL mode.'
                                        ;
                            type enumeration {
                              enum uniform {
                                value 0 ;
                                description 'Uniform TTL mode.'
                                            ;
                              }
                              enum pipe {
                                value 1 ;
                                description 'Pipe TTL mode.'
                                            ;
                              }
                            }
                            default uniform ;
                          }
                          leaf ecmp {
                            description 'Start IPv6 TRACE ECMP function.'
                                        ;
                            type empty ;
                            ncd:revise-date 2020-04-07 ;
                          }
                        }
                      }
                      case vxlan {
                        // if-feature vxlan ;
                        description VXLAN-TRACE. ;
                        container vxlans {
                          description VXLAN-TRACE. ;
                          leaf vrf-name {
                            description 'The VRF name.'
                                        ;
                            type string {
                              length 1..32 {
                                description 'The VRF name.'
                                            ;
                              }
                            }
                          }
                          leaf dst-address {
                            description 'The destination IPv6 address.'
                                        ;
                            type ncd:ipv6-address ;
                            mandatory true ;
                          }
                        }
                        container vxlan-option {
                          description 'Optional parameters of VXLAN TRACE.'
                                      ;
                          leaf source {
                            description 'The source IP address of the packet.'
                                        ;
                            type ncd:ipv6-address ;
                          }
                          leaf size {
                            description 'The packet size.'
                                        ;
                            type int16 {
                              range 36..8192 {
                                description 'The packet size, include IP header.'
                                            ;
                              }
                            }
                            default 100 ;
                          }
                          choice underlay {
                            description 'underlay VXLAN information.'
                                        ;
                            case dynamic {
                              description 'Dynamic VXLAN IPv4 address.'
                                          ;
                              container dynamics {
                                description 'Dynamic VXLAN IPv4 address.'
                                            ;
                                leaf local-ip {
                                  description 'The local IPv4 address.'
                                              ;
                                  type ncd:ipv4-address ;
                                  mandatory true ;
                                }
                                leaf remote-ip {
                                  description 'The remote IPv4 address.'
                                              ;
                                  type ncd:ipv4-address ;
                                  mandatory true ;
                                }
                              }
                            }
                            case ipv6-dynamic {
                              description 'Dynamic VXLAN IPv6 address.'
                                          ;
                              container ipv6-dynamics {
                                description 'Dynamic VXLAN IPv6 address.'
                                            ;
                                leaf ipv6-local {
                                  description 'The local IPv6 address.'
                                              ;
                                  type ncd:ipv6-address ;
                                  mandatory true ;
                                }
                                leaf ipv6-remote {
                                  description 'The remote IPv6 address.'
                                              ;
                                  type ncd:ipv6-address ;
                                  mandatory true ;
                                }
                              }
                            }
                            case static {
                              description 'Static VXLAN Tunnel.'
                                          ;
                              container statics {
                                description 'Static VXLAN Tunnel.'
                                            ;
                                leaf vxlan-interface {
                                  description 'The VXLAN interface of sending packets.'
                                              ;
                                  type ncd:ifname {
                                    length 1..31 {
                                      description 'The VXLAN interface of sending packets.'
                                                  ;
                                    }
                                  }
                                  mandatory true ;
                                }
                              }
                            }
                          }
                        }
                        ncd:revise-date 2020-04-07 ;
                      }
                      case srv6 {
                        // if-feature srv6 ;
                        description 'SRv6 TRACE.'
                                    ;
                        container srv6 {
                          description 'SRv6 TRACE.'
                                      ;
                          choice dest-type {
                            description 'The type of SRv6 TRACE.'
                                        ;
                            case sid {
                              description 'SRv6 Segment ID'
                                          ;
                              leaf sid {
                                description 'SRv6 Segment ID'
                                            ;
                                type ncd:ipv6-address-none-zero ;
                              }
                              leaf end-op {
                                description 'The END-OP SID.'
                                            ;
                                type ncd:ipv6-address-none-zero ;
                                ncd:revise-date 2020-06-23 ;
                              }
                            }
                            case tunnel {
                              description 'SRv6 tunnel ID'
                                          ;
                              leaf tunnel-id {
                                description 'SRv6 tunnel ID'
                                            ;
                                type uint16 {
                                  range 1..65535 {
                                    description 'SRv6 tunnel ID'
                                                ;
                                  }
                                }
                                mandatory true ;
                              }
                              leaf lsp-role {
                                description 'Lsp role of SRv6-TE lsp ping, include master and slave.'
                                            ;
                                type enumeration {
                                  enum master {
                                    value 1 ;
                                    description 'The master lsp of SRv6-TE.'
                                                ;
                                  }
                                  enum slave {
                                    value 2 ;
                                    description 'The slave lsp of SRv6-TE.'
                                                ;
                                  }
                                }
                              }
                            }
                          }
                        }
                        container srv6-opt {
                          description 'Optional parameters for SRv6 TRACE.'
                                      ;
                          leaf size {
                            description 'The packet size.'
                                        ;
                            type int16 {
                              range 64..8192 {
                                description 'The packet size.'
                                            ;
                              }
                            }
                            default 100 ;
                          }
                          leaf source {
                            description 'The source IPv6 address of the packet.'
                                        ;
                            type ncd:ipv6-address-none-zero ;
                          }
                        }
                        ncd:revise-date 2020-04-07 ;
                      }
                      case srv6-policy {
                        // if-feature srv6 ;
                        description 'SRv6 policy TRACE.'
                                    ;
                        container srv6-policy {
                          description 'SRv6 policy TRACE.'
                                      ;
                          choice dest-type {
                            description 'The type of SRv6 TRACE.'
                                        ;
                            mandatory true ;
                            case policy-name {
                              description 'Policy name.'
                                          ;
                              leaf policy-name {
                                description 'Policy name.'
                                            ;
                                type string {
                                  length 1..63 {
                                    description 'Policy name'
                                                ;
                                  }
                                }
                                mandatory true ;
                              }
                            }
                            case endpoint {
                              description 'SRv6 tunnel ID'
                                          ;
                              leaf endpoint {
                                description 'Endpoint IP address'
                                            ;
                                type ncd:ipv6-address-none-zero ;
                                mandatory true ;
                              }
                              leaf color {
                                description 'Color id.'
                                            ;
                                type uint32 {
                                  range 1..4294967295 {
                                    description 'Color value'
                                                ;
                                  }
                                }
                                mandatory true ;
                              }
                            }
                          }
                        }
                        container srv6-policy-opt {
                          description 'Optional parameters for SRv6 policy TRAC'
                                    + 'E.'
                                      ;
                          leaf size {
                            description 'The packet size.'
                                        ;
                            type int16 {
                              range 64..8192 {
                                description 'The packet size.'
                                            ;
                              }
                            }
                            default 100 ;
                          }
                          leaf end-op {
                            description 'The END-OP SID.'
                                        ;
                            type ncd:ipv6-address-none-zero ;
                          }
                          leaf path-type {
                            description 'Path type.'
                                        ;
                            type enumeration {
                              enum master {
                                value 0 ;
                              }
                              enum slave {
                                value 1 ;
                              }
                            }
                          }
                          leaf source {
                            description 'The source IPv6 address of the packet.'
                                        ;
                            type ncd:ipv6-address-none-zero ;
                          }
                        }
                        ncd:revise-date 2020-05-15 ;
                      }
                      case uni {
                        // if-feature uni-nni-trace-ipv6 ;
                        description 'UNI-TRACE IPv6.'
                                    ;
                        container unis {
                          description 'UNI-TRACE IPv6.'
                                      ;
                          leaf dst-address {
                            description 'The destination IPv6 address.'
                                        ;
                            type ncd:ipv6-address ;
                            mandatory true ;
                          }
                          leaf vrf-name {
                            description 'The VRF name.'
                                        ;
                            type string {
                              length 1..32 {
                                description 'The VRF name.'
                                            ;
                              }
                            }
                          }
                        }
                        ncd:revise-date 2021-03-30 ;
                      }
                      case nni {
                        // if-feature uni-nni-trace-ipv6 ;
                        description 'NNI-TRACE IPv6.'
                                    ;
                        container nnis {
                          description 'NNI-TRACE IPv6.'
                                      ;
                          leaf dst-address {
                            description 'The destination IPv6 address.'
                                        ;
                            type ncd:ipv6-address ;
                            mandatory true ;
                          }
                          leaf next-hop {
                            description 'The next hop IPv6 address for NNI-TRACE.'
                                        ;
                            type ncd:ipv6-address-none-zero ;
                            mandatory true ;
                          }
                          leaf vrf-name {
                            description 'The VRF name.'
                                        ;
                            type string {
                              length 1..32 {
                                description 'The VRF name.'
                                            ;
                              }
                            }
                          }
                        }
                        ncd:revise-date 2021-03-30 ;
                      }
                    }
                  }
                  container common-opt {
                    description 'Option parameters for IPv6 TRACE.'
                                ;
                    leaf max-ttl {
                      description 'The maximum of time to live.'
                                  ;
                      type uint8 {
                        range 1..255 {
                          description 'The maximum of time to live.'
                                      ;
                        }
                      }
                      default 30 ;
                    }
                    leaf time-out {
                      description Timeout. ;
                      type uint8 {
                        range 1..20 {
                          description Timeout. ;
                        }
                      }
                      default 3 ;
                    }
                    leaf pattern {
                      description 'The pad bytes.'
                                  ;
                      type string {
                        length 4 {
                          description 'The pattern string.'
                                      ;
                        }
                      }
                      ncd:revise-date 2019-07-10 ;
                    }
                    choice pkt-priority {
                      description 'The priority of sending packets.'
                                  ;
                      case dscp {
                        description 'Differentiated Services Code Point.'
                                    ;
                        leaf dscp {
                          description 'Differentiated Services Code Point.'
                                      ;
                          type uint8 {
                            range 0..63 {
                              description 'Differentiated Services Code Point.'
                                          ;
                            }
                          }
                        }
                      }
                      case tc {
                        description 'Traffic class.'
                                    ;
                        leaf tc {
                          description 'Traffic class.'
                                      ;
                          type uint8 {
                            range 0..255 {
                              description 'Type of services.'
                                          ;
                            }
                          }
                        }
                      }
                      ncd:revise-date 2020-08-11 ;
                    }
                  }
                }
                case disable {
                  description 'Stop IPv6 TRACE function.'
                              ;
                  leaf trace6-disable {
                    description 'Stop IPv6 TRACE function.'
                                ;
                    type empty ;
                    mandatory true ;
                  }
                }
              }
            }
          }
        }
      }
    }
    container trace-vxlan-vni {
      // if-feature vxlan ;
      description 'Send VXLAN GPE echo messages.'
                  ;
      list trace-vxlan-vnis {
        description 'Send VXLAN GPE echo messages.'
                    ;
        key serial-num ;
        leaf serial-num {
          description 'IPv4 TRACE serial number.'
                      ;
          type uint64 ;
        }
        choice status {
          description 'The switch for turning on/off IPv4 TRACE.'
                      ;
          mandatory true ;
          case enable {
            description 'Start IPv4 TRACE function.'
                        ;
            leaf trace-enable {
              description 'Start IPv4 TRACE function.'
                          ;
              type empty ;
              mandatory true ;
            }
            container trace-data {
              description 'Parameters for IPv4 TRACE.'
                          ;
              leaf vni-id {
                description 'Vxlan network ID.'
                            ;
                type uint32 {
                  range 1..16777215 {
                    description 'VNI ID'
                                ;
                  }
                }
                mandatory true ;
              }
              choice underlay {
                description 'underlay VXLAN information.'
                            ;
                mandatory true ;
                case dynamic {
                  description 'Dynamic VXLAN IPv4 address.'
                              ;
                  container dynamics {
                    description 'Dynamic VXLAN IPv4 address.'
                                ;
                    leaf local-ip {
                      description 'The local IPv4 address.'
                                  ;
                      type ncd:ipv4-address ;
                      mandatory true ;
                    }
                    leaf remote-ip {
                      description 'The remote IPv4 address.'
                                  ;
                      type ncd:ipv4-address ;
                      mandatory true ;
                    }
                  }
                }
                case ipv6-dynamic {
                  description 'Dynamic VXLAN IPv6 address.'
                              ;
                  container ipv6-dynamics {
                    description 'Dynamic VXLAN IPv6 address.'
                                ;
                    leaf ipv6-local {
                      description 'The local IPv6 address.'
                                  ;
                      type ncd:ipv6-address ;
                      mandatory true ;
                    }
                    leaf ipv6-remote {
                      description 'The remote IPv6 address.'
                                  ;
                      type ncd:ipv6-address ;
                      mandatory true ;
                    }
                  }
                }
                case static {
                  description 'Static VXLAN Tunnel.'
                              ;
                  container statics {
                    description 'Static VXLAN Tunnel.'
                                ;
                    leaf vxlan-interface {
                      description 'The VXLAN interface of sending packets.'
                                  ;
                      type ncd:ifname {
                        length 1..31 {
                          description 'The VXLAN interface of sending packets.'
                                      ;
                        }
                      }
                      mandatory true ;
                    }
                  }
                }
              }
            }
            container common-opt {
              description 'Option parameters for IPv4 TRACE.'
                          ;
              leaf max-ttl {
                description 'The maximum of time to live.'
                            ;
                type uint8 {
                  range 1..255 {
                    description 'The maximum of time to live.'
                                ;
                  }
                }
                default 30 ;
              }
              leaf time-out {
                description Timeout. ;
                type uint8 {
                  range 1..20 {
                    description Timeout. ;
                  }
                }
                default 3 ;
              }
              leaf size {
                description 'The packet size.'
                            ;
                type int16 {
                  range 36..8192 {
                    description 'The packet size, include IP header.'
                                ;
                  }
                }
                default 100 ;
              }
              leaf pattern {
                description 'The pad bytes.'
                            ;
                type string {
                  length 4 {
                    description 'The pattern string.'
                                ;
                  }
                }
              }
            }
          }
          case disable {
            description 'Stop IPv4 TRACE function.'
                        ;
            leaf trace-disable {
              description 'Stop IPv4 TRACE function.'
                          ;
              type empty ;
              mandatory true ;
            }
          }
        }
      }
      ncd:revise-date 2020-04-07 ;
    }
  }
  container state {
    config false ;
    description 'TRACE state model info.'
                ;
    container traces {
      description 'Trace state models.'
                  ;
      list trace {
        description 'The detail result information of trace.'
                    ;
        key 'serial-num hop-index probe-index'
            ;
        leaf serial-num {
          description 'Trace serial number.'
                      ;
          type uint64 ;
        }
        leaf hop-index {
          description 'The num of current hop.'
                      ;
          type uint8 ;
        }
        leaf probe-index {
          description 'The repeat count of current hop.'
                      ;
          type uint8 ;
        }
        leaf path-num {
          description 'The detect path number of current hop.'
                      ;
          type uint8 ;
        }
        leaf path-out-if {
          description 'The output interface of current path.'
                      ;
          type string ;
        }
        leaf path-next-hop {
          description 'The next hop address of current path.'
                      ;
          type string ;
        }
        leaf hop-ip-type {
          description 'The IP address type.'
                      ;
          type enumeration {
            enum unknown {
              value 0 ;
              description 'Unknown IP type.'
                          ;
            }
            enum ipv4 {
              value 1 ;
              description 'The IPv4 type.'
                          ;
            }
            enum ipv6 {
              value 2 ;
              description 'The IPv6 type.'
                          ;
            }
          }
        }
        leaf hop-address {
          description 'The address of current hop.'
                      ;
          type string ;
        }
        leaf hop-rtt {
          description 'The round trip time of current hop.'
                      ;
          type uint32 ;
          units ms ;
        }
        leaf hop-status {
          description 'The status of current hop.'
                      ;
          type enumeration {
            enum success {
              value 0 ;
            }
            enum fail {
              value 1 ;
            }
          }
        }
        leaf label-count {
          description 'The label count.'
                      ;
          type uint8 ;
        }
        leaf label-stack1 {
          description 'The first label stack.'
                      ;
          type uint32 ;
        }
        leaf label-stack2 {
          description 'The second label stack.'
                      ;
          type uint32 ;
        }
        leaf label-stack3 {
          description 'The third label stack.'
                      ;
          type uint32 ;
        }
        leaf label-stack4 {
          description 'The fourth label stack.'
                      ;
          type uint32 ;
        }
        leaf label-stack5 {
          description 'The fifth label stack.'
                      ;
          type uint32 ;
        }
        leaf label-list {
          description 'The labels of current hop.'
                      ;
          type string {
            length 1..255 ;
          }
        }
        leaf segments-left {
          description 'Segments left.'
                      ;
          type uint16 ;
          ncd:revise-date 2020-05-11 ;
        }
        leaf-list segment-list {
          description 'Segment list.'
                      ;
          type ncd:string-all {
            length 1..46 ;
          }
          ncd:revise-date 2020-05-11 ;
        }
        ncd:select serial-num ;
        ncd:select 'serial-num hop-index'
                   ;
        ncd:select 'serial-num hop-index probe-index'
                   ;
      }
    }
  }
  notification notification-hop-results {
    description 'event notification of trace hop result'
                ;
    container trace-hop-results {
      config false ;
      description 'Trace hop result'
                  ;
      list trace-hop-result {
        description 'The detail result information of trace.'
                    ;
        key 'serial-num hop-index probe-index path-num'
            ;
        leaf serial-num {
          description 'Trace serial number.'
                      ;
          type uint64 ;
        }
        leaf path-num {
          description 'The detect path number of current hop.'
                      ;
          type uint8 ;
        }
        leaf hop-index {
          description 'The num of current hop.'
                      ;
          type uint8 ;
        }
        leaf probe-index {
          description 'The repeat count of current hop.'
                      ;
          type uint8 ;
        }
        leaf segment-list-id {
          description 'Segment-List ID.'
                      ;
          type uint32 ;
          ncd:revise-date 2020-05-15 ;
        }
        leaf path-type {
          description 'Path type.'
                      ;
          type enumeration {
            enum master {
              value 0 ;
              description 'master path'
                          ;
            }
            enum slave {
              value 1 ;
              description 'Slave path'
                          ;
            }
          }
          ncd:revise-date 2020-05-15 ;
        }
        leaf protocol-origin {
          description 'Protocol origin.'
                      ;
          type enumeration {
            enum pcep {
              value 10 ;
            }
            enum bgp {
              value 20 ;
            }
            enum config {
              value 30 ;
            }
            enum unknown {
              value 0 ;
            }
          }
          ncd:revise-date 2020-05-15 ;
        }
        leaf discriminator {
          description Discriminator. ;
          type uint32 ;
          ncd:revise-date 2020-05-15 ;
        }
        leaf autonomous-system {
          description 'Autonomous System ID.'
                      ;
          type int32 ;
          ncd:revise-date 2020-05-15 ;
        }
        leaf originator-address {
          description 'Originator address.'
                      ;
          type string ;
          ncd:revise-date 2020-05-15 ;
        }
        leaf path-out-if {
          description 'The output interface of current path.'
                      ;
          type string ;
        }
        leaf path-next-hop {
          description 'The next hop address of current path.'
                      ;
          type string ;
        }
        leaf hop-ip-type {
          description 'The IP address type.'
                      ;
          type enumeration {
            enum unknown {
              value 0 ;
              description 'Unknown IP type.'
                          ;
            }
            enum ipv4 {
              value 1 ;
              description 'The IPv4 type.'
                          ;
            }
            enum ipv6 {
              value 2 ;
              description 'The IPv6 type.'
                          ;
            }
          }
        }
        leaf hop-address {
          description 'The address of current hop.'
                      ;
          type string ;
        }
        leaf hop-rtt {
          description 'The round trip time of current hop.'
                      ;
          type uint32 ;
          units ms ;
        }
        leaf hop-status {
          description 'The status of current hop.'
                      ;
          type uint8 ;
        }
        leaf label-count {
          description 'The label count.'
                      ;
          type uint8 ;
        }
        leaf label-stack1 {
          description 'The first label stack.'
                      ;
          type uint32 ;
        }
        leaf label-stack2 {
          description 'The second label stack.'
                      ;
          type uint32 ;
        }
        leaf label-stack3 {
          description 'The third label stack.'
                      ;
          type uint32 ;
        }
        leaf label-stack4 {
          description 'The fourth label stack.'
                      ;
          type uint32 ;
        }
        leaf label-stack5 {
          description 'The fifth label stack.'
                      ;
          type uint32 ;
        }
        leaf label-list {
          description 'The labels of current hop.'
                      ;
          type string {
            length 1..255 ;
          }
        }
        leaf segments-left {
          description 'Segments left.'
                      ;
          type uint16 ;
          ncd:revise-date 2020-05-11 ;
        }
        leaf-list segment-list {
          description 'Segment list.'
                      ;
          type ncd:string-all {
            length 1..46 ;
          }
          ncd:revise-date 2020-05-11 ;
        }
      }
    }
  }
  notification notification-results {
    description 'event notification of trace result'
                ;
    container trace-results {
      config false ;
      description 'Trace result'
                  ;
      list trace-result {
        config true ;
        key 'serial-num path-num'
            ;
        leaf serial-num {
          config false ;
          description 'Trace serial number.'
                      ;
          type uint64 ;
        }
        leaf path-num {
          config false ;
          description 'The detect path number of current hop.'
                      ;
          type uint8 ;
        }
        leaf hop-count {
          config false ;
          description 'The number of trace hops.'
                      ;
          type uint8 ;
        }
      }
    }
  }
}
