module zxr10-p2mp-te {
  namespace 'http://www.zte.com.cn/zxr10/netconf/schema/rosng/p2mp-te'
            ;
  prefix p2mpte ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description "The netconf model to describe the P2MP.It's full name is Point-t"
            + "o-MultiPoint (P2MP) ,The netconf model provide a mechanism :How "
            + "to build point-to-multipoint (P2MP) TE tunnels, lsps and sublsps"
            + ".sametimes,how to bind destlist."
              ;
  revision 2020-04-18 {
    description '1.Add choice /configuration/p2mp-te/templates/template/multipo'
              + 'int-bfd/detect-param'+"\n"
              + '2.Add choice /configuration/p2mp-te/mvpn-bfd/detect-param'+"\n"
              + '3.Add choice /configuration/p2mp-te/mte-tunnel/root-tunnel/bfd'
              + '/detect-param'
                ;
  }
  revision 2019-06-04 {
    description '1.Add container /configuration/p2mp-te/templates/template/prio'
              + 'rity'+"\n"
              + '2.Add leaf /configuration/p2mp-te/templates/template/bandwidth'
              + ''+"\n"
              + '3.Add leaf /configuration/p2mp-te/templates/template/crankback'
              + ''+"\n"
              + '4.Add leaf /configuration/p2mp-te/templates/template/reoptimiz'
              + 'e'
                ;
  }
  revision 2019-03-27 {
    description 'add leaf /configuration/p2mp-te/mvpn-frr-block'
                ;
  }
  revision 2019-03-14 {
    description '1.Modify leaf /configuration/p2mp-te/static-mtunnel/tunnel/lsp'
              + 's/lsp/cir.'+"\n"
              + '2.Modify leaf /configuration/p2mp-te/static-mtunnel/tunnel/lsp'
              + 's/lsp/cbs.'+"\n"
              + '3.Modify leaf /configuration/p2mp-te/static-mtunnel/tunnel/lsp'
              + 's/lsp/eir.'+"\n"
              + '4.Modify leaf /configuration/p2mp-te/static-mtunnel/tunnel/lsp'
              + 's/lsp/ebs.'+"\n"
              + '5.Modify leaf /configuration/p2mp-te/tnnl-rate-limit/tunnel/ci'
              + 'r.'+"\n"
              + '6.Modify leaf /configuration/p2mp-te/tnnl-rate-limit/tunnel/cb'
              + 's.'+"\n"
              + '7.Modify leaf /configuration/p2mp-te/tnnl-rate-limit/tunnel/pi'
              + 'r.'+"\n"
              + '8.Modify leaf /configuration/p2mp-te/tnnl-rate-limit/tunnel/pb'
              + 's.'
                ;
  }
  revision 2019-02-20 {
    description 'obsolete leaf /configuration/p2mp-te/templates/template/multip'
              + 'oint-bfd/minrx-interval'
                ;
  }
  revision 2018-12-07 {
    description '1.Add container /configuration/p2mp-te/templates/template/mult'
              + 'ipoint-bfd'
                ;
  }
  revision 2018-11-01 {
    description '1.Add leaf /configuration/p2mp-te/templates/template/escape-pa'
              + 'th'
                ;
  }
  revision 2018-03-19 {
    description '1.Add container /configuration/p2mp-te/templates'
                ;
  }
  revision 2017-05-17 {
    description '1.Add container /configuration/p2mp-te/tnnl-rate-limit'
                ;
  }
  revision 2017-02-21 {
    description '1.add container /configuration/p2mp-te/mvpn-bfd'+"\n"
              + '2.add leaf /configuration/p2mp-te/mvpn-e2e-enable'
                ;
  }
  revision 2016-09-14 {
    description '1.Add units and range for /configuration/p2mp-te/static-mtunne'
              + 'l/tunnel/lsps/lsp/cir.'+"\n"
              + '2.Add units and range for /configuration/p2mp-te/static-mtunne'
              + 'l/tunnel/lsps/lsp/cbs.'+"\n"
              + '3.Add units and range for /configuration/p2mp-te/static-mtunne'
              + 'l/tunnel/lsps/lsp/eir.'+"\n"
              + '4.Add units and range for /configuration/p2mp-te/static-mtunne'
              + 'l/tunnel/lsps/lsp/ebs.'+"\n"
              + '5.Add pattern for /configuration/p2mp-te/static-mtunnel/tunnel'
              + '/lsps/lsp/out-seg-infos/out-seg-info/next-hop.'+"\n"
              + '6.Modify the container /configuration/p2mp-te/static-mtunnel/t'
              + 'unnel/tunnel-leaf'
                ;
  }
  revision 2016-05-23 {
    description '1.Rename /configuration/p2mp-te/static-mtunnel/tunnel/leaf to '
              + '/configuration/p2mp-te/static-mtunnel/tunnel/tunnel-leaf.'
                ;
  }
  revision 2016-03-11 {
    description '1.add container /configuration/p2mp-te/static-mtunnel'+"\n"
              + '2.add conatiner /state/p2mp-te/static-mtunnel.'
                ;
  }
  revision 2016-03-07 {
    description '1.Modify the list of /state/p2mp-te/root-tunnel/tunnel.'+"\n"
              + '2.Modify the list of /state/p2mp-te/root-tunnel/lsp.'+"\n"
              + '3.Modify the list of /state/p2mp-te/root-tunnel/sub-lsp.'+"\n"
              + '4.Modify the list of /state/p2mp-te/root-tunnel/tunnel-chop.'+"\n"
              + '5.Modify the list of /state/p2mp-te/root-tunnel/tunnel-arhop.'+"\n"
              + '6.Add the notification of root-tunnel.'
                ;
  }
  revision 2016-02-04 {
    description '1.add /p2mp-te/mte-tunnel/root-tunnel/flow-statistics'+"\n"
              + '2.add /p2mp-te/mte-tunnel/leaf-tunnel/flow-statistics'
                ;
  }
  revision 2016-01-29 {
    description '1.Modify the range of /configuration/p2mp-te/mte-tunnel/root-t'
              + 'unnel/bfd/mintx-interval and /configuration/p2mp-te/mte-tunnel'
              + '/root-tunnel/bfd/minrx-interval.'
                ;
  }
  revision 2015-12-21 {
    description '1.Delete the default value of /configuration/p2mp-te/mte-tunne'
              + 'l/root-tunnel/list-type/name/list-name and /configuration/p2mp'
              + '-te/mte-tunnel/root-tunnel/list-type/name/list-id'+"\n"
              + '2.Modify the range of /configuration/p2mp-te/mte-tunnel/root-t'
              + 'unnel/list-type/name/list-name and /configuration/p2mp-te/dest'
              + 'list/name-based/name'+"\n"
              + '3.Modify the range of /configuration/p2mp-te/destip/name-based'
              + '/path-type/path-name/explicit-path-name and /configuration/p2m'
              + 'p-te/destip/id-based/path-type/path-name/explicit-path-name'
                ;
  }
  revision 2015-12-03 {
    description '1.Add the leaf of /configuration/p2mp-te/mte-tunnel/root-tunne'
              + 'l/e2e-protect and the container of/configuration/p2mp-te/mte-t'
              + 'unnel/root-tunnel/bfd.'+"\n"
              + '2.Modify the description according to the standard requirement'
              + 's.'
                ;
  }
  revision 2015-10-21 {
    description '1. update /p2mp-te/resource-manage/tunnel-dste/ selects to tun'
              + 'nel-name and class-type'
                ;
  }
  revision 2015-09-25 {
    description '1.add /p2mp-te/resource-manage/tunnel-bandwidth/bandwidth Unit'
              + 's kbps'+"\n"
              + '2.add /p2mp-te/resource-manage/tunnel-dste/bandwidth Units kbp'
              + 's'+"\n"
              + '3.add /p2mp-te/root_tunnel/lsp/bandwidth Units kbps'
                ;
  }
  revision 2015-08-26 {
    description '1.Modify the config label of state.'
                ;
  }
  revision 2015-08-25 {
    description '1.Modify the range of /configuration/p2mp-te/mte-tunnel/root-t'
              + 'unnel/tunnel-id.'+"\n"
              + '2.Modify the range of /configuration/p2mp-te/mte-tunnel/leaf-t'
              + 'unnel/tunnel-id.'+"\n"
              + '3.Modify the range of /configuration/p2mp-te/mte-tunnel/leaf-t'
              + 'unnel/list-type/root-lsr-tnnl-id.'+"\n"
              + '4.Modify the range of /state/p2mp-te/root-tunnel/tunnel/tunnel'
              + '-id.'+"\n"
              + '5.Modify the range of /state/p2mp-te/root-tunnel/lsp/tunnel-id'
              + '.'+"\n"
              + '6.Modify the range of /state/p2mp-te/root-tunnel/sub-lsp/tunne'
              + 'l-id.'+"\n"
              + '7.Modify the range of /state/p2mp-te/leaf-tunnel/tunnel/tunnel'
              + '-id.'
                ;
  }
  revision 2015-07-30 {
    description '1.Modify the type of /configuration/p2mp-te/mte-tunnel/root-tu'
              + 'nnel/tunnel-id.'+"\n"
              + '2.Modify the type of /configuration/p2mp-te/mte-tunnel/leaf-tu'
              + 'nnel/tunnel-id.'
                ;
  }
  revision 2015-07-01 {
    description '.Add the leaf of /configuration/p2mp-te/mte-tunnel/root-tunnel'
              + '/escape-path.'
                ;
  }
  revision 2015-03-05 {
    description '1.add container /p2mp-te/resource-manage'+"\n"
              + '2.add leaf /p2mp-te/mte-tunnel/root-tunnel/resv-style'+"\n"
              + '3.add /p2mp-te/mte-tunnel/root-tunnel/priority'+"\n"
              + '4.add /p2mp-te/mte-tunnel/root-tunnel/crankback'+"\n"
              + '5.add /p2mp-te/mte-tunnel/root-tunnel/reoptimize'
                ;
  }
  revision 2015-02-11 {
    description '1.Modify the type of /state/p2mp-te/root-tunnel/sub-lsp/inifna'
              + 'me and outifname,/state/p2mp-te/root-tunnel/frr/backuptunnel-i'
              + 'ndex.'+"\n"
              + '2.Modify the name of tunnel_name to tunnel-name, Modify the na'
              + 'me of setup_priority to setup-priority, Modify the name of hol'
              + 'd_priority to hold-priority.The path is /configuration/p2mp-te'
              + '/mte-tunnel/root-tunnel/tunnel-name/setup-priority and hold-pr'
              + 'iority'
                ;
  }
  revision 2014-07-02 {
    description "1.The node of state/p2mp-te/root-tunnel/tunnel/creationtime&up"
              + "time added the type's range ,The node of state/p2mp-te/root-tu"
              + "nnel/lsp/creationtime added the type's range ,The node of /sta"
              + "te/p2mp-te/root-tunnel/sub-lsp/creationtime&uptime added the t"
              + "ype's range."
                ;
  }
  revision 2014-04-15 {
    description '1.add the list of frr.'
                ;
  }
  revision 2014-04-10 {
    description '1.add the filter id of interface.&#xD;'+"\n"
              + '2.add the property of mandatory.'
                ;
  }
  revision 2014-03-06 {
    description '1.modify the range of destlist identifier.'+"\n"
              + '2.modify the length of destlist name.'
                ;
  }
  revision 2014-02-19 {
    description 'modify the range of destlist name.'+"\n"
              + 'modify the tunnel-id of lsp and sublsp.'
                ;
  }
  revision 2014-02-07 {
    description 'modify the range of root-lsr-tnnl-id and root-lsr-p2mp-id.'+"\n"
              + 'modify the type of creationtime and uptime.'+"\n"
              + 'modify the string of tunnel-name.'+"\n"
              + 'modify the range of root-lsr-ip-addr.'
                ;
  }
  revision 2014-01-08 {
    description 'Change the range of tunnel id.'
                ;
  }
  revision 2013-09-18 {
    description 'Initial version.'
                ;
  }
  container configuration {
    description 'The branch of configuration model.'
                ;
    container p2mp-te {
      description 'The configuration of P2MP TE.'
                  ;
      leaf te-enable {
        description 'The global switch of TE.'
                    ;
        type enumeration {
          enum disable {
            value 0 ;
          }
          enum enable {
            value 1 ;
          }
        }
        default disable ;
      }
      leaf mvpn-e2e-enable {
        description 'The endtoend(E2E) protect global configuration of MVPN mtu'
                  + 'nnel.'
                    ;
        type enumeration {
          enum disable {
            value 0 ;
          }
          enum enable {
            value 1 ;
          }
        }
        default disable ;
        ncd:revise-date 2017-02-21 ;
      }
      leaf mvpn-frr-block {
        description 'The fast-reroute(FRR) block global configuration of MVPN m'
                  + 'tunnel.'
                    ;
        type enumeration {
          enum disable {
            value 0 ;
          }
          enum enable {
            value 1 ;
          }
        }
        default disable ;
        ncd:revise-date 2019-03-27 ;
      }
      container mvpn-bfd {
        description 'The BFD global configuration of MVPN mtunnel.'
                    ;
        presence 'bfd of mvpn tunnel'
                 ;
        leaf enable {
          description "To enable the bfd of MVPN tunnel when it's true.And to d"
                    + "isable the bfd of MVPN tunnel when it's false."
                      ;
          type enumeration {
            enum false {
              value 0 ;
            }
            enum true {
              value 1 ;
            }
          }
          mandatory true ;
        }
        choice detect-param {
          description 'Detect param.'
                      ;
          mandatory true ;
          case template {
            description 'Bfd template name.'
                        ;
            leaf template-name {
              description 'The tunnel bfd template name.'
                          ;
              type string {
                length 1..31 ;
              }
              mandatory true ;
            }
            ncd:revise-date 2020-04-18 ;
          }
          case detect-params {
            description 'Detect params.'
                        ;
            leaf mintx-interval {
              description 'The interval of sending BFD control packets.'
                          ;
              type uint32 {
                range 3..990 ;
              }
              units ms ;
              mandatory true ;
            }
            leaf minrx-interval {
              description 'The interval of reciving BFD control packets.'
                          ;
              type uint32 {
                range 3..990 ;
              }
              units ms ;
              mandatory true ;
            }
            leaf multiplier {
              description 'The multiplier of BFD detecting interval.'
                          ;
              type uint16 {
                range 3..50 ;
              }
              mandatory true ;
            }
            ncd:revise-date 2017-02-21 ;
          }
          ncd:revise-date 2017-02-21 ;
        }
        ncd:revise-date 2017-02-21 ;
      }
      container mte-tunnel {
        description 'The configration of the P2MP TE tunnel.'
                    ;
        list root-tunnel {
          description 'The configration of root tunnel.'
                      ;
          key 'tunnel-id tunnel-name'
              ;
          leaf tunnel-id {
            description 'The index of tunnel.'
                        ;
            type uint32 {
              range 1..65535 ;
            }
          }
          leaf tunnel-name {
            description 'Tunnel name.'
                        ;
            type ncd:ifname {
              length 0..31 ;
            }
          }
          leaf integrity {
            description 'The integrity of tunnel.'
                        ;
            type enumeration {
              enum false {
                value 0 ;
              }
              enum true {
                value 1 ;
              }
            }
            default false ;
          }
          leaf record-route {
            description 'The record-route of tunnel.'
                        ;
            type enumeration {
              enum false {
                value 0 ;
              }
              enum true {
                value 1 ;
              }
            }
            default false ;
          }
          leaf resv-style {
            description 'The resv-style of tunnel.'
                        ;
            type enumeration {
              enum se {
                value 1 ;
              }
              enum ff {
                value 2 ;
              }
            }
            default se ;
          }
          leaf crankback {
            description 'The crankback mode of tunnel.'
                        ;
            type enumeration {
              enum end-to-end {
                value 1 ;
                description end-to-end ;
              }
              enum disabled {
                value 0 ;
              }
            }
            default disabled ;
          }
          leaf reoptimize {
            description 'The reoptimization of tunnel.'
                        ;
            type enumeration {
              enum false {
                value 0 ;
              }
              enum true {
                value 1 ;
              }
            }
            default false ;
          }
          leaf frr {
            description 'The frr of tunnel.'
                        ;
            type enumeration {
              enum false {
                value 0 ;
              }
              enum true {
                value 1 ;
              }
            }
            default false ;
          }
          leaf escape-path {
            description 'The escape-path of tunnel.'
                        ;
            type enumeration {
              enum disabled {
                value 0 ;
              }
              enum enabled {
                value 1 ;
              }
            }
            default disabled ;
          }
          leaf e2e-protect {
            description 'The endtoend(e2e) protection of mtunnel.'
                        ;
            type enumeration {
              enum false {
                value 0 ;
              }
              enum true {
                value 1 ;
              }
            }
            default false ;
            ncd:revise-date 2015-12-03 ;
          }
          choice list-type {
            description 'DestList Selection Type.'
                        ;
            case name {
              description 'Based on the name of the destlist selection.'
                          ;
              leaf list-name {
                description 'The related destlist name.'
                            ;
                type string {
                  length 1..16 ;
                }
              }
            }
            case id {
              description 'Id-based destlist selection.'
                          ;
              leaf list-id {
                description 'The related destlist ID.'
                            ;
                type uint16 ;
              }
            }
          }
          container priority {
            description 'The priority of tunnel.'
                        ;
            presence 'priority of this tunnel'
                     ;
            leaf setup-priority {
              description "The tunnel setup priority.This attribute can't be hi"
                        + "gher than the holding-priority.0 is the highest prio"
                        + "rity and 7 isthe lowest priority."
                          ;
              type uint8 {
                range 0..7 ;
              }
              mandatory true ;
            }
            leaf hold-priority {
              description 'The tunnel holding priority.The tunnel of lower hold'
                        + 'ing-priority will be preempted by the tunnel of high'
                        + 'er setup-priority.0 is the highest priority and 7 is'
                        + ' the lowest priority.'
                          ;
              type uint8 {
                range 0..7 ;
              }
              mandatory true ;
            }
          }
          container bfd {
            description 'The bfd of tunnel.'
                        ;
            presence 'bfd of this tunnel'
                     ;
            leaf bfd {
              description "To enable the bfd of tunnel when it's true.And to di"
                        + "sable the bfd of
\ntunnel when it's false."
                          ;
              type enumeration {
                enum false {
                  value 0 ;
                }
                enum true {
                  value 1 ;
                }
              }
              mandatory true ;
            }
            choice detect-param {
              description 'Detect param.'
                          ;
              mandatory true ;
              case template {
                description 'Bfd template name.'
                            ;
                leaf template-name {
                  description 'The tunnel bfd template name.'
                              ;
                  type string {
                    length 1..31 ;
                  }
                  mandatory true ;
                }
                ncd:revise-date 2020-04-18 ;
              }
              case detect-params {
                description 'Detect params.'
                            ;
                leaf mintx-interval {
                  description 'The interval of sending BFD control packets.'
                              ;
                  type uint32 {
                    range 3..990 ;
                  }
                  units ms ;
                  mandatory true ;
                }
                leaf minrx-interval {
                  description 'The interval of reciving BFD control packets.'
                              ;
                  type uint32 {
                    range 3..990 ;
                  }
                  units ms ;
                  mandatory true ;
                }
                leaf multiplier {
                  description 'The multiplier of BFD detecting interval.'
                              ;
                  type uint16 {
                    range 3..50 ;
                  }
                  mandatory true ;
                }
                ncd:revise-date 2015-12-03 ;
              }
              ncd:revise-date 2015-12-03 ;
            }
            ncd:revise-date 2015-12-03 ;
          }
          leaf flow-statistics {
            description 'The flow statistics of root tunnel.'
                        ;
            type enumeration {
              enum false {
                value 0 ;
              }
              enum true {
                value 1 ;
              }
            }
            default false ;
            ncd:revise-date 2016-02-04 ;
          }
          ncd:select 'tunnel-id tunnel-name'
                     ;
        }
        list leaf-tunnel {
          description 'The configration of leaf tunnel.'
                      ;
          key 'tunnel-id tunnel-name'
              ;
          leaf tunnel-id {
            description 'The index of tunnel.'
                        ;
            type uint32 {
              range 1..65535 ;
            }
          }
          leaf tunnel-name {
            description 'Tunnel name.'
                        ;
            type ncd:ifname {
              length 0..31 ;
            }
          }
          container list-type {
            description 'The container which have three leaf ,there need to con'
                      + 'fig at the sametimes.'
                        ;
            presence necessary ;
            leaf root-lsr-ip-addr {
              description 'The ip address which is bind the root tunnel.'
                          ;
              type ncd:ipv4-address {
                pattern '([1-9]|[1-9][0-9]|1[0-9][0-9]|2[0-4][0-9]|25[0-5])(.(['
                      + '0-9]|[1-9][0-9]|1[0-9][0-9]|2[0-4][0-9]|25[0-5])){3}'
                        {
                  description 'To filter the invalid address.'
                              ;
                }
              }
              mandatory true ;
            }
            leaf root-lsr-tnnl-id {
              description 'The tunnel id which is bind with root tunnel.'
                          ;
              type uint16 {
                range 1..65535 ;
              }
              mandatory true ;
            }
            leaf root-lsr-p2mp-id {
              description 'The p2mp id which is bind with root tunnel.'
                          ;
              type uint32 {
                range 1..4294967295 ;
              }
              mandatory true ;
            }
          }
          leaf flow-statistics {
            description 'The flow statistics of leaf tunnel.'
                        ;
            type enumeration {
              enum false {
                value 0 ;
              }
              enum true {
                value 1 ;
              }
            }
            default false ;
            ncd:revise-date 2016-02-04 ;
          }
          ncd:select 'tunnel-id tunnel-name'
                     ;
        }
      }
      container destlist {
        description 'The list of destination.'
                    ;
        list name-based {
          description 'Based on the name of destlist.'
                      ;
          key name ;
          leaf name {
            description 'The name of destlist.'
                        ;
            type string {
              length 1..16 ;
            }
          }
          ncd:select name ;
        }
        list id-based {
          description 'Based on the id of destlist.'
                      ;
          key id ;
          leaf id {
            description 'The id of destlist.'
                        ;
            type uint16 {
              range 1..65535 ;
            }
          }
          ncd:select id ;
        }
      }
      container destip {
        description 'Dest ip.'
                    ;
        list name-based {
          description 'Based on the name of destip.'
                      ;
          key 'name ip-addr'
              ;
          leaf name {
            description 'The name of destlist.'
                        ;
            type string {
              length 1..16 ;
            }
          }
          leaf ip-addr {
            description 'The ip address of destip.'
                        ;
            type ncd:ipv4-address ;
          }
          leaf path-option {
            description 'The attribute is the path-option.'
                        ;
            type uint16 {
              range 1..16 ;
            }
            mandatory true ;
          }
          choice path-type {
            description 'Path Selection Type.'
                        ;
            mandatory true ;
            case path-name {
              description 'Based on the name of the explicit path selection.'
                          ;
              leaf explicit-path-name {
                description 'The related explict path name.'
                            ;
                type string {
                  length 1..64 ;
                }
                mandatory true ;
              }
            }
            case path-id {
              description 'Id-based explicit path selection.'
                          ;
              leaf explicit-path-id {
                description 'The related explicit path ID.'
                            ;
                type uint16 {
                  range 1..65535 ;
                }
                mandatory true ;
              }
            }
            case dynamic {
              description 'Dynamic Path Selection.'
                          ;
              leaf dynamic {
                description 'The path type is dynamic.'
                            ;
                type empty ;
                mandatory true ;
              }
            }
          }
          ncd:select 'name ip-addr'
                     ;
        }
        list id-based {
          description 'Based on the id of destip.'
                      ;
          key 'id ip-addr'
              ;
          leaf id {
            description 'The index of destlist.'
                        ;
            type uint16 {
              range 1..65535 ;
            }
          }
          leaf ip-addr {
            description 'The ip address of destip.'
                        ;
            type ncd:ipv4-address ;
          }
          leaf path-option {
            description 'The attribute is the path-option.'
                        ;
            type uint16 {
              range 1..16 ;
            }
            mandatory true ;
          }
          choice path-type {
            description 'Path Selection Type.'
                        ;
            mandatory true ;
            case path-name {
              description 'Based on the name of the explicit path selection.'
                          ;
              leaf explicit-path-name {
                description 'The related explict path name.'
                            ;
                type string {
                  length 1..64 ;
                }
                mandatory true ;
              }
            }
            case path-id {
              description 'Id-based explicit path selection.'
                          ;
              leaf explicit-path-id {
                description 'The related explicit path ID.'
                            ;
                type uint16 {
                  range 1..65535 ;
                }
                mandatory true ;
              }
            }
            case dynamic {
              description 'Dynamic Path Selection.'
                          ;
              leaf dynamic {
                description 'The path type is dynamic.'
                            ;
                type empty ;
                mandatory true ;
              }
            }
          }
          ncd:select 'id ip-addr'
                     ;
        }
      }
      container templates {
        description 'Configuration of p2mp-template.'
                    ;
        list template {
          description 'Mte_tunnel template configuration.'
                      ;
          max-elements 1000 ;
          key name ;
          leaf name {
            description 'The name of template.'
                        ;
            type string {
              length 1..32 ;
            }
          }
          container main-dest {
            description 'Configuration destlist of p2mp-template.'
                        ;
            choice dest-type {
              description 'Destination list Type in template.'
                          ;
              case name-based {
                description 'Based on the name of the template selection.'
                            ;
                leaf dest-name {
                  description 'The related destination list name.'
                              ;
                  type string {
                    length 1..16 ;
                  }
                }
              }
              case id-based {
                description 'Based on the ID of the template selection.'
                            ;
                leaf dest-id {
                  description 'The related destination list ID.'
                              ;
                  type uint16 {
                    range 1..65535 ;
                  }
                }
              }
            }
          }
          container backup-dest {
            description 'Configuration e2e-protect destlist of p2mp-template.'
                        ;
            choice dest-type {
              description 'Destination list Type in template.'
                          ;
              case name-based {
                description 'Based on the name of the template selection.'
                            ;
                leaf dest-name {
                  description 'The related destination list name.'
                              ;
                  type string {
                    length 1..16 ;
                  }
                }
              }
              case id-based {
                description 'Based on the ID of the template selection.'
                            ;
                leaf dest-id {
                  description 'The related destination list ID.'
                              ;
                  type uint16 {
                    range 1..65535 ;
                  }
                }
              }
            }
          }
          container multipoint-bfd {
            description 'The multipoint BFD of template.'
                        ;
            presence 'multipoint-bfd of this template'
                     ;
            leaf enable {
              description "To enable the multipoint bfd of template when it's t"
                        + "rue.And to disable the multipoint bfd of template wh"
                        + "en it's false."
                          ;
              type enumeration {
                enum false {
                  value 0 ;
                }
                enum true {
                  value 1 ;
                }
              }
              mandatory true ;
            }
            choice detect-param {
              description 'Detect param.'
                          ;
              mandatory true ;
              case template {
                description 'Bfd template name.'
                            ;
                leaf template-name {
                  description 'The tunnel bfd template name.'
                              ;
                  type string {
                    length 1..31 ;
                  }
                  mandatory true ;
                }
                ncd:revise-date 2020-04-18 ;
              }
              case detect-params {
                description 'Detect params.'
                            ;
                leaf mintx-interval {
                  description 'The interval of sending BFD control packets.'
                              ;
                  type uint32 {
                    range 3..990 ;
                  }
                  units ms ;
                  mandatory true ;
                }
                leaf minrx-interval {
                  status obsolete {
                    ncd:revise-date 2019-02-20 ;
                  }
                  description 'The interval of reciving BFD control packets.'
                              ;
                  type uint32 {
                    range 3..990 ;
                  }
                  units ms ;
                  mandatory true ;
                }
                leaf multiplier {
                  description 'The multiplier of BFD detecting interval.'
                              ;
                  type uint16 {
                    range 3..50 ;
                  }
                  mandatory true ;
                }
                ncd:revise-date 2018-12-07 ;
              }
              ncd:revise-date 2018-12-07 ;
            }
            ncd:revise-date 2018-12-07 ;
          }
          leaf escape-path {
            description 'The escape-path of template.'
                        ;
            type enumeration {
              enum disabled {
                value 0 ;
              }
              enum enabled {
                value 1 ;
              }
            }
            default disabled ;
            ncd:revise-date 2018-11-01 ;
          }
          container priority {
            description 'The priority of tunnel.'
                        ;
            presence 'priority of this tunnel'
                     ;
            leaf setup-priority {
              description "The tunnel setup priority.This attribute can't be hi"
                        + "gher than the holding-priority.0 is the highest prio"
                        + "rity and 7 isthe lowest priority."
                          ;
              type uint8 {
                range 0..7 ;
              }
              mandatory true ;
            }
            leaf hold-priority {
              description 'The tunnel holding priority.The tunnel of lower hold'
                        + 'ing-priority will be preempted by the tunnel of high'
                        + 'er setup-priority.0 is the highest priority and 7 is'
                        + ' the lowest priority.'
                          ;
              type uint8 {
                range 0..7 ;
              }
              mandatory true ;
            }
            ncd:revise-date 2019-06-04 ;
          }
          leaf bandwidth {
            description 'The bandwidth of tunnel.'
                        ;
            type uint32 {
              range 1..4294967295 ;
            }
            units kbps ;
            ncd:revise-date 2019-06-04 ;
          }
          leaf crankback {
            description 'The crankback mode of tunnel.'
                        ;
            type enumeration {
              enum end-to-end {
                value 1 ;
                description end-to-end ;
              }
              enum disabled {
                value 0 ;
              }
            }
            default disabled ;
            ncd:revise-date 2019-06-04 ;
          }
          leaf reoptimize {
            description 'The reoptimization of tunnel.'
                        ;
            type enumeration {
              enum false {
                value 0 ;
              }
              enum true {
                value 1 ;
              }
            }
            default false ;
            ncd:revise-date 2019-06-04 ;
          }
        }
        ncd:revise-date 2018-03-19 ;
      }
      container resource-manage {
        list tunnel-bandwidth {
          description 'The bandwidth of tunnel.'
                      ;
          key tunnel-name ;
          leaf tunnel-name {
            description 'Tunnel name.'
                        ;
            type string {
              length 0..31 ;
            }
          }
          leaf bandwidth {
            description 'The bandwidth of tunnel.'
                        ;
            type uint32 {
              range 1..4294967295 ;
            }
            units kbps ;
            mandatory true ;
          }
          ncd:select tunnel-name ;
        }
        list tunnel-dste {
          description 'The DS-TE bandwidth of tunnel.'
                      ;
          key 'tunnel-name class-type'
              ;
          leaf tunnel-name {
            description 'Tunnel name.'
                        ;
            type string {
              length 0..31 ;
            }
          }
          leaf class-type {
            description 'The class-type of tunnel ds-te bandwidth.'
                        ;
            type uint8 {
              range 0..7 ;
            }
          }
          leaf bandwidth {
            description 'The ds-te bandwidth of tunnel.'
                        ;
            type uint32 {
              range 1..4294967295 ;
            }
            units kbps ;
            mandatory true ;
          }
          ncd:select 'tunnel-name class-type'
                     ;
        }
      }
      container static-mtunnel {
        description 'The configration of the static P2MP tunnel.'
                    ;
        presence 'static mtunnel'
                 ;
        list tunnel {
          description 'The static P2MP tunnel list.'
                      ;
          key 'tunnel-name tunnel-id'
              ;
          leaf tunnel-name {
            description 'The static p2mp tunnel name.'
                        ;
            type ncd:ifname ;
          }
          leaf tunnel-id {
            description 'The tunnel id of the static p2mp tunnel.'
                        ;
            type uint32 ;
          }
          leaf tunnel-enable {
            description 'If this node is true, then activate the tunnel.'
                        ;
            type enumeration {
              enum true {
                value 1 ;
              }
              enum false {
                value 2 ;
              }
            }
            default true ;
          }
          leaf role-type {
            description 'The role-type of static p2mp tunnel.'
                        ;
            type enumeration {
              enum root {
                value 1 ;
              }
              enum unroot {
                value 2 ;
              }
            }
          }
          container tunnel-leaf {
            description 'The leaf node object of static p2mp tunnel.'
                        ;
            presence tunnel-leaf ;
            leaf enable {
              description 'The flag to indicate whether leaf is enabled.'
                          ;
              type enumeration {
                enum true {
                  value 1 ;
                }
              }
              mandatory true ;
            }
            ncd:revise-date 2016-05-23 ;
          }
          container lsps {
            description 'The configured lsp of static p2mp tunnel.'
                        ;
            list lsp {
              description 'Lsp list.'
                          ;
              key lsp-id ;
              leaf lsp-id {
                description "The tunnel's lsp ID."
                            ;
                type uint16 {
                  range 1 ;
                }
              }
              container out-seg-infos {
                description 'The out-seg-info list.'
                            ;
                presence out-seg-infos ;
                list out-seg-info {
                  description 'The out-seg-info of static p2mp tunnel.'
                              ;
                  key out-seg-id ;
                  leaf out-seg-id {
                    description 'The out-seg-id of the out-seg-info.'
                                ;
                    type uint16 {
                      range 1..32 ;
                    }
                  }
                  leaf out-port {
                    description 'The out-port.This attribute must be configured'
                              + ' with outlabel at the same time.'
                                ;
                    type ncd:ifname ;
                    mandatory true ;
                  }
                  leaf out-label {
                    description 'The out-label.This attribute must be configure'
                              + 'd with outport at the same time.'
                                ;
                    type uint32 {
                      range 16..1048575 ;
                    }
                    mandatory true ;
                  }
                  leaf next-hop {
                    description 'The next-hop.'
                                ;
                    type ncd:ipv4-address {
                      pattern '([1-9]|[1-9][0-9]|1[0-9][0-9]|2[0-4][0-9]|25[0-5'
                            + '])(.([0-9]|[1-9][0-9]|1[0-9][0-9]|2[0-4][0-9]|25'
                            + '[0-5])){3}'
                              ;
                    }
                  }
                }
              }
              container in-seg-info {
                description 'The in-seg-info of static p2mp tunnel.'
                            ;
                presence in-seg-info ;
                leaf in-port {
                  description 'The in-port.This attribute must be configured wi'
                            + 'th inlabel at the same time.'
                              ;
                  type ncd:ifname ;
                  mandatory true ;
                }
                leaf in-label {
                  description 'The in-label. This attribute must be configured '
                            + 'with inport at the same time.'
                              ;
                  type uint32 {
                    range 16..1048575 ;
                  }
                  mandatory true ;
                }
              }
              leaf cir {
                description CIR. ;
                type uint32 {
                  range 1..4294967295 {
                    description 'The minimum value may be greater than 1, and t'
                              + 'he maximum value may be less than 4294967295, '
                              + 'depending on the system.'
                                ;
                  }
                }
                units kbps ;
              }
              leaf cbs {
                description CBS. ;
                type uint32 {
                  range 1..4294967295 {
                    description 'The minimum value may be greater than 1, and t'
                              + 'he maximum value may be less than 4294967295, '
                              + 'depending on the system.'
                                ;
                  }
                }
                units byte ;
              }
              leaf eir {
                description EIR. ;
                type uint32 {
                  range 1..4294967295 {
                    description 'The minimum value may be greater than 1, and t'
                              + 'he maximum value may be less than 4294967295, '
                              + 'depending on the system.'
                                ;
                  }
                }
                units kbps ;
              }
              leaf ebs {
                description EBS. ;
                type uint32 {
                  range 1..4294967295 {
                    description 'The minimum value may be greater than 1, and t'
                              + 'he maximum value may be less than 4294967295, '
                              + 'depending on the system.'
                                ;
                  }
                }
                units byte ;
              }
            }
          }
        }
        ncd:revise-date 2016-03-11 ;
      }
      container tnnl-rate-limit {
        description 'The configuration of tunnel rate limit.'
                    ;
        presence 'configuration of tnnl-rate-limit'
                 ;
        list tunnel {
          description 'The tunnel rate limit list.'
                      ;
          max-elements 65535 ;
          key name ;
          leaf name {
            description 'The tunnel name.'
                        ;
            type ncd:ifname ;
          }
          leaf mode {
            description 'The tunnel rate limit mode.'
                        ;
            type enumeration {
              enum blind {
                value 1 ;
              }
              enum aware {
                value 2 ;
              }
            }
            mandatory true ;
          }
          leaf cir {
            description CIR. ;
            type uint32 {
              range 0..4294967295 {
                description 'The maximum value may be less than 4294967295, dep'
                          + 'ending on the system.'
                            ;
              }
            }
            units kbps ;
            mandatory true ;
          }
          leaf cbs {
            description CBS. ;
            type uint32 {
              range 1..4294967295 {
                description 'The minimum value may be greater than 1, and the m'
                          + 'aximum value may be less than 4294967295, dependin'
                          + 'g on the system.'
                            ;
              }
            }
            units KB ;
            mandatory true ;
          }
          leaf pir {
            description "PIR.PIR can't be smaller than CIR."
                        ;
            type uint32 {
              range 1..4294967295 {
                description 'The minimum value may be greater than 1, and the m'
                          + 'aximum value may be less than 4294967295, dependin'
                          + 'g on the system.'
                            ;
              }
            }
            units kbps ;
            mandatory true ;
          }
          leaf pbs {
            description PBS. ;
            type uint32 {
              range 1..4294967295 {
                description 'The minimum value may be greater than 1, and the m'
                          + 'aximum value may be less than 4294967295, dependin'
                          + 'g on the system.'
                            ;
              }
            }
            units KB ;
            mandatory true ;
          }
          leaf red_action {
            description 'The action of message handling.'
                        ;
            type enumeration {
              enum discard {
                value 1 ;
              }
              enum forward {
                value 2 ;
              }
            }
          }
        }
        ncd:revise-date 2017-05-17 ;
      }
    }
  }
  container state {
    config false ;
    description 'The branch of dynamic data model.'
                ;
    container p2mp-te {
      description 'The state of p2mp-te.'
                  ;
      container root-tunnel {
        description 'The state of root tunnel.'
                    ;
        list tunnel {
          description 'Root tunnel.'
                      ;
          key tunnelid ;
          leaf tunnelid {
            description 'The index of tunnel.'
                        ;
            type uint16 {
              range 1..65535 ;
            }
            ncd:revise-date 2016-03-07 ;
          }
          leaf p2mpid {
            description 'The p2mp id of tunnel.'
                        ;
            type uint32 ;
            ncd:revise-date 2016-03-07 ;
          }
          leaf ingressid {
            description 'The ingress id of tunnel.'
                        ;
            type ncd:ipv4-address ;
            ncd:revise-date 2016-03-07 ;
          }
          leaf integrity {
            description 'The integrity of tunnel.'
                        ;
            type enumeration {
              enum false {
                value 0 ;
              }
              enum true {
                value 1 ;
              }
            }
            ncd:revise-date 2016-03-07 ;
          }
          leaf mbb-lspid {
            description 'The lsp id of mbb(make before break).'
                        ;
            type uint16 ;
            ncd:revise-date 2016-03-07 ;
          }
          leaf inuse-lspid {
            description 'The lsp id in use.'
                        ;
            type uint16 ;
            ncd:revise-date 2016-03-07 ;
          }
          leaf creationtime {
            description 'The creationtime of tunnel.'
                        ;
            type ncd:string-with-blank {
              length 1..31 ;
            }
          }
          leaf uptime {
            description 'The uptime of tunnel.'
                        ;
            type ncd:string-with-blank {
              length 1..31 ;
            }
          }
          leaf operstatus {
            description 'The operstatus of tunnel.'
                        ;
            type enumeration {
              enum down {
                value 0 ;
              }
              enum up {
                value 1 ;
              }
            }
          }
          leaf adminstatus {
            description 'The adminstatus of tunnel.'
                        ;
            type enumeration {
              enum down {
                value 0 ;
              }
              enum up {
                value 1 ;
              }
            }
          }
        }
        list lsp {
          description 'The lsp of tunnel.'
                      ;
          key 'tunnelid lspid'
              ;
          leaf tunnelid {
            description 'The index of tunnel.'
                        ;
            type uint16 {
              range 1..65535 ;
            }
            ncd:revise-date 2016-03-07 ;
          }
          leaf lspid {
            description 'The lsp id of tunnel.'
                        ;
            type uint16 ;
            ncd:revise-date 2016-03-07 ;
          }
          leaf role {
            description 'The role of lsp.'
                        ;
            type enumeration {
              enum inuse {
                value 0 ;
              }
              enum inuse_active {
                value 1 ;
              }
              enum old {
                value 2 ;
              }
            }
            ncd:revise-date 2016-03-07 ;
          }
          leaf bandwidth {
            description 'The bandwidth of lsp.'
                        ;
            type uint32 ;
            units kpbs ;
            ncd:revise-date 2016-03-07 ;
          }
          leaf rro {
            description 'The record-route of lsp.'
                        ;
            type enumeration {
              enum false {
                value 0 ;
              }
              enum true {
                value 1 ;
              }
            }
            ncd:revise-date 2016-03-07 ;
          }
          leaf setupprio {
            description 'The setupprio of root tunnel.'
                        ;
            type uint16 {
              range 0..7 ;
            }
          }
          leaf holdprio {
            description 'The holdprio of root tunnel.'
                        ;
            type uint16 {
              range 0..7 ;
            }
          }
          leaf creationtime {
            description 'The creationtime of tunnel.'
                        ;
            type ncd:string-with-blank {
              length 1..31 ;
            }
          }
          leaf uptime {
            description 'The uptime of tunnel.'
                        ;
            type ncd:string-with-blank {
              length 1..31 ;
            }
            ncd:revise-date 2016-03-07 ;
          }
          leaf operstatus {
            description 'The operstatus of tunnel.'
                        ;
            type enumeration {
              enum down {
                value 0 ;
              }
              enum up {
                value 1 ;
              }
            }
          }
        }
        list sub-lsp {
          description 'The sublsp of tunnel.'
                      ;
          key 'tunnelid lspid destaddr'
              ;
          leaf tunnelid {
            description 'The index of tunnel.'
                        ;
            type uint16 {
              range 1..65535 ;
            }
            ncd:revise-date 2016-03-07 ;
          }
          leaf lspid {
            description 'The lsp id of tunnel.'
                        ;
            type uint16 ;
            ncd:revise-date 2016-03-07 ;
          }
          leaf destaddr {
            description 'The destination address of the tunnel sublsp.'
                        ;
            type ncd:ipv4-address ;
          }
          leaf outlabel {
            description 'The outlabel of sublsp.'
                        ;
            type uint32 ;
          }
          leaf outifname {
            description 'The out interface of sublsp.'
                        ;
            type string {
              length 0..32 ;
            }
          }
          leaf chopindex {
            description 'The chop index of sublsp.'
                        ;
            type uint32 ;
          }
          leaf arhopindex {
            description 'The arhop index of sublsp.'
                        ;
            type uint32 ;
          }
          leaf creationtime {
            description 'The creationtime of sublsp.'
                        ;
            type ncd:string-with-blank {
              length 1..31 ;
            }
          }
          leaf uptime {
            description 'The uptime of sublsp.'
                        ;
            type ncd:string-with-blank {
              length 1..31 ;
            }
          }
          leaf operstatus {
            description 'The operstatus of sublsp.'
                        ;
            type enumeration {
              enum down {
                value 0 ;
              }
              enum up {
                value 1 ;
              }
            }
          }
        }
        list tunnel-chop {
          description 'The tunnel ero,it is the path-compute result of route.'
                      ;
          key 'list-index index'
              ;
          leaf list-index {
            description 'The table index of chop.'
                        ;
            type uint32 ;
          }
          leaf index {
            description 'The index of ero hop.'
                        ;
            type uint32 ;
          }
          leaf addrtype {
            description 'The hop address type.'
                        ;
            type enumeration {
              enum ipv4 {
                value 1 ;
              }
              enum ipv6 {
                value 2 ;
              }
            }
          }
          leaf ipaddr {
            description 'The ip address of hop.'
                        ;
            type ncd:ipv4-address ;
          }
          leaf ip-prefixlen {
            description 'The prefix length of ip address.'
                        ;
            type uint32 ;
            ncd:revise-date 2016-03-07 ;
          }
          leaf choptype {
            description 'The hop type.'
                        ;
            type enumeration {
              enum strict {
                value 1 ;
              }
              enum loose {
                value 2 ;
              }
            }
          }
        }
        list tunnel-arhop {
          description 'The tunnel rro hop,It records the bypassed path informat'
                    + 'ion of tunnel.'
                      ;
          key 'list-index index'
              ;
          leaf list-index {
            description 'The table index of arhop.'
                        ;
            type uint32 ;
          }
          leaf index {
            description 'The hop index of rro.'
                        ;
            type uint32 ;
          }
          leaf addrtype {
            description 'The address type.'
                        ;
            type enumeration {
              enum ipv4 {
                value 1 ;
              }
              enum ipv6 {
                value 2 ;
              }
            }
          }
          leaf lsr-id {
            description routerid. ;
            type ncd:ipv4-address ;
            ncd:revise-date 2016-03-07 ;
          }
          leaf ip-prefixlen {
            description 'The prefix length of ip address.'
                        ;
            type uint32 ;
            ncd:revise-date 2016-03-07 ;
          }
          leaf in-ifaddr {
            description 'The address of in interface.'
                        ;
            type ncd:ipv4-address ;
            ncd:revise-date 2016-03-07 ;
          }
          leaf out-ifaddr {
            description 'The address of out interface.'
                        ;
            type ncd:ipv4-address ;
            ncd:revise-date 2016-03-07 ;
          }
          leaf path-inlabel {
            description 'The inlabel of path.'
                        ;
            type uint32 ;
            ncd:revise-date 2016-03-07 ;
          }
          leaf path-outlabel {
            description 'The outlabel of path.'
                        ;
            type uint32 ;
            ncd:revise-date 2016-03-07 ;
          }
        }
        list frr {
          description 'The frr information of tunnel.'
                      ;
          key 'protected-if-index pritunnel-index pritunnel-p2mpId pritunnel-in'
            + 'gressid pritunnel-lspid pritunnel-prevhop pritunnel-nexthop'
              ;
          leaf protected-if-index {
            description 'The index of the protected interface.'
                        ;
            type uint32 ;
          }
          leaf pritunnel-index {
            description 'The index of the primary tunnel.'
                        ;
            type uint16 ;
          }
          leaf pritunnel-p2mpId {
            description 'The p2mpid of the primary tunnel.'
                        ;
            type uint32 ;
          }
          leaf pritunnel-ingressid {
            description 'The ingressid of the primary tunnel.'
                        ;
            type ncd:ipv4-address ;
          }
          leaf pritunnel-lspid {
            description 'The lspid of the primary tunnel.'
                        ;
            type uint16 ;
          }
          leaf pritunnel-prevhop {
            description 'The prevhop of the primary tunnel.'
                        ;
            type ncd:ipv4-address ;
          }
          leaf pritunnel-nexthop {
            description 'The nexthop of the primary tunnel.'
                        ;
            type ncd:ipv4-address ;
          }
          leaf backuptunnel-index {
            description 'The index of backup tunnel.'
                        ;
            type uint16 ;
          }
          leaf protected-ifname {
            description 'The name of protected interface.'
                        ;
            type string {
              length 0..32 ;
            }
          }
          leaf inner-label {
            description 'Inner lable.'
                        ;
            type uint32 ;
          }
          leaf frrstatus {
            description 'The status of frr.'
                        ;
            type enumeration {
              enum ready {
                value 1 ;
              }
              enum active {
                value 2 ;
              }
            }
          }
          ncd:select 'protected-if-index pritunnel-index pritunnel-p2mpId pritu'
                   + 'nnel-ingressid pritunnel-lspid pritunnel-prevhop pritunne'
                   + 'l-nexthop'
                     ;
        }
      }
      container leaf-tunnel {
        description 'The state of leaf tunnel.'
                    ;
        list tunnel {
          description 'Leaf tunnel.'
                      ;
          key tunnel-id ;
          leaf tunnel-id {
            description 'The index of leaf tunnel.'
                        ;
            type uint16 {
              range 1..65535 ;
            }
          }
          leaf tnnl-name {
            description 'The name of tunnel.'
                        ;
            type ncd:ifname ;
            default null ;
          }
          leaf operstatus {
            description 'The operstatus of tunnel.'
                        ;
            type enumeration {
              enum down {
                value 0 ;
              }
              enum up {
                value 1 ;
              }
            }
            default down ;
          }
        }
      }
      container static-mtunnel {
        description 'The state of the static P2MP tunnel.'
                    ;
        list tunnel {
          description 'The static P2MP tunnel list.'
                      ;
          key tunnel-id ;
          leaf tunnel-id {
            description 'The tunnel id of the static p2mp tunnel.'
                        ;
            type uint32 ;
          }
          leaf admin_status {
            description 'The adminstatus of tunnel.'
                        ;
            type enumeration {
              enum down {
                value 1 ;
              }
              enum up {
                value 0 ;
              }
            }
          }
          leaf oper_status {
            description 'The operstatus of tunnel.'
                        ;
            type enumeration {
              enum down {
                value 1 ;
              }
              enum up {
                value 0 ;
              }
            }
          }
        }
        ncd:revise-date 2016-03-11 ;
      }
    }
  }
  notification root-tunnel {
    description 'The notification of root tunnel.'
                ;
    list tunnel {
      description 'Root tunnel.'
                  ;
      key tunnelid ;
      leaf tunnelid {
        description 'The index of tunnel.'
                    ;
        type uint16 ;
      }
      leaf p2mpid {
        description 'The p2mp id of tunnel.'
                    ;
        type uint32 ;
      }
      leaf ingressid {
        description 'The ingress id of tunnel.'
                    ;
        type ncd:ipv4-address ;
      }
      leaf integrity {
        description 'The integrity of tunnel.'
                    ;
        type enumeration {
          enum false {
            value 0 ;
          }
          enum true {
            value 1 ;
          }
        }
      }
      leaf mbb-lspid {
        description 'The lsp id in mbb.'
                    ;
        type uint16 ;
      }
      leaf inuse-lspid {
        description 'The lsp id in use.'
                    ;
        type uint16 ;
      }
      leaf creationtime {
        description 'The creationtime of tunnel.'
                    ;
        type ncd:string-with-blank {
          length 1..31 ;
        }
      }
      leaf uptime {
        description 'The uptime of tunnel.'
                    ;
        type ncd:string-with-blank {
          length 1..31 ;
        }
      }
      leaf operstatus {
        description 'The operstatus of tunnel.'
                    ;
        type enumeration {
          enum down {
            value 0 ;
          }
          enum up {
            value 1 ;
          }
        }
      }
      leaf adminstatus {
        description 'The adminstatus of tunnel.'
                    ;
        type enumeration {
          enum down {
            value 0 ;
          }
          enum up {
            value 1 ;
          }
        }
      }
    }
    list lsp {
      description 'The lsp list of tunnel.'
                  ;
      key 'tunnelid lspid'
          ;
      leaf tunnelid {
        description 'The index of tunnel.'
                    ;
        type uint16 ;
      }
      leaf lspid {
        description 'The lspid of tunnel.'
                    ;
        type uint16 ;
      }
      leaf role {
        description 'The role of lsp.'
                    ;
        type enumeration {
          enum inuse {
            value 0 ;
          }
          enum inuse_active {
            value 1 ;
          }
          enum old {
            value 2 ;
          }
        }
      }
      leaf bandwidth {
        description 'The bandwith of lsp.'
                    ;
        type uint32 ;
        units kpbs ;
      }
      leaf rro {
        description 'The record-route of lsp.'
                    ;
        type enumeration {
          enum false {
            value 0 ;
          }
          enum true {
            value 1 ;
          }
        }
      }
      leaf setupprio {
        description 'The setupprio of root tunnel.'
                    ;
        type uint16 ;
      }
      leaf holdprio {
        description 'The holdprio of root tunnel.'
                    ;
        type uint16 ;
      }
      leaf creationtime {
        description 'The creationtime of tunnel.'
                    ;
        type ncd:string-with-blank {
          length 1..31 ;
        }
      }
      leaf uptime {
        description 'The uptime of tunnel.'
                    ;
        type ncd:string-with-blank {
          length 1..31 ;
        }
      }
      leaf operstatus {
        description 'The operstatus of tunnel.'
                    ;
        type enumeration {
          enum down {
            value 0 ;
          }
          enum up {
            value 1 ;
          }
        }
      }
    }
    list sub-lsp {
      description 'The sublsp of tunnel.'
                  ;
      key 'tunnelid lspid destaddr'
          ;
      leaf tunnelid {
        description 'The index of tunnel.'
                    ;
        type uint16 ;
      }
      leaf lspid {
        description 'The lsp id of tunnel.'
                    ;
        type uint16 ;
      }
      leaf destaddr {
        description 'The destaddr of the tunnel sublsp.'
                    ;
        type ncd:ipv4-address ;
      }
      leaf outlabel {
        description 'The outlabel of sublsp.'
                    ;
        type uint32 ;
      }
      leaf outifname {
        description 'The out interface of sublsp.'
                    ;
        type string ;
      }
      leaf chopindex {
        description 'The chop index of sublsp.'
                    ;
        type uint32 ;
      }
      leaf arhopindex {
        description 'The arhop index of sublsp.'
                    ;
        type uint32 ;
      }
      leaf creationtime {
        description 'The creationtime of sublsp.'
                    ;
        type ncd:string-with-blank {
          length 1..31 ;
        }
      }
      leaf uptime {
        description 'The uptime of sublsp.'
                    ;
        type ncd:string-with-blank {
          length 1..31 ;
        }
      }
      leaf operstatus {
        description 'The operstatus of sublsp.'
                    ;
        type enumeration {
          enum down {
            value 0 ;
          }
          enum up {
            value 1 ;
          }
        }
      }
    }
    list tunnel-chop {
      description 'The tunnel ero,it is the path-compute result of route.'
                  ;
      key 'list-index index'
          ;
      leaf list-index {
        description 'The table index of chop.'
                    ;
        type uint32 ;
      }
      leaf index {
        description 'The index of ero hop.'
                    ;
        type uint32 ;
      }
      leaf addrtype {
        description 'The hop address type.'
                    ;
        type enumeration {
          enum ipv4 {
            value 1 ;
          }
          enum ipv6 {
            value 2 ;
          }
        }
      }
      leaf ipaddr {
        description 'The ip address of hop.'
                    ;
        type ncd:ipv4-address ;
      }
      leaf ip-prefixlen {
        description 'The prefix length of ip address.'
                    ;
        type uint32 ;
      }
      leaf choptype {
        description 'The hop type.'
                    ;
        type enumeration {
          enum strict {
            value 1 ;
          }
          enum loose {
            value 2 ;
          }
        }
      }
    }
    list tunnel-arhop {
      description 'The tunnel rro hop,It records the bypassed path information '
                + 'of tunnel.'
                  ;
      key 'list-index index'
          ;
      leaf list-index {
        description 'The table index of arhop.'
                    ;
        type uint32 ;
      }
      leaf index {
        description 'The hop index of rro.'
                    ;
        type uint32 ;
      }
      leaf addrtype {
        description 'The address type.'
                    ;
        type enumeration {
          enum ipv4 {
            value 1 ;
          }
          enum ipv6 {
            value 2 ;
          }
        }
      }
      leaf lsr-id {
        description routerid. ;
        type ncd:ipv4-address ;
      }
      leaf ip-prefixlen {
        description 'The prefix length of ip address.'
                    ;
        type uint32 ;
      }
      leaf in-ifaddr {
        description 'The address of in interface.'
                    ;
        type ncd:ipv4-address ;
      }
      leaf out-ifaddr {
        description 'The address of out interface.'
                    ;
        type ncd:ipv4-address ;
      }
      leaf path-inlabel {
        description 'The inlabel of path.'
                    ;
        type uint32 ;
      }
      leaf path-outlabel {
        description 'The outlabel of path.'
                    ;
        type uint32 ;
      }
    }
  }
}
