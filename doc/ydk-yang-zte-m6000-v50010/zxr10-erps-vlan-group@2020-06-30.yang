module zxr10-erps-vlan-group {
  namespace 'http://www.zte.com.cn/zxr10/netconf/schema/rosng/erps-vlan-group'
            ;
  prefix erps-vlan-group ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe the ERPS(Ethernet Ring Protection'
            + ' Switching) group.'
              ;
  revision 2020-06-30 {
    description '1.Create the ERPS(Ethernet Ring Protection Switching)VLAN grou'
              + 'p netconf model.'
                ;
  }
  typedef erps-group-port-role {
    type enumeration {
      enum rpl-normal {
        value 0 ;
        description 'RPL normal port.'
                    ;
      }
      enum rpl-owner {
        value 1 ;
        description 'RPL owner port.'
                    ;
      }
      enum rpl-neighbour {
        value 2 ;
        description 'RPL neighbour port.'
                    ;
      }
    }
    description 'Port role of ERPS VLAN group.'
                ;
  }
  container configuration {
    description 'Configuration model information of ERPS VLAN group.'
                ;
    container erps {
      description 'The configuration information of ERPS VLAN group.'
                  ;
      container VLAN-groups {
        description 'Configure ERPS VLAN groups.'
                    ;
        list VLAN-group-instance {
          description 'ERPS VLAN group instance.'
                      ;
          key group-id ;
          leaf group-id {
            description 'Group ID of ERPS VLAN group.'
                        ;
            type uint32 {
              range 1..239 {
                description 'The range of ERPS VLAN group id.'
                            ;
              }
            }
          }
          container control-vlan {
            description 'Control VLAN of ERPS VLAN group.'
                        ;
            presence 'control vlan'
                     ;
            leaf vlan-id {
              description 'Control protect VLAN of ERPS VLAN group.'
                          ;
              type uint16 {
                range 1..4094 {
                  description 'The range of VLAN id.'
                              ;
                }
              }
              mandatory true ;
            }
          }
          container east-port {
            description 'East port of ERPS VLAN group.'
                        ;
            presence east-port ;
            leaf port-role {
              description 'Configure east port role of ERPS VLAN group.'
                          ;
              type erps-group-port-role ;
              default rpl-normal ;
            }
            leaf if-name {
              description 'Configure east port of ERPS VLAN group.'
                          ;
              type ncd:ifname ;
              mandatory true ;
            }
          }
          container west-port {
            description 'West port of ERPS VLAN group.'
                        ;
            presence west-port ;
            leaf port-role {
              description 'Configure west port role of ERPS VLAN group.'
                          ;
              type erps-group-port-role ;
              default rpl-normal ;
            }
            leaf if-name {
              description 'Configure east port of ERPS VLAN group.'
                          ;
              type ncd:ifname ;
              mandatory true ;
            }
          }
          container protect-strategy {
            description 'Protection strategy of ERPS VLAN group.'
                        ;
            presence protection-strategy ;
            leaf switch-strategy {
              description 'Protection strategy type.'
                          ;
              type enumeration {
                enum aps {
                  value 1 ;
                  description 'Protection strategy type is aps.'
                              ;
                }
              }
              mandatory true ;
            }
          }
          container protect-vlan {
            description 'Protection VLAN of ERPS VLAN group.'
                        ;
            presence protection-instance ;
            list protect-vlan {
              description 'Protection VLAN of ERPS VLAN group.'
                          ;
              key vlan-id ;
              leaf vlan-id {
                description 'Control protect VLAN of ERPS VLAN group.'
                            ;
                type uint16 {
                  range 1..4094 {
                    description 'The range of VLAN id.'
                                ;
                  }
                }
                mandatory true ;
              }
            }
          }
        }
      }
    }
  }
}
