module zxr10-cip {
  namespace 'http://www.zte.com.cn/zxr10/netconf/schema/rosng/cip' ;
  prefix cip ;
  import zxr10-netconf-defs {
    prefix ncd ;
  }
  organization 'ZTE Corporation' ;
  contact "ZTE Corporation  
\n"
        + "   Nanjing Institute of ZTE Corporation 
\n"
        + "   No.68 Zijinghua Rd. Yuhuatai District, Nanjing, China 
\n"
        + '   Tel: +86-25-52870000'
          ;
  description 'The netconf module to describe the Interface Relation.Like the b'
            + 'inding relation between cip interface and channelizing cpos inte'
            + 'rface.'
              ;
  revision 2013-10-30 {
    description 'The initial version' ;
  }
  container configuration {
    description 'Configure the binding relation between interfaces' ;
    container cip {
      description 'Describe the parameters of interface binding relation to be '
                + 'configured'
                  ;
      container bind {
        description 'Describe the parameters of interface binding relation to b'
                  + 'e configured'
                    ;
        list bind-interfaces {
          description 'The list of binding interfaces for configuring parameter'
                    + 's'
                      ;
          key src-interface ;
          leaf src-interface {
            description 'Source interface name' ;
            type ncd:ifname ;
          }
          leaf dst-interface {
            description 'Destination interface name' ;
            type ncd:ifname ;
            mandatory true ;
          }
        }
      }
    }
  }
}
