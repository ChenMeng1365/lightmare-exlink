module zxr10-route-map {
  namespace 'http://www.zte.com.cn/zxr10/netconf/schema/rosng/route-map'
            ;
  prefix rmap ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe route-map.'
              ;
  revision 2021-04-02 {
    description 'Add a container:/configuration/route-map/rmaps/route-map-seq-r'
              + 'equired/route-map-seq-required.'
                ;
  }
  revision 2021-01-21 {
    description 'Modify the range of the leaf:/configuration/route-map/rmaps/rm'
              + 'ap/match/as-paths/as-path/leaf.'
                ;
  }
  revision 2020-12-30 {
    description 'Add a container:/configuration/route-map/rmaps/rmap/set/cpu.'
                ;
  }
  revision 2020-12-04 {
    description '1,Add containers:'+"\n"
              + '/configuration/route-map/rmaps/rmap/set/l2-srv6-function-id/dt'
              + '2m.'+"\n"
              + '/configuration/route-map/rmaps/rmap/set/l2-srv6-function-id/dt'
              + '2u.'+"\n"
              + '/configuration/route-map/rmaps/rmap/set/l2-srv6-sid/equivalent'
              + '-sid.'
                ;
  }
  revision 2020-11-13 {
    description 'Add enum type for the leaf:/configuration/route-map/rmaps/rmap'
              + '/match/protocols/protocol/type.'
                ;
  }
  revision 2020-10-12 {
    description 'Add a container:/configuration/route-map/rmaps/rmap/match/mac-'
              + 'address.'
                ;
  }
  revision 2020-09-27 {
    description 'Modify the max elements of the yang list:/configuration/route-'
              + 'map/rmaps/rmap/match/interfaces/interface.'
                ;
  }
  revision 2020-08-13 {
    description '1,Add choice case:/configuration/route-map/rmaps/rmap/set/next'
              + '-hop/balckhole.'+"\n"
              + '2,Add choice case:/configuration/route-map/rmaps/rmap/set/ipv6'
              + '/next-hop/balckhole.'
                ;
  }
  revision 2020-07-21 {
    description '1,Modify the range of the leaf:/configuration/route-map/rmaps/'
              + 'rmap/match/ipv4/peer/pfls/pfl/name.'+"\n"
              + '2,Modify the range of the leaf:/configuration/route-map/rmaps/'
              + 'rmap/match/ipv6/peer/pfls/pfl/name.'
                ;
  }
  revision 2020-07-02 {
    description '1,Add containers:'+"\n"
              + '/configuration/route-map/rmaps/rmap/set/extcommunity/mulitcast'
              + '-rt.'
                ;
  }
  revision 2020-06-04 {
    description 'Modify the range of the leaf:/configuration/route-map/rmaps/rm'
              + 'ap/rmap-name.'
                ;
  }
  revision 2020-05-14 {
    description 'Add choice case:/configuration/route-map/rmaps/rmap/set/as-pat'
              + 'hs/replace-private-as.'
                ;
  }
  revision 2020-03-25 {
    description '1,Add containers:'+"\n"
              + '/configuration/route-map/rmaps/rmap/match/large-community-name'
              + 's.'+"\n"
              + '/configuration/route-map/rmaps/rmap/set/large-community.'
                ;
  }
  revision 2020-02-26 {
    description '1,Add containers:'+"\n"
              + '/configuration/route-map/rmaps/rmap/set/ip/sr-policy.'+"\n"
              + '/configuration/route-map/rmaps/rmap/set/ipv6/sr-policy.'
                ;
  }
  revision 2019-11-20 {
    description 'Add selects of the list:/configuration/route-map/rmaps/rmap.'
                ;
  }
  revision 2019-11-06 {
    description '1,Add containers:/configuration/route-map/rmaps/rmap/set/ipv6/'
              + 'vxlan-tunnel.'
                ;
  }
  revision 2019-09-26 {
    description '1,Add containers:'+"\n"
              + '/configuration/route-map/rmaps/rmap/set/ipv6/gw-ip.'+"\n"
              + '/configuration/route-map/rmaps/rmap/set/gw-ip.'+"\n"
              + '2,Add choice:/configuration/route-map/rmaps/rmap/set/l3-vni-la'
              + 'bel/l3-vni-label.'
                ;
  }
  revision 2019-09-09 {
    description '1,Add containers:/configuration/route-map/rmaps/rmap/set/equiv'
              + 'alent-evi-label.'+"\n"
              + '2,Add containers:/configuration/route-map/rmaps/rmap/set/evi-l'
              + 'abel.'
                ;
  }
  revision 2019-07-22 {
    description '1,Add choice:/configuration/route-map/rmaps/rmap/set/metric/me'
              + 'tric.'+"\n"
              + '2,Add container:/configuration/route-map/rmaps/rmap/match/ipv4'
              + '-ipv6.'
                ;
  }
  revision 2019-07-16 {
    description 'Modify the range and description of the leaf:/configuration/ro'
              + 'ute-map/rmaps/rmap/set/traffic-index/value.'
                ;
  }
  revision 2019-05-31 {
    description '1,Add containers:'+"\n"
              + '/configuration/route-map/rmaps/rmap/match/route-type/nssa-exte'
              + 'rns,'+"\n"
              + '/configuration/route-map/rmaps/rmap/match/rpki,'+"\n"
              + '/configuration/route-map/rmaps/rmap/match/protocols.'+"\n"
              + '2,Add choice:/configuration/route-map/rmaps/rmap/set/as-paths.'
              + ''+"\n"
              + '3,Add choice case:/configuration/route-map/rmaps/rmap/set/colo'
              + 'r/list-name.'+"\n"
              + '4,Remove mandatory:/configuration/route-map/rmaps/rmap/set/as-'
              + 'path/value. '+"\n"
              + '5,Add enum items of delete and empty to the leaf:/configuratio'
              + 'n/route-map/rmaps/rmap/set/as-path/operation. '+"\n"
              + '6,Move the container:/configuration/route-map/rmaps/rmap/set/a'
              + 's-path to the choice case:/configuration/route-map/rmaps/rmap/'
              + 'set/as-paths/as-path.'
                ;
  }
  revision 2019-05-08 {
    description '1,Add containers:/configuration/route-map/rmaps/rmap/set/tunne'
              + 'l-encapsulation.'
                ;
  }
  revision 2019-05-01 {
    description '1,Add containers:/configuration/route-map/rmaps/rmap/match/esi.'
                ;
  }
  revision 2019-04-17 {
    description '1.Add containers:/configuration/route-map/rmaps/rmap/match/ipv'
              + '4/next-hop-pfls.'+"\n"
              + '2.Add containers:/configuration/route-map/rmaps/rmap/match/ipv'
              + '6/next-hop-pfls.'+"\n"
              + '3.Add containers:/configuration/route-map/rmaps/rmap/match/ipv'
              + '6/source-pfls.'+"\n"
              + '4.Add containers:/configuration/route-map/rmaps/rmap/match/met'
              + 'rics.'+"\n"
              + '5.Add containers:/configuration/route-map/rmaps/rmap/match/tag'
              + 's.'+"\n"
              + '6.Add containers:/configuration/route-map/rmaps/rmap/set/metri'
              + 'c.'+"\n"
              + '7.Add containers:/configuration/route-map/rmaps/rmap/set/metri'
              + 'c-type.'+"\n"
              + '8.Add containers:/configuration/route-map/rmaps/rmap/set/tag.'
                ;
  }
  revision 2019-04-04 {
    description 'Modify the range and description of the leaf:/configuration/ro'
              + 'ute-map/rmaps/rmap/set/l3-vni-label/label.'
                ;
  }
  revision 2019-03-21 {
    description '1.Add choice:/configuration/route-map/rmaps/rmap/set/color/col'
              + 'or; '+"\n"
              + '2.Add leaf:/configuration/route-map/rmaps/rmap/set/color/color'
              + '/remove/remove.'
                ;
  }
  revision 2019-03-12 {
    description 'Remove choice: /configuration/route-map/rmaps/rmap/match/ip an'
              + 'd /configuration/route-map/rmaps/rmap/set/ip.'
                ;
  }
  revision 2019-02-27 {
    description '1.Add containers:/configuration/route-map/rmaps/trigger-delay.'
              + ''+"\n"
              + '2.Add containers:/configuration/route-map/rmaps/rmap/set/urpf.'
              + ''+"\n"
              + '3.Add containers:/configuration/route-map/rmaps/rmap/set/aigp-'
              + 'metric.'+"\n"
              + '4.Add containers:/configuration/route-map/rmaps/rmap/set/color'
              + '.'
                ;
  }
  revision 2018-12-29 {
    description '1,modify the description of the leaf:/configuration/route-map/'
              + 'rmaps/rmap/match/ip/ipv4/ipv4/address/address/acl/acls/acl/nam'
              + 'e.'+"\n"
              + '2,modify the description of the leaf:/configuration/route-map/'
              + 'rmaps/rmap/match/ip/ipv4/ipv4/address/address/pfl/pfls/pfl/nam'
              + 'e.'+"\n"
              + '3,modify the description of the leaf:/configuration/route-map/'
              + 'rmaps/rmap/match/ip/ipv4/ipv4/next-hops/next-hop/acl-name.'+"\n"
              + '4,modify the description of the leaf:/configuration/route-map/'
              + 'rmaps/rmap/match/ip/ipv4/ipv4/sources/source/acl/acls/acl/name'
              + '.'+"\n"
              + '5,modify the description of the leaf:/configuration/route-map/'
              + 'rmaps/rmap/match/ip/ipv4/ipv4/sources/source/pfl/pfls/pfl/name'
              + '.'+"\n"
              + '6,modify the description of the leaf:/configuration/route-map/'
              + 'rmaps/rmap/match/ip/ipv4/ipv4/peer/peer/acl/acls/acl/name.'+"\n"
              + '7,modify the description of the leaf:/configuration/route-map/'
              + 'rmaps/rmap/match/ip/ipv4/ipv4/peer/peer/pfl/pfls/pfl/name.'+"\n"
              + '8,modify the description of the leaf:/configuration/route-map/'
              + 'rmaps/rmap/match/ip/ipv6/ipv6/address/address/acl/acls/acl/nam'
              + 'e.'+"\n"
              + '9,modify the description of the leaf:/configuration/route-map/'
              + 'rmaps/rmap/match/ip/ipv6/ipv6/address/address/pfl/pfls/pfl/nam'
              + 'e.'+"\n"
              + '10,modify the description of the leaf:/configuration/route-map'
              + '/rmaps/rmap/match/ip/ipv6/ipv6/next-hops/next-hop/acl-name.'+"\n"
              + '11,modify the description of the leaf:/configuration/route-map'
              + '/rmaps/rmap/match/ip/ipv6/ipv6/sources/source/acl/acls/acl/nam'
              + 'e.'+"\n"
              + '12,modify the description of the leaf:/configuration/route-map'
              + '/rmaps/rmap/match/ip/ipv6/ipv6/sources/source/pfl/pfls/pfl/nam'
              + 'e.'+"\n"
              + '13,modify the description of the leaf:/configuration/route-map'
              + '/rmaps/rmap/match/ip/ipv6/ipv6/peer/peer/acl/acls/acl/name.'+"\n"
              + '14,modify the description of the leaf:/configuration/route-map'
              + '/rmaps/rmap/match/ip/ipv6/ipv6/peer/peer/pfl/pfls/pfl/name.'+"\n"
              + '15,modify the description of the leaf:/configuration/route-map'
              + '/rmaps/rmap/set/local-preference/add-del.'
                ;
  }
  revision 2018-12-19 {
    description 'Add a leaf:/configuration/route-map/rmaps/rmap/set/local-prefe'
              + 'rence/add-del.'
                ;
  }
  revision 2018-12-04 {
    description '1,Add containers:/configuration/route-map/rmaps/rmap/match/ip/'
              + 'ipv4/ipv4/peer.'+"\n"
              + '2,Add containers:/configuration/route-map/rmaps/rmap/match/ip/'
              + 'ipv6/ipv6/peer.'+"\n"
              + '3,Add containers:/configuration/route-map/rmaps/rmap/set/split'
              + '-horizon-scope.'+"\n"
              + '4,Add containers:/configuration/route-map/rmaps/rmap/set/l3-eq'
              + 'uivalent-vni-lable.'+"\n"
              + '5,Add containers:/configuration/route-map/rmaps/rmap/set/l2-eq'
              + 'uivalent-vni-lable.'
                ;
  }
  revision 2018-11-27 {
    description '1,Add containers:/configuration/route-map/rmaps/rmap/descripti'
              + 'on.'
                ;
  }
  revision 2018-11-15 {
    description 'Add a container:/configuration/route-map/rmaps/rmap/set/distan'
              + 'ce.'
                ;
  }
  revision 2018-10-15 {
    description 'Add a container:/configuration/route-map/rmaps/rmap/set/router'
              + '-mac.'
                ;
  }
  revision 2018-02-09 {
    description '1,Add containers:/configuration/route-map/rmaps/rmap/match/as-'
              + 'path-names.'
                ;
  }
  revision 2017-11-20 {
    description '1,Add containers:/configuration/route-map/rmaps/rmap/match/com'
              + 'munity-names;/configuration/route-map/rmaps/rmap/match/extcomm'
              + 'unity-names;'+"\n"
              + '2,Add cases:/configuration/route-map/rmaps/rmap/set/community/'
              + 'community/set-community-name; /configuration/route-map/rmaps/r'
              + 'map/set/community/community/set-community-name-add.'
                ;
  }
  revision 2017-07-25 {
    description 'Add V6000 project label for strict-policy feature.'
                ;
  }
  revision 2017-07-04 {
    description 'Modify the presence of the container:/configuration/route-map/'
              + 'rmaps/rmap/set/monitor-group-id.'
                ;
  }
  revision 2017-06-28 {
    description 'Modify the description of the container:/configuration/route-m'
              + 'ap/rmaps/rmap/match/route-type/externs.'+"\n"
              + 'Modify the description of the list:/configuration/route-map/rm'
              + 'aps/rmap/match/route-type/externs/extern.'+"\n"
              + 'Modify the description of the leaf:/configuration/route-map/rm'
              + 'aps/rmap/match/route-type/externs/extern/type.'
                ;
  }
  revision 2017-04-28 {
    description 'Add container:/configuration/route-map/rmaps/rmap/match/ip/ipv'
              + '4/ipv4/policy-route-id '+"\n"
              + 'and /configuration/route-map/rmaps/rmap/match/ip/ipv6/ipv6/pol'
              + 'icy-route-id '+"\n"
              + 'and /configuration/route-map/rmaps/rmap/set/monitor-group-id'+"\n"
              + 'and /configuration/route-map/rmaps/rmap/set/policy-route-id'
                ;
  }
  revision 2017-03-10 {
    description 'Add a container:/configuration/route-map/rmaps/rmap/match/l2-v'
              + 'ni-label and /configuration/route-map/rmaps/rmap/match/l3-vni-'
              + 'label.'+"\n"
              + 'Modify the range of the leaf:/configuration/route-map/rmaps/rm'
              + 'ap/match/route-type/routes/route/type.'
                ;
  }
  revision 2017-02-28 {
    description 'Add a container:/configuration/route-map/rmaps/rmap/set/l3vni-'
              + 'label.'
                ;
  }
  revision 2016-12-05 {
    description 'Modify the range of the leaf:/configuration/route-map/rmaps/rm'
              + 'ap/match/evpns/evpn/route-type.'
                ;
  }
  revision 2016-11-17 {
    description 'Add a container:/configuration/route-map/rmaps/rmap/set/evpn-r'
              + 'oute-mac'+"\n"
              + 'and /configuration/route-map/rmaps/rmap/set/ip/ipv4/ipv4/vxlan'
              + '-tunnel and /configuration/route-map/rmaps/rmap/set/l2vni-labe'
              + 'l.'
                ;
  }
  revision 2016-08-18 {
    description 'Add a feature: strict-policy.'+"\n"
              + 'Add a container:/configuration/route-map/rmaps/rmap/strict-pol'
              + 'icy.'+"\n"
              + 'Add containers:/configuration/route-map/rmaps/rmap/set/ip/ipv4'
              + '/ipv4/paths and /configuration/route-map/rmaps/rmap/set/ip/ipv'
              + '6/ipv6/paths.'
                ;
  }
  revision 2016-08-12 {
    description 'Remove mandatory: /configuration/route-map/rmaps/rmap/default-'
              + 'route/default-route-enable and /configuration/route-map/rmaps/'
              + 'rmap/blackhole-route/blackhole-route-enable.'
                ;
  }
  revision 2016-07-18 {
    description 'Add containers:/configuration/route-map/rmaps/rmap/default-rou'
              + 'te,blackhole-route.'
                ;
  }
  revision 2016-05-24 {
    description 'Add a container:/configuration/route-map/rmaps/rmap/match/evpn'
              + 's.'
                ;
  }
  revision 2016-05-18 {
    description 'Add a container:/configuration/route-map/rmaps/rmap/time-range.'
                ;
  }
  revision 2016-04-25 {
    description 'Add a container:/configuration/route-map/rmaps/rmap/load-share.'
                ;
  }
  revision 2016-02-02 {
    description 'Add a container:/configuration/route-map/rmaps/rmap/match/vni.'
                ;
  }
  revision 2015-09-01 {
    description 'Add the container,/confiuration/route-map/rmaps/rmap/continues'
                ;
  }
  revision 2015-04-20 {
    description '1.Add the pattern:/configuration/route-map/rmaps/rmap/set/comm'
              + 'unity/community/set-community/non-add/asns/asn/value and /conf'
              + 'iguration/route-map/rmaps/rmap/set/community/community/set-com'
              + 'munity-add/with-add/asns/asn/value.'
                ;
  }
  revision 2015-02-25 {
    description 'Modify set next-hop and set ipv6 next-hop path as follow:'+"\n"
              + 'Modify before:'+"\n"
              + '/rmap:configuration/rmap:route-map/rmap:rmaps/rmap:rmap/rmap:s'
              + 'et/rmap:ipv6/rmap:peer-address'+"\n"
              + '/rmap:configuration/rmap:route-map/rmap:rmaps/rmap:rmap/rmap:s'
              + 'et/rmap:ipv6/rmap:next-hops/rmap:next-hop/rmap:ipv6-addr'+"\n"
              + '/rmap:configuration/rmap:route-map/rmap:rmaps/rmap:rmap/rmap:s'
              + 'et/rmap:peer-address'+"\n"
              + '/rmap:configuration/rmap:route-map/rmap:rmaps/rmap:rmap/rmap:s'
              + 'et/rmap:next-hops/rmap:next-hop/rmap:ipv4-addr'+"\n"
              + 'Modify after:'+"\n"
              + '/rmap:configuration/rmap:route-map/rmap:rmaps/rmap:rmap/rmap:s'
              + 'et/rmap:ipv6/rmap:next-hop/rmap:peer/rmap:peer-address'+"\n"
              + '/rmap:configuration/rmap:route-map/rmap:rmaps/rmap:rmap/rmap:s'
              + 'et/rmap:ipv6/rmap:next-hop/rmap:next-hops/rmap:next-hop/rmap:i'
              + 'pv6-addr'+"\n"
              + '/rmap:configuration/rmap:route-map/rmap:rmaps/rmap:rmap/rmap:s'
              + 'et/rmap:next-hop/rmap:peer/rmap:peer-address'+"\n"
              + '/rmap:configuration/rmap:route-map/rmap:rmaps/rmap:rmap/rmap:s'
              + 'et/rmap:next-hop/rmap:next-hops/rmap:next-hop/rmap:ipv4-addr'
                ;
  }
  revision 2014-12-09 {
    description 'Add set as-path replace item as follow:'+"\n"
              + '/rmap:configuration/rmap:route-map/rmap:rmaps/rmap:rmap/rmap:s'
              + 'et/rmap:as-path/operation'
                ;
  }
  revision 2014-09-25 {
    description 'Add set nexthop peer-address and set ipv6 nexthop peer-address'
              + ' item as follow:'+"\n"
              + '/rmap:configuration/rmap:route-map/rmap:rmaps/rmap:rmap/rmap:s'
              + 'et/rmap:peer-address'+"\n"
              + '/rmap:configuration/rmap:route-map/rmap:rmaps/rmap:rmap/rmap:s'
              + 'et/rmap:ipv6/rmap:peer-address'
                ;
  }
  revision 2014-09-17 {
    description 'Add match ipv6 address prefix-list node as follow:'+"\n"
              + '/rmap:configuration/rmap:route-map/rmap:rmaps/rmap:rmap/rmap:m'
              + 'atch/rmap:ipv6/'+"\n"
              + 'rmap:address/rmap:pfls/rmap:pfl/rmap:name.'
                ;
  }
  revision 2014-04-21 {
    description 'Initial version.'
                ;
  }
  feature strict-policy {
    description 'Strict policy.'
                ;
  }
  container configuration {
    description "Route-map's configuration."
                ;
    container route-map {
      description "Routing policy's module."
                  ;
      container rmaps {
        description "Routing policy's list."
                    ;
        list rmap {
          description "Routing policy's list."
                      ;
          key 'rmap-name rseq-no'
              ;
          leaf rmap-name {
            description "Routing Policy's name."
                        ;
            type string {
              length 1..200 {
                description 'The length of rmap name is from 1 to 200.'
                            ;
              }
            }
          }
          leaf rseq-no {
            description "Routing Policy's sequence."
                        ;
            type uint16 {
              range 0..65535 {
                description 'The range of routemap-sequence is from 0 to 65535'
                            ;
              }
            }
          }
          leaf deny-permit {
            description 'Deny  : Route map denies set operations and specify pa'
                      + 'ckets to reject.'+"\n"
                      + 'Permit: Route map permits set operations and specify p'
                      + 'ackets to forward.'
                        ;
            type enumeration {
              enum deny {
                value 1 ;
                description 'Deny  : Route map denies set operations and specif'
                          + 'y packets to reject.'
                            ;
              }
              enum permit {
                value 0 ;
                description 'Permit: Route map permits set operations and speci'
                          + 'fy packets to forward'
                            ;
              }
            }
            default permit ;
          }
          container description {
            description 'Description of the route map (1-199).'
                        ;
            presence description ;
            leaf description {
              description 'Description of the route map (1-199).'
                          ;
              type ncd:string-with-blank {
                length 1..199 ;
              }
              mandatory true ;
            }
            ncd:revise-date 2018-11-27 ;
          }
          container match {
            description "Routing Policy's condition."
                        ;
            presence match ;
            container as-paths {
              description 'Match BGP as-path list.'
                          ;
              list as-path {
                description 'Match BGP as-path list.'
                            ;
                max-elements 10 ;
                key name ;
                leaf name {
                  description "Match BGP's as-path list."
                              ;
                  type uint16 {
                    range 1..256 {
                      description 'The range of as-path number is from 0 to 256.'
                                  ;
                    }
                  }
                }
              }
            }
            container as-path-names {
              description 'Match BGP as-path list name.'
                          ;
              list as-path-name {
                description 'Match BGP as-path list name.'
                            ;
                max-elements 10 ;
                key name ;
                leaf name {
                  description 'As-path list name.'
                              ;
                  type string {
                    length 1..31 ;
                  }
                }
              }
              ncd:revise-date 2018-02-09 ;
            }
            container as-path-len {
              description 'Match BGP as-path-length.'
                          ;
              presence 'as-path-length is not Mandatory'
                       ;
              leaf alg {
                description 'Eq:Equal as-path length to be matched.'+"\n"
                          + 'Ge:Minimum as-path length to be matched.'+"\n"
                          + 'Le:Maximun as-path length to be matched.'
                            ;
                type enumeration {
                  enum eq {
                    value 0 ;
                    description 'Equal as-path length to be matched.'
                                ;
                  }
                  enum ge {
                    value 1 ;
                    description 'Minimum as-path length to be matched.'
                                ;
                  }
                  enum le {
                    value 2 ;
                    description 'Maximun as-path length to be matched.'
                                ;
                  }
                }
                mandatory true ;
              }
              leaf length {
                description 'AS-PATH length(0~255).'
                            ;
                type uint32 {
                  range 0..255 {
                    description 'The range of as-path number is from 0 to 255.'
                                ;
                  }
                }
                mandatory true ;
              }
            }
            container as-path-uni-len {
              description 'Match BGP as-path-unique-length.'
                          ;
              presence 'as-path-unique-length is not Mandatory'
                       ;
              leaf alg {
                description 'Eq:Equal as-path unique length to be matched.'+"\n"
                          + 'Ge:Minimum as-path unique length to be matched.'+"\n"
                          + 'Le:Maximun as-path unique length to be matched.'
                            ;
                type enumeration {
                  enum eq {
                    value 0 ;
                    description 'Equal as-path unique length to be matched.'
                                ;
                  }
                  enum ge {
                    value 1 ;
                    description 'Minimum as-path unique length to be matched.'
                                ;
                  }
                  enum le {
                    value 2 ;
                    description 'Maximun as-path unique length to be matched.'
                                ;
                  }
                }
                mandatory true ;
              }
              leaf length {
                description 'AS-PATH unique length(0~255).'
                            ;
                type uint32 {
                  range 0..255 {
                    description 'The Range of length is from 0 to 255.'
                                ;
                  }
                }
                mandatory true ;
              }
            }
            container communitys {
              description 'Match BGP community list.'
                          ;
              list community {
                description 'Match BGP community list.'
                            ;
                max-elements 10 ;
                key value ;
                leaf value {
                  description 'BGP community list number.'
                              ;
                  type uint16 {
                    range 1..499 {
                      description 'The range of community-list-number is from 1'
                                + ' to 499.'
                                  ;
                    }
                  }
                }
              }
            }
            container community-names {
              description 'Match BGP community list name.'
                          ;
              list community-name {
                description 'Match BGP community list name.'
                            ;
                max-elements 10 ;
                key name ;
                leaf name {
                  description 'BGP community list name.'
                              ;
                  type string {
                    length 1..31 ;
                  }
                }
              }
              ncd:revise-date 2017-11-20 ;
            }
            container large-community-names {
              description 'Match BGP/VPN large community list name.'
                          ;
              list large-community-name {
                description 'Match BGP/VPN large community list name.'
                            ;
                max-elements 10 ;
                key name ;
                leaf name {
                  description 'BGP/VPN large community list name.'
                              ;
                  type string {
                    length 1..31 ;
                  }
                }
              }
              ncd:revise-date 2020-03-25 ;
            }
            container extcommunitys {
              description 'Match BGP/VPN extended community list.'
                          ;
              list extcommunity {
                description 'Match BGP/VPN extended community list.'
                            ;
                max-elements 10 ;
                key value ;
                leaf value {
                  description 'BGP/VPN extended community list number.'
                              ;
                  type uint16 {
                    range 1..500 {
                      description 'The range of excommunity-list-number is from'
                                + ' 1 to 500.'
                                  ;
                    }
                  }
                }
              }
            }
            container extcommunity-names {
              description 'Match BGP/VPN extended community list name.'
                          ;
              list extcommunity-name {
                description 'Match BGP/VPN extended community list name.'
                            ;
                max-elements 10 ;
                key name ;
                leaf name {
                  description 'BGP/VPN extended community list name.'
                              ;
                  type string {
                    length 1..31 ;
                  }
                }
              }
              ncd:revise-date 2017-11-20 ;
            }
            container interfaces {
              description 'Match first hop interface of route.'
                          ;
              list interface {
                description 'Match first hop interface of route.'
                            ;
                max-elements 16 ;
                key ifname ;
                leaf ifname {
                  description 'First hop interface of route.'
                              ;
                  type ncd:ifname ;
                }
              }
            }
            container ipv4 {
              description 'Match IP specific information.'
                          ;
              container address {
                description 'Match address of route or match packet.'+"\n"
                          + 'Address value can be specifed to prefix-list/acces'
                          + 's list type.'
                            ;
                choice address {
                  description 'Match address of route or match packet.'+"\n"
                            + 'Address value can be specifed to prefix-list/acc'
                            + 'ess list type.'
                              ;
                  case acl {
                    description 'access list type.'
                                ;
                    container acls {
                      description 'IP access-list or prefix-list (max quantity '
                                + '10).'
                                  ;
                      list acl {
                        description 'IP access-list or prefix-list (max quantit'
                                  + 'y 10).'
                                    ;
                        max-elements 10 ;
                        key name ;
                        leaf name {
                          description 'The name of access-list.'
                                      ;
                          type string {
                            length 1..31 {
                              description 'The length of access-list-name is from 1 to 31.'
                                          ;
                            }
                          }
                        }
                      }
                    }
                  }
                  case pfl {
                    description 'Prefix-list type.'
                                ;
                    container pfls {
                      description 'Match entries of prefix-lists(max quantity 1'
                                + '0).'
                                  ;
                      list pfl {
                        description 'Match entries of prefix-lists.'
                                    ;
                        max-elements 10 ;
                        key name ;
                        leaf name {
                          description 'The name of prefix-list.'
                                      ;
                          type string {
                            length 1..169 {
                              description 'The length of prefix-list-name is from 1 to 169.'
                                          ;
                            }
                          }
                        }
                      }
                    }
                  }
                }
              }
              choice metric {
                description 'Match metric of route.'
                            ;
                case algmetric {
                  description 'Match metric of route with alg sign(eq,ge,le).Fo'
                            + 'r example, The command is follow:ip metric {eq|g'
                            + 'e|le} <metric-value>.'
                              ;
                  container algmetric {
                    description 'Match metric of route with alg sign(eq,ge,le).'
                              + 'For example, The command is follow:ip metric {'
                              + 'eq|ge|le} <metric-value>.'
                                ;
                    presence algmetric ;
                    leaf alg {
                      description 'Eq:Equal metric value to be matched.'+"\n"
                                + 'Ge:Minimum metric value to be matched.'+"\n"
                                + 'Le:Maximun metric value to be matched.'
                                  ;
                      type enumeration {
                        enum eq {
                          value 0 ;
                          description 'Equal metric value to be matched'
                                      ;
                        }
                        enum ge {
                          value 1 ;
                          description 'Minimum metric value to be matched'
                                      ;
                        }
                        enum le {
                          value 2 ;
                          description 'Maximun metric value to be matched'
                                      ;
                        }
                      }
                      mandatory true ;
                    }
                    leaf value {
                      description 'Metric value(0~4294967295).'
                                  ;
                      type uint32 {
                        range 0..4294967295 {
                          description 'The Range of metric-value is from 0 to 4'
                                    + '294967295.'
                                      ;
                        }
                      }
                      mandatory true ;
                    }
                  }
                }
                case metric {
                  description 'Match metric of route.'
                              ;
                  container metrics {
                    description 'Match metric of route.'
                                ;
                    list metric {
                      description 'Match metric of route.'
                                  ;
                      max-elements 10 ;
                      key value ;
                      leaf value {
                        description 'Metric value(0~4294967295).'
                                    ;
                        type uint32 {
                          range 0..4294967295 {
                            description 'The Range of metric-value is from 0 to 4294967295.'
                                        ;
                          }
                        }
                      }
                    }
                  }
                }
              }
              container next-hops {
                description 'Match next-hop address of route.'
                            ;
                list next-hop {
                  description 'Match next-hop address of route.'
                              ;
                  max-elements 10 ;
                  key acl-name ;
                  leaf acl-name {
                    description 'The name of access-list.'
                                ;
                    type string {
                      length 1..31 {
                        description 'The length of access-list-name is from 1 t'
                                  + 'o 31 characters.'
                                    ;
                      }
                    }
                  }
                }
              }
              container next-hop-pfls {
                description 'Match next-hop address of route. Address value sho'
                          + 'uld be specifed to prefix-list.'
                            ;
                list next-hop-pfl {
                  description 'Match next-hop address of route. Address value s'
                            + 'hould be specifed to prefix-list.'
                              ;
                  max-elements 10 ;
                  key pfl-name ;
                  leaf pfl-name {
                    description 'The name of prefix-list.'
                                ;
                    type string {
                      length 1..169 {
                        description 'The length of prefix-list-name is from 1 t'
                                  + 'o 169.'
                                    ;
                      }
                    }
                  }
                }
                ncd:revise-date 2019-04-17 ;
              }
              container sources {
                description 'Match source address of route.'
                            ;
                choice source {
                  description 'Match source address of route.'
                              ;
                  case acl {
                    description 'Match source address of route in access list t'
                              + 'ype.'
                                ;
                    container acls {
                      description 'Match source address of route in access list'
                                + ' type(max quantity 10).'
                                  ;
                      list acl {
                        description 'Match source address of route in access li'
                                  + 'st type(max quantity 10).'
                                    ;
                        max-elements 10 ;
                        key name ;
                        leaf name {
                          description 'IP access list name.'
                                      ;
                          type string {
                            length 1..31 {
                              description 'The length of access-list-name is from 1 to 31 characters.'
                                          ;
                            }
                          }
                        }
                      }
                    }
                  }
                  case pfl {
                    description 'Match source address of route in prefix list t'
                              + 'ype.'
                                ;
                    container pfls {
                      description 'Match source address of route in prefix list'
                                + ' type(max quantity 10).'
                                  ;
                      list pfl {
                        description 'Match source address of route in prefix li'
                                  + 'st type(max quantity 10).'
                                    ;
                        max-elements 10 ;
                        key name ;
                        leaf name {
                          description 'IP prefix list name.'
                                      ;
                          type string {
                            length 1..169 {
                              description 'The length of prefix-list-name is from 1 to 169 characters.'
                                          ;
                            }
                          }
                        }
                      }
                    }
                  }
                }
              }
              container tags {
                description 'Match tag of route.'
                            ;
                list tag {
                  description 'Match tag of route.'
                              ;
                  max-elements 10 ;
                  key value ;
                  leaf value {
                    description 'Tag value of route.'
                                ;
                    type uint32 {
                      range 0..4294967295 {
                        description 'The range of tag value is from 0 to 429496'
                                  + '7295.'
                                    ;
                      }
                    }
                  }
                }
              }
              container policy-route-ids {
                description 'Match policy route id.'
                            ;
                list policy-route-id {
                  description 'Match policy route id.'
                              ;
                  max-elements 10 ;
                  key 'pid direction'
                      ;
                  leaf pid {
                    description 'Policy route id.'
                                ;
                    type uint8 {
                      range 1..63 ;
                    }
                  }
                  leaf direction {
                    description 'Direction of policy route.'
                                ;
                    type enumeration {
                      enum distination {
                        value 1 ;
                        description 'Destination direction.'
                                    ;
                      }
                      enum source {
                        value 2 ;
                        description 'Source direction.'
                                    ;
                      }
                    }
                  }
                }
                ncd:revise-date 2017-04-28 ;
              }
              container peer {
                description 'Match BGP peer. And peer value can be specified to'
                          + ' prefix-list or access-list type.'
                            ;
                choice peer {
                  description 'Match BGP peer. And peer value can be specified '
                            + 'to prefix-list or access-list type.'
                              ;
                  case acl {
                    description 'Access-list type.'
                                ;
                    container acls {
                      description 'Match entries of access-list(max quantity 10'
                                + ').'
                                  ;
                      list acl {
                        description 'Match entries of access-list(max quantity '
                                  + '10).'
                                    ;
                        max-elements 10 ;
                        key name ;
                        leaf name {
                          description 'The name of access-list.'
                                      ;
                          type string {
                            length 1..31 {
                              description 'The length of access-list-name is from 1 to 31.'
                                          ;
                            }
                          }
                        }
                      }
                    }
                  }
                  case pfl {
                    description 'Prefix-list type.'
                                ;
                    container pfls {
                      description 'Match entries of prefix-lists(max quantity 1'
                                + '0).'
                                  ;
                      list pfl {
                        description 'Match entries of prefix-lists.'
                                    ;
                        max-elements 10 ;
                        key name ;
                        leaf name {
                          description 'The name of prefix-list.'
                                      ;
                          type string {
                            length 1..169 {
                              description 'The length of prefix-list-name is from 1 to 169.'
                                          ;
                            }
                          }
                        }
                      }
                    }
                  }
                }
                ncd:revise-date 2018-12-04 ;
              }
            }
            container ipv6 {
              description 'Match IPV6 specific information.'
                          ;
              container address {
                description 'Match address of route or match packet(max quantit'
                          + 'y 10).'
                            ;
                choice address {
                  description 'Match address of route or match packet.'+"\n"
                            + 'Address value can be specifed to prefix-list/acc'
                            + 'ess list type.'
                              ;
                  case acl {
                    description 'access list type.'
                                ;
                    container acls {
                      description 'Match address of route or match packet(max q'
                                + 'uantity 10).'
                                  ;
                      list acl {
                        description 'Match address of route or match packet(max'
                                  + ' quantity 10).'
                                    ;
                        max-elements 10 ;
                        key name ;
                        leaf name {
                          description 'The name of access-list.'
                                      ;
                          type string {
                            length 1..31 {
                              description 'The length of access-list-name is from 1 to 31.'
                                          ;
                            }
                          }
                        }
                      }
                    }
                  }
                  case pfl {
                    description 'Prefix-list type.'
                                ;
                    container pfls {
                      description 'Match entries of prefix-lists(max quantity 1'
                                + '0).'
                                  ;
                      list pfl {
                        description 'Match entries of prefix-lists.'
                                    ;
                        key name ;
                        leaf name {
                          description 'The name of prefix-list.'
                                      ;
                          type string {
                            length 1..169 {
                              description 'The length of prefix-list-name is from 1 to 169.'
                                          ;
                            }
                          }
                        }
                      }
                    }
                  }
                }
              }
              choice metric {
                description 'Match metric of route.'
                            ;
                case algmetric {
                  description 'Match metric of route with alg sign(eq,ge,le).Fo'
                            + 'r example, The command is follow:ipv6 metric {eq'
                            + '|ge|le} <metric-value>.'
                              ;
                  container algmetric {
                    description 'Match metric of route with alg sign(eq,ge,le).'
                              + 'For example, The command is follow:ipv6 metric'
                              + ' {eq|ge|le} <metric-value>.'
                                ;
                    presence algmetric ;
                    leaf alg {
                      description 'Eq:Equal metric value to be matched.'+"\n"
                                + 'Ge:Minimum metric value to be matched.'+"\n"
                                + 'Le:Maximun metric value to be matched.'
                                  ;
                      type enumeration {
                        enum eq {
                          value 0 ;
                          description 'Equal metric value to be matched.'
                                      ;
                        }
                        enum ge {
                          value 1 ;
                          description 'Minimum metric value to be matched.'
                                      ;
                        }
                        enum le {
                          value 2 ;
                          description 'Maximun metric value to be matched.'
                                      ;
                        }
                      }
                      mandatory true ;
                    }
                    leaf value {
                      description 'Metric value(0~4294967295)'
                                  ;
                      type uint32 {
                        range 0..4294967295 {
                          description 'The Range of value is from 0 to 42949672'
                                    + '95.'
                                      ;
                        }
                      }
                      mandatory true ;
                    }
                  }
                }
                case metric {
                  description 'Match metric of route.'
                              ;
                  container metrics {
                    description 'Match metric of route(max quantity 10).'
                                ;
                    list metric {
                      description 'Match metric of route(max quantity 10).'
                                  ;
                      max-elements 10 ;
                      key value ;
                      leaf value {
                        description 'Metric value(0~4294967295).'
                                    ;
                        type uint32 {
                          range 0..4294967295 {
                            description 'The Range of value is from 0 to 4294967295.'
                                        ;
                          }
                        }
                      }
                    }
                  }
                }
              }
              container next-hops {
                description 'Match next-hop address of route(max quantity 10).'
                            ;
                list next-hop {
                  description 'Match next-hop address of route(max quantity 10).'
                              ;
                  max-elements 10 ;
                  key acl-name ;
                  leaf acl-name {
                    description 'The name of access-list.'
                                ;
                    type string {
                      length 1..31 {
                        description 'The length of access-list-name is from 1 t'
                                  + 'o 31.'
                                    ;
                      }
                    }
                  }
                }
              }
              container next-hop-pfls {
                description 'Match next-hop address of route. Address value sho'
                          + 'uld be specifed to prefix-list.'
                            ;
                list next-hop-pfl {
                  description 'Match next-hop address of route. Address value s'
                            + 'hould be specifed to prefix-list.'
                              ;
                  max-elements 10 ;
                  key pfl-name ;
                  leaf pfl-name {
                    description 'The name of prefix-list.'
                                ;
                    type string {
                      length 1..169 {
                        description 'The length of prefix-list-name is from 1 t'
                                  + 'o 169.'
                                    ;
                      }
                    }
                  }
                }
                ncd:revise-date 2019-04-17 ;
              }
              container sources {
                description 'Match source address of route(max quantity 10).'
                            ;
                list source {
                  description 'Match source address of route(max quantity 10).'
                              ;
                  max-elements 10 ;
                  key acl-name ;
                  leaf acl-name {
                    description 'IP access list name.'
                                ;
                    type string {
                      length 1..31 {
                        description 'The length of access-list-name is from 1 t'
                                  + 'o 31 characters.'
                                    ;
                      }
                    }
                  }
                }
              }
              container source-pfls {
                description 'Match source address of route. Address value shoul'
                          + 'd be specifed to prefix-list.'
                            ;
                list source-pfl {
                  description 'Match source address of route. Address value sho'
                            + 'uld be specifed to prefix-list.'
                              ;
                  max-elements 10 ;
                  key pfl-name ;
                  leaf pfl-name {
                    description 'The name of prefix-list.'
                                ;
                    type string {
                      length 1..169 {
                        description 'The length of prefix-list-name is from 1 t'
                                  + 'o 169.'
                                    ;
                      }
                    }
                  }
                }
                ncd:revise-date 2019-04-17 ;
              }
              container tags {
                description 'Match tag of route(max quantity 10).'
                            ;
                list tag {
                  description 'Match tag of route(max quantity 10).'
                              ;
                  max-elements 10 ;
                  key value ;
                  leaf value {
                    description 'Tag value of route.'
                                ;
                    type uint32 {
                      range 0..4294967295 {
                        description 'The range of tag value of route is from 0 '
                                  + 'to 4294967295.'
                                    ;
                      }
                    }
                  }
                }
              }
              container policy-route-ids {
                description 'Match policy route id.'
                            ;
                list policy-route-id {
                  description 'Match policy route id.'
                              ;
                  max-elements 10 ;
                  key 'pid direction'
                      ;
                  leaf pid {
                    description 'Policy route id.'
                                ;
                    type uint8 {
                      range 1..63 ;
                    }
                  }
                  leaf direction {
                    description 'Direction of policy route.'
                                ;
                    type enumeration {
                      enum distination {
                        value 1 ;
                        description 'Destination direction.'
                                    ;
                      }
                      enum source {
                        value 2 ;
                        description 'Source direction.'
                                    ;
                      }
                    }
                  }
                }
                ncd:revise-date 2017-04-28 ;
              }
              container peer {
                description 'Match BGP peer. And peer value can be specified to'
                          + ' prefix-list or access-list type.'
                            ;
                choice peer {
                  description 'Match BGP peer. And peer value can be specified '
                            + 'to prefix-list or access-list type.'
                              ;
                  case acl {
                    description 'access list type.'
                                ;
                    container acls {
                      description 'Match entries of access-list(max quantity 10'
                                + ').'
                                  ;
                      list acl {
                        description 'Match entries of access-list(max quantity '
                                  + '10).'
                                    ;
                        max-elements 10 ;
                        key name ;
                        leaf name {
                          description 'The name of access-list.'
                                      ;
                          type string {
                            length 1..31 {
                              description 'The length of access-list-name is from 1 to 31.'
                                          ;
                            }
                          }
                        }
                      }
                    }
                  }
                  case pfl {
                    description 'Prefix-list type.'
                                ;
                    container pfls {
                      description 'Match entries of prefix-lists(max quantity 1'
                                + '0).'
                                  ;
                      list pfl {
                        description 'Match entries of prefix-lists.'
                                    ;
                        key name ;
                        leaf name {
                          description 'The name of prefix-list.'
                                      ;
                          type string {
                            length 1..169 {
                              description 'The length of prefix-list-name is from 1 to 169.'
                                          ;
                            }
                          }
                        }
                      }
                    }
                  }
                }
                ncd:revise-date 2018-12-04 ;
              }
            }
            container vni {
              description 'Match VNI.'
                          ;
              presence VNI ;
              leaf first-from {
                description 'Set the first lower limit.'
                            ;
                type uint32 {
                  range 1..16777215 ;
                }
                mandatory true ;
              }
              leaf first-to {
                description 'Set the first upper limit.'
                            ;
                type uint32 {
                  range 1..16777215 ;
                }
                mandatory true ;
              }
              container region2 {
                description 'The second region of VNI.'
                            ;
                presence region2 ;
                leaf second-from {
                  description 'Set the second lower limit.'
                              ;
                  type uint32 {
                    range 1..16777215 ;
                  }
                  mandatory true ;
                }
                leaf second-to {
                  description 'Set the second upper limit.'
                              ;
                  type uint32 {
                    range 1..16777215 ;
                  }
                  mandatory true ;
                }
                container region3 {
                  description 'The third region of VNI.'
                              ;
                  presence region3 ;
                  leaf third-from {
                    description 'Set the third lower limit.'
                                ;
                    type uint32 {
                      range 1..16777215 ;
                    }
                    mandatory true ;
                  }
                  leaf third-to {
                    description 'Set the third upper limit.'
                                ;
                    type uint32 {
                      range 1..16777215 ;
                    }
                    mandatory true ;
                  }
                  container region4 {
                    description 'The fourth region of VNI.'
                                ;
                    presence region4 ;
                    leaf fourth-from {
                      description 'Set the fourth lower limit.'
                                  ;
                      type uint32 {
                        range 1..16777215 ;
                      }
                      mandatory true ;
                    }
                    leaf fourth-to {
                      description 'Set the fourth upper limit.'
                                  ;
                      type uint32 {
                        range 1..16777215 ;
                      }
                      mandatory true ;
                    }
                  }
                }
              }
              ncd:revise-date 2016-02-02 ;
            }
            container local-preference {
              description 'Match BGP local preference path attribute.'
                          ;
              presence local-preference ;
              leaf alg {
                description 'Eq:Equal preference value to be matched.'+"\n"
                          + 'Ge:Minimum preference value to be matched.'+"\n"
                          + 'Le:Maximun preference value to be matched.'
                            ;
                type enumeration {
                  enum eq {
                    value 0 ;
                    description 'Equal preference value to be matched.'
                                ;
                  }
                  enum ge {
                    value 1 ;
                    description 'Minimum preference value to be matched.'
                                ;
                  }
                  enum le {
                    value 2 ;
                    description 'Maximun preference value to be matched.'
                                ;
                  }
                }
                mandatory true ;
              }
              leaf value {
                description 'Preference value(0~4294967295).'
                            ;
                type uint32 {
                  range 0..4294967295 {
                    description 'The Range of length is from 0 to 4294967295.'
                                ;
                  }
                }
                mandatory true ;
              }
            }
            container origin {
              description 'Match BGP origin code.'
                          ;
              presence origin ;
              leaf type {
                description 'IGP:Local IGP;'+"\n"
                          + 'Egp:Remote EGP;'+"\n"
                          + 'Incomplete:Unknown heritage.'
                            ;
                type enumeration {
                  enum igp {
                    value 0 ;
                    description 'Local IGP'
                                ;
                  }
                  enum egp {
                    value 1 ;
                    description 'Remote EGP'
                                ;
                  }
                  enum incomplete {
                    value 2 ;
                    description 'Unknown heritage'
                                ;
                  }
                }
                mandatory true ;
              }
            }
            container rd-lists {
              description 'Match BGP/VPN rd list(max quantity 10).'
                          ;
              list rd-list {
                description 'Match BGP/VPN rd list(max quantity 10).'
                            ;
                max-elements 10 ;
                key value ;
                leaf value {
                  description 'Set BGP/VPN rd-list name.'
                              ;
                  type uint16 {
                    range 1..500 {
                      description 'The range of rd-list-number is from 1 to 500.'
                                  ;
                    }
                  }
                }
              }
            }
            container route-type {
              description 'Match route-type of route.'
                          ;
              container routes {
                description 'Match route-type of route.'+"\n"
                          + 'Internal: internal route (including OSPF intra/int'
                          + 'er area);'+"\n"
                          + 'Level-1 : IS-IS level-1 route;'+"\n"
                          + 'Level-2 : IS-IS level-2 route;'+"\n"
                          + 'Local   : Locally generated route.'
                            ;
                list route {
                  description 'Match route-type of route.'+"\n"
                            + 'Internal: internal route (including OSPF intra/i'
                            + 'nter area);'+"\n"
                            + 'Level-1 : IS-IS level-1 route;'+"\n"
                            + 'Level-2 : IS-IS level-2 route;'+"\n"
                            + 'Local   : Locally generated route.'
                              ;
                  key type ;
                  leaf type {
                    description 'Internal: internal route (including OSPF intra'
                              + '/inter area);'+"\n"
                              + 'Level-1 : IS-IS level-1 route;'+"\n"
                              + 'Level-2 : IS-IS level-2 route;'+"\n"
                              + 'Local   : Locally generated route;'+"\n"
                              + 'EBGP    : External border gateway protocol(EBG'
                              + 'P) route;'+"\n"
                              + 'IBGP    : Internal border gateway protocol(IBG'
                              + 'P) route;'+"\n"
                              + 'Static  : Static route;'+"\n"
                              + 'BGP-agg : BGP aggregate route.'
                                ;
                    type enumeration {
                      enum local {
                        value 1 ;
                        description 'Local   : Locally generated route'
                                    ;
                      }
                      enum level-1 {
                        value 3 ;
                        description 'Level-1 : IS-IS level-1 route'
                                    ;
                      }
                      enum level-2 {
                        value 4 ;
                        description 'Level-2 : IS-IS level-2 route'
                                    ;
                      }
                      enum internal {
                        value 2 ;
                        description 'Internal: internal route (including OSPF i'
                                  + 'ntra/inter area)'
                                    ;
                      }
                      enum ebgp {
                        value 8 ;
                        description 'EBGP: External border gateway protocol(EBG'
                                  + 'P) route'
                                    ;
                      }
                      enum ibgp {
                        value 9 ;
                        description 'IBGP: Internal border gateway protocol(IBG'
                                  + 'P) route'
                                    ;
                      }
                      enum static {
                        value 10 ;
                        description 'Static: Static route'
                                    ;
                      }
                      enum bgp-agg {
                        value 11 ;
                        description 'BGP-agg: BGP aggregate route'
                                    ;
                      }
                    }
                  }
                }
              }
              container externs {
                description 'External:external route(OSPF type1/2).'
                            ;
                list extern {
                  description 'External:external route(OSPF type1/2).'
                              ;
                  key type ;
                  leaf type {
                    description 'External:external route(OSPF type1/2).'
                                ;
                    type enumeration {
                      enum type-1 {
                        value 6 ;
                        description 'OSPF external type 1 route.'
                                    ;
                      }
                      enum type-2 {
                        value 7 ;
                        description 'OSPF external type 2 route.'
                                    ;
                      }
                      enum external {
                        value 0 ;
                        description 'External route .'
                                    ;
                      }
                    }
                  }
                }
              }
              container nssa-externs {
                description 'NSSA external:external route(OSPF type1/2).'
                            ;
                list nssa-extern {
                  description 'NSSA external:external route(OSPF type1/2).'
                              ;
                  key type ;
                  leaf type {
                    description 'NSSA external:external route(OSPF type1/2).'
                                ;
                    type enumeration {
                      enum type-1 {
                        value 13 ;
                        description 'OSPF NSSA external type 1 route.'
                                    ;
                      }
                      enum type-2 {
                        value 14 ;
                        description 'OSPF NSSA external type 2 route.'
                                    ;
                      }
                      enum nssa-external {
                        value 0 ;
                        description 'NSSA external route.'
                                    ;
                      }
                    }
                  }
                }
                ncd:revise-date 2019-05-31 ;
              }
            }
            container evpns {
              description 'Match EVPN route.'
                          ;
              list evpn {
                description 'Match EVPN route.'
                            ;
                key route-type ;
                leaf route-type {
                  description 'EVPN route type.'
                              ;
                  type uint32 {
                    range 1..5 ;
                  }
                }
              }
              ncd:revise-date 2016-05-24 ;
            }
            container l2-vni-label {
              description 'Match l2-VNI label.'
                          ;
              presence l2-vni-label ;
              leaf label {
                description 'Match the label value.'
                            ;
                type uint32 {
                  range 1..16777215 {
                    description 'The range of l2-vni label is from 1 to 1677721'
                              + '5.'
                                ;
                  }
                }
                mandatory true ;
              }
              ncd:revise-date 2017-03-10 ;
            }
            container l3-vni-label {
              description 'Match l3-VNI label.'
                          ;
              presence l3-vni-label ;
              leaf label {
                description 'Match the label value.'
                            ;
                type uint32 {
                  range 1..16777215 {
                    description 'The range of l3-vni label is from 1 to 1677721'
                              + '5.'
                                ;
                  }
                }
                mandatory true ;
              }
              ncd:revise-date 2017-03-10 ;
            }
            container metrics {
              description 'Match metric of route.'
                          ;
              choice metric {
                description 'Match metric of route.'
                            ;
                case algmetric {
                  description 'Match metric of route with alg sign(eq,ge,le).Fo'
                            + 'r example, The command is follow:ip metric {eq|g'
                            + 'e|le} <metric-value>.'
                              ;
                  container algmetric {
                    description 'Match metric of route with alg sign(eq,ge,le).'
                              + 'For example, The command is follow:ip metric {'
                              + 'eq|ge|le} <metric-value>.'
                                ;
                    presence algmetric ;
                    leaf alg {
                      description 'Eq:Equal metric value to be matched.'+"\n"
                                + 'Ge:Minimum metric value to be matched.'+"\n"
                                + 'Le:Maximun metric value to be matched.'
                                  ;
                      type enumeration {
                        enum eq {
                          value 0 ;
                          description 'Equal metric value to be matched'
                                      ;
                        }
                        enum ge {
                          value 1 ;
                          description 'Minimum metric value to be matched'
                                      ;
                        }
                        enum le {
                          value 2 ;
                          description 'Maximun metric value to be matched'
                                      ;
                        }
                      }
                      mandatory true ;
                    }
                    leaf value {
                      description 'Metric value(0~4294967295).'
                                  ;
                      type uint32 {
                        range 0..4294967295 {
                          description 'The Range of metric-value is from 0 to 4'
                                    + '294967295.'
                                      ;
                        }
                      }
                      mandatory true ;
                    }
                  }
                }
                case metric {
                  description 'Match metric of route.'
                              ;
                  container metrics {
                    description 'Match metric of route.'
                                ;
                    list metric {
                      description 'Match metric of route.'
                                  ;
                      max-elements 10 ;
                      key value ;
                      leaf value {
                        description 'Metric value(0~4294967295).'
                                    ;
                        type uint32 {
                          range 0..4294967295 {
                            description 'The Range of metric-value is from 0 to 4294967295.'
                                        ;
                          }
                        }
                      }
                    }
                  }
                }
              }
              ncd:revise-date 2019-04-17 ;
            }
            container tags {
              description 'Match tag of route.'
                          ;
              list tag {
                description 'Match tag of route.'
                            ;
                max-elements 10 ;
                key value ;
                leaf value {
                  description 'Tag value of route.'
                              ;
                  type uint32 {
                    range 0..4294967295 {
                      description 'The range of tag value is from 0 to 42949672'
                                + '95.'
                                  ;
                    }
                  }
                }
              }
              ncd:revise-date 2019-04-17 ;
            }
            container esi {
              description 'Match non-zero ESI'
                          ;
              presence 'ESI is not Mandatory'
                       ;
              leaf esi {
                description 'Match ESI'
                            ;
                type empty ;
                mandatory true ;
              }
              ncd:revise-date 2019-05-01 ;
            }
            container rpki {
              description 'Match RPKI'
                          ;
              container origin-as-validations {
                description 'Match origin-as validation.'
                            ;
                list origin-as-validation {
                  description 'Match origin-as validation.'
                              ;
                  key value ;
                  leaf value {
                    description 'The result of origin-as validation.'
                                ;
                    type enumeration {
                      enum valid {
                        value 1 ;
                        description 'Valid BGP route'
                                    ;
                      }
                      enum invalid {
                        value 2 ;
                        description 'Invalid BGP route'
                                    ;
                      }
                      enum not-found {
                        value 3 ;
                        description 'Unable to validate BGP route'
                                    ;
                      }
                    }
                  }
                }
              }
              ncd:revise-date 2019-05-31 ;
            }
            container protocols {
              description 'Match protocol type.'
                          ;
              list protocol {
                description 'Match protocol type.'
                            ;
                key type ;
                leaf type {
                  description 'Set the protocol type of direct/static/rip/ripng'
                            + '/ospf/ospfv3/bgp/isis/special/arp/nd.'
                              ;
                  type enumeration {
                    enum direct {
                      value 1 ;
                      description 'Protocol type direct.'
                                  ;
                    }
                    enum static {
                      value 2 ;
                      description 'Protocol type static.'
                                  ;
                    }
                    enum rip {
                      value 3 ;
                      description 'Protocol type rip.'
                                  ;
                    }
                    enum ripng {
                      value 4 ;
                      description 'Protocol type ripng.'
                                  ;
                    }
                    enum ospf {
                      value 5 ;
                      description 'Protocol type ospf.'
                                  ;
                    }
                    enum ospfv3 {
                      value 6 ;
                      description 'Protocol type ospfv3.'
                                  ;
                    }
                    enum bgp {
                      value 7 ;
                      description 'Protocol type bgp.'
                                  ;
                    }
                    enum isis {
                      value 8 ;
                      description 'Protocol type isis.'
                                  ;
                    }
                    enum special {
                      value 9 ;
                      description 'Protocol type special.'
                                  ;
                    }
                    enum arp {
                      value 10 ;
                      description 'Protocol type ARP.'
                                  ;
                    }
                    enum nd {
                      value 11 ;
                      description 'Protocol type ND.'
                                  ;
                    }
                  }
                }
              }
              ncd:revise-date 2019-05-31 ;
            }
            container ipv4-ipv6 {
              description 'Match IPv4 and IPv6 specific information strict.'
                          ;
              leaf strict {
                description 'Match IPv4 and IPv6 specific information strict.'
                            ;
                type empty ;
              }
              ncd:revise-date 2019-07-22 ;
            }
            container mac-address {
              description 'Match MAC address.'
                          ;
              presence mac-address ;
              leaf mac-addr {
                description 'Match MAC address.'
                            ;
                type ncd:mac-address ;
                mandatory true ;
              }
              ncd:revise-date 2020-10-12 ;
            }
          }
          container set {
            description "Routing policy's action."
                        ;
            presence set ;
            choice as-paths {
              description 'BGP AS path list.'
                          ;
              case as-path {
                description 'BGP AS path attribute.'
                            ;
                container as-path {
                  description 'Set string for a BGP as-path attribute.'
                              ;
                  presence 'aspath is not Mandatory'
                           ;
                  leaf operation {
                    description "As path 's prepend, replace, delete or empty f"
                              + "lag"
                                ;
                    type enumeration {
                      enum prepend {
                        value 0 ;
                        description 'The prepend operation'
                                    ;
                      }
                      enum replace {
                        value 1 ;
                        description 'The replace operation'
                                    ;
                      }
                      enum delete {
                        value 2 ;
                        description 'The delete operation'
                                    ;
                      }
                      enum empty {
                        value 3 ;
                        description 'The empty operation'
                                    ;
                      }
                    }
                  }
                  leaf value {
                    description 'Set prepend string for a BGP as-path attribute'
                              + '1.'
                                ;
                    type union {
                      type uint16 {
                        range 1..65535 {
                          description 'The range of value is from 1 to 65535.'
                                      ;
                        }
                      }
                      type ncd:asn-dot ;
                    }
                  }
                  container as-path2 {
                    description 'Set string for a BGP as-path attribute2.'
                                ;
                    presence aspath2 ;
                    leaf value {
                      description 'Set prepend string for a BGP as-path attribu'
                                + 'te2.'
                                  ;
                      type union {
                        type uint16 {
                          range 1..65535 {
                            description 'The range of value is from 1 to 65535.'
                                        ;
                          }
                        }
                        type ncd:asn-dot ;
                      }
                      mandatory true ;
                    }
                    container as-path3 {
                      description 'Set string for a BGP as-path attribute3.'
                                  ;
                      presence aspath3 ;
                      leaf value {
                        description 'Set prepend string for a BGP as-path attri'
                                  + 'bute3.'
                                    ;
                        type union {
                          type uint16 {
                            range 1..65535 {
                              description 'The range of value is from 1 to 65535.'
                                          ;
                            }
                          }
                          type ncd:asn-dot ;
                        }
                        mandatory true ;
                      }
                      container as-path4 {
                        description 'Set string for a BGP as-path attribute4.'
                                    ;
                        presence aspath4 ;
                        leaf value {
                          description 'Set prepend string for a BGP as-path att'
                                    + 'ribute4.'
                                      ;
                          type union {
                            type uint16 {
                              range 1..65535 {
                                description 'The range of value is from 1 to 65535.'
                                            ;
                              }
                            }
                            type ncd:asn-dot ;
                          }
                          mandatory true ;
                        }
                        container as-path5 {
                          description 'Set string for a BGP as-path attribute5.'
                                      ;
                          presence aspath5 ;
                          leaf value {
                            description 'Set prepend string for a BGP as-path attribute5.'
                                        ;
                            type union {
                              type uint16 {
                                range 1..65535 {
                                  description 'The range of value is from 1 to 65535.'
                                              ;
                                }
                              }
                              type ncd:asn-dot ;
                            }
                            mandatory true ;
                          }
                          container as-path6 {
                            description 'Set string for a BGP as-path attribute6.'
                                        ;
                            presence aspath6 ;
                            leaf value {
                              description 'Set prepend string for a BGP as-path attribute6.'
                                          ;
                              type union {
                                type uint16 {
                                  range 1..65535 {
                                    description 'The range of value is from 1 to 65535.'
                                                ;
                                  }
                                }
                                type ncd:asn-dot ;
                              }
                              mandatory true ;
                            }
                            container as-path7 {
                              description 'Set string for a BGP as-path attribute7.'
                                          ;
                              presence aspath7 ;
                              leaf value {
                                description 'Set prepend string for a BGP as-path attribute7.'
                                            ;
                                type union {
                                  type uint16 {
                                    range 1..65535 {
                                      description 'The range of value is from 1 to 65535.'
                                                  ;
                                    }
                                  }
                                  type ncd:asn-dot ;
                                }
                                mandatory true ;
                              }
                              container as-path8 {
                                description 'Set string for a BGP as-path attribute8.'
                                            ;
                                presence aspath8 ;
                                leaf value {
                                  description 'Set prepend string for a BGP as-path attribute8.'
                                              ;
                                  type union {
                                    type uint16 {
                                      range 1..65535 {
                                        description 'The range of value is from 1 to 65535.'
                                                    ;
                                      }
                                    }
                                    type ncd:asn-dot ;
                                  }
                                  mandatory true ;
                                }
                                container as-path9 {
                                  description 'Set string for a BGP as-path attribute9.'
                                              ;
                                  presence as-path9 ;
                                  leaf value {
                                    description 'Set prepend string for a BGP as-path attribute9.'
                                                ;
                                    type union {
                                      type uint16 {
                                        range 1..65535 {
                                          description 'The range of value is from 1 to 65535.'
                                                      ;
                                        }
                                      }
                                      type ncd:asn-dot ;
                                    }
                                    mandatory true ;
                                  }
                                  container as-path10 {
                                    description 'Set string for a BGP as-path attribute10.'
                                                ;
                                    presence as-path10 ;
                                    leaf value {
                                      description 'Set prepend string for a BGP as-path attribute10.'
                                                  ;
                                      type union {
                                        type uint16 {
                                          range 1..65535 {
                                            description 'The range of value is from 1 to 65535.'
                                                        ;
                                          }
                                        }
                                        type ncd:asn-dot ;
                                      }
                                      mandatory true ;
                                    }
                                  }
                                }
                              }
                            }
                          }
                        }
                      }
                    }
                  }
                }
              }
              case as-path-list-standard {
                description 'BGP AS path list name(standard).'
                            ;
                container as-path-list-standard {
                  description 'BGP AS path list name(standard).'
                              ;
                  presence as-path-list-standard ;
                  leaf name {
                    description 'BGP AS path list name(standard).'
                                ;
                    type string {
                      length 1..31 ;
                    }
                    mandatory true ;
                  }
                }
              }
              case replace-private-as {
                description 'Set string for a BGP as-path attribute.'
                            ;
                container replace-private-as {
                  description 'Set string for a BGP as-path attribute.'
                              ;
                  presence replace-private-as ;
                  leaf private-as {
                    description "As path's replace private AS flag."
                                ;
                    type empty ;
                    mandatory true ;
                  }
                }
                ncd:revise-date 2020-05-14 ;
              }
              ncd:revise-date 2019-05-31 ;
            }
            container community {
              description 'Set BGP community attribute.'
                          ;
              presence 'community is not Mandatory'
                       ;
              choice community {
                description 'Set BGP community attribute.'
                            ;
                mandatory true ;
                case set-community {
                  description 'Default operation:'+"\n"
                            + 'Set community [para1] [para2] [para3]'+"\n"
                            + 'Para1:'+"\n"
                            + '<0-65535>:<0-65535>  Community number in aa:nn f'
                            + 'ormat.'+"\n"
                            + 'Para2:'+"\n"
                            + '<1-4294967295>       Community number.'+"\n"
                            + 'Para3:'+"\n"
                            + 'Internet             Internet(Well known communi'
                            + 'ty).'+"\n"
                            + 'No-advertise         Do not advertise to any pee'
                            + 'r.'+"\n"
                            + 'No-export            Do not export to next AS.'+"\n"
                            + 'No-export-subconfed  Do not send outside local A'
                            + 'S.'
                              ;
                  container non-add {
                    description 'Default operation:'+"\n"
                              + 'Set community [para1] [para2] [para3]'+"\n"
                              + 'Para1:'+"\n"
                              + '<0-65535>:<0-65535>  Community number in aa:nn'
                              + ' format.'+"\n"
                              + 'Para2:'+"\n"
                              + '<1-4294967295>       Community number.'+"\n"
                              + 'Para3:'+"\n"
                              + 'Internet             Internet(Well known commu'
                              + 'nity).'+"\n"
                              + 'No-advertise         Do not advertise to any p'
                              + 'eer.'+"\n"
                              + 'No-export            Do not export to next AS.'
                              + ''+"\n"
                              + 'No-export-subconfed  Do not send outside local'
                              + ' AS.'
                                ;
                    container asns {
                      description 'Default operation:'+"\n"
                                + 'Set community <para> '+"\n"
                                + 'Para:'+"\n"
                                + '<0-65535>:<0-65535>  Community number in aa:'
                                + 'nn format.'
                                  ;
                      list asn {
                        description 'Default operation:'+"\n"
                                  + 'Set community <para1> '+"\n"
                                  + 'Para1:'+"\n"
                                  + '<0-65535>:<0-65535>  Community number in a'
                                  + 'a:nn format.'
                                    ;
                        max-elements 10 ;
                        key value ;
                        leaf value {
                          description 'Community number in aa:nn format <0-6553'
                                    + '5>:<0-65535>.'
                                      ;
                          type ncd:asn-nn {
                            pattern '((([0-9]{1,4})|([0-5]([0-9]{1,4}))|(6[0-4]'
                                  + '([0-9]{1,3}))|(65[0-4]([0-9]{1,2}))|(655[0'
                                  + '-2]([0-9]{1,1}))|(6553([0-5]{1,1}))):(([0-'
                                  + '9]{1,4})|([0-5]([0-9]{1,4}))|(6[0-4]([0-9]'
                                  + '{1,3}))|(65[0-4]([0-9]{1,2}))|(655[0-2]([0'
                                  + '-9]{1,1}))|(6553([0-5]{1,1}))))'
                                    ;
                          }
                        }
                      }
                    }
                    container enums {
                      description 'Default operation:'+"\n"
                                + 'Set community  <para>'+"\n"
                                + 'Para:'+"\n"
                                + 'Internet             Internet(Well known com'
                                + 'munity).'+"\n"
                                + 'No-advertise         Do not advertise to any'
                                + ' peer.'+"\n"
                                + 'No-export            Do not export to next A'
                                + 'S.'+"\n"
                                + 'No-export-subconfed  Do not send outside loc'
                                + 'al AS.'
                                  ;
                      list enum {
                        description 'Default operation:'+"\n"
                                  + 'Set community  <para>'+"\n"
                                  + 'Para:'+"\n"
                                  + 'Internet             Internet(Well known c'
                                  + 'ommunity).'+"\n"
                                  + 'No-advertise         Do not advertise to a'
                                  + 'ny peer.'+"\n"
                                  + 'No-export            Do not export to next'
                                  + ' AS.'+"\n"
                                  + 'No-export-subconfed  Do not send outside l'
                                  + 'ocal AS.'
                                    ;
                        max-elements 10 ;
                        key value ;
                        leaf value {
                          description 'Internet             Internet(Well known'
                                    + ' community)'+"\n"
                                    + 'No-advertise         Do not advertise to'
                                    + ' any peer'+"\n"
                                    + 'No-export            Do not export to ne'
                                    + 'xt AS'+"\n"
                                    + 'No-export-subconfed  Do not send outside'
                                    + ' local AS'
                                      ;
                          type enumeration {
                            enum internet {
                              value 15 ;
                              description 'Internet             Internet(Well known community)'
                                          ;
                            }
                            enum no-export {
                              value 1 ;
                              description 'No-export            Do not export to next AS'
                                          ;
                            }
                            enum no-advertise {
                              value 2 ;
                              description 'No-advertise         Do not advertise to any peer'
                                          ;
                            }
                            enum no-export-subconfed {
                              value 3 ;
                              description 'No-export-subconfed  Do not send outside local AS'
                                          ;
                            }
                          }
                        }
                      }
                    }
                    container uints {
                      description 'Default operation:'+"\n"
                                + 'Set community  <para> '+"\n"
                                + 'Para:'+"\n"
                                + 'Community number local AS  <1-4294967295>.'
                                  ;
                      list uint {
                        description 'Default operation:'+"\n"
                                  + 'Set community  <para> '+"\n"
                                  + 'Para:'+"\n"
                                  + 'Community number local AS  <1-4294967295>.'
                                    ;
                        max-elements 10 ;
                        key value ;
                        leaf value {
                          description 'Community number local AS  <1-4294967295'
                                    + '>.'
                                      ;
                          type uint32 {
                            range 1..4294967295 {
                              description 'The range of Community number is from 1 to 4294967295.'
                                          ;
                            }
                          }
                        }
                      }
                    }
                  }
                }
                case set-community-add {
                  description 'Set community additive [para1][para2][para3]'+"\n"
                            + 'Para1:'+"\n"
                            + '<0-65535>:<0-65535>  Community number in aa:nn f'
                            + 'ormat.'+"\n"
                            + 'Para2:'+"\n"
                            + '<1-4294967295>       Community number.'+"\n"
                            + 'Para3:'+"\n"
                            + 'Internet             Internet(Well known communi'
                            + 'ty).'+"\n"
                            + 'No-advertise         Do not advertise to any pee'
                            + 'r.'+"\n"
                            + 'No-export            Do not export to next AS.'+"\n"
                            + 'No-export-subconfed  Do not send outside local A'
                            + 'S.'
                              ;
                  container with-add {
                    description 'Set community additive [para1][para2][para3]'+"\n"
                              + 'Para1:'+"\n"
                              + '<0-65535>:<0-65535>  Community number in aa:nn'
                              + ' format.'+"\n"
                              + 'Para2:'+"\n"
                              + '<1-4294967295>       Community number.'+"\n"
                              + 'Para3:'+"\n"
                              + 'Internet             Internet(Well known commu'
                              + 'nity).'+"\n"
                              + 'No-advertise         Do not advertise to any p'
                              + 'eer.'+"\n"
                              + 'No-export            Do not export to next AS.'
                              + ''+"\n"
                              + 'No-export-subconfed  Do not send outside local'
                              + ' AS.'
                                ;
                    container asns {
                      description 'Set community additive <para> '+"\n"
                                + 'Para:'+"\n"
                                + 'Community number in aa:nn format <0-65535>:<'
                                + '0-65535>.'
                                  ;
                      list asn {
                        description 'Set community additive <para> '+"\n"
                                  + 'Para:'+"\n"
                                  + 'Community number in aa:nn format <0-65535>'
                                  + ':<0-65535>.'
                                    ;
                        max-elements 10 ;
                        key value ;
                        leaf value {
                          description 'Community number in aa:nn format  <0-655'
                                    + '35>:<0-65535>.'
                                      ;
                          type ncd:asn-nn {
                            pattern '((([0-9]{1,4})|([0-5]([0-9]{1,4}))|(6[0-4]'
                                  + '([0-9]{1,3}))|(65[0-4]([0-9]{1,2}))|(655[0'
                                  + '-2]([0-9]{1,1}))|(6553([0-5]{1,1}))):(([0-'
                                  + '9]{1,4})|([0-5]([0-9]{1,4}))|(6[0-4]([0-9]'
                                  + '{1,3}))|(65[0-4]([0-9]{1,2}))|(655[0-2]([0'
                                  + '-9]{1,1}))|(6553([0-5]{1,1}))))'
                                    ;
                          }
                        }
                      }
                    }
                    container enums {
                      description 'Set community additive  <para>'+"\n"
                                + 'Para:'+"\n"
                                + 'Internet             Internet(Well known com'
                                + 'munity).'+"\n"
                                + 'No-advertise         Do not advertise to any'
                                + ' peer.'+"\n"
                                + 'No-export            Do not export to next A'
                                + 'S.'+"\n"
                                + 'No-export-subconfed  Do not send outside loc'
                                + 'al AS.'
                                  ;
                      list enum {
                        description 'Set community additive  <para>'+"\n"
                                  + 'Para:'+"\n"
                                  + 'Internet             Internet(Well known c'
                                  + 'ommunity).'+"\n"
                                  + 'No-advertise         Do not advertise to a'
                                  + 'ny peer.'+"\n"
                                  + 'No-export            Do not export to next'
                                  + ' AS.'+"\n"
                                  + 'No-export-subconfed  Do not send outside l'
                                  + 'ocal AS.'
                                    ;
                        max-elements 10 ;
                        key value ;
                        leaf value {
                          description 'Internet             Internet(Well known'
                                    + ' community)'+"\n"
                                    + 'No-advertise         Do not advertise to'
                                    + ' any peer'+"\n"
                                    + 'No-export            Do not export to ne'
                                    + 'xt AS'+"\n"
                                    + 'No-export-subconfed  Do not send outside'
                                    + ' local AS'
                                      ;
                          type enumeration {
                            enum internet {
                              value 15 ;
                              description 'Internet             Internet(Well known community)'
                                          ;
                            }
                            enum no-export {
                              value 1 ;
                              description 'No-export            Do not export to next AS'
                                          ;
                            }
                            enum no-advertise {
                              value 2 ;
                              description 'No-advertise         Do not advertise to any peer'
                                          ;
                            }
                            enum no-export-subconfed {
                              value 3 ;
                              description 'No-export-subconfed  Do not send outside local AS'
                                          ;
                            }
                          }
                        }
                      }
                    }
                    container uints {
                      description 'Set community  additive <para> '+"\n"
                                + 'Para:'+"\n"
                                + 'Community number local AS  <1-4294967295>.'
                                  ;
                      list uint {
                        description 'Set community  additive <para> '+"\n"
                                  + 'Para:'+"\n"
                                  + 'Community number local AS  <1-4294967295>'
                                    ;
                        max-elements 10 ;
                        key value ;
                        leaf value {
                          description 'Community number local AS <1-4294967295>.'
                                      ;
                          type uint32 {
                            range 1..4294967295 {
                              description 'The range of Community number is from 1 to 4294967295.'
                                          ;
                            }
                          }
                        }
                      }
                    }
                  }
                }
                case set-community-none {
                  description 'No community attribute.The command is as follow:'
                            + ' set community none.'
                              ;
                  leaf none {
                    description 'No community attribute.'
                                ;
                    type empty ;
                    mandatory true ;
                  }
                }
                case set-community-name {
                  description 'Set community list name.'
                              ;
                  container non-additive {
                    description 'Set community list name.'
                                ;
                    container names {
                      description 'Community list name.'
                                  ;
                      list name {
                        description 'Community list name.'
                                    ;
                        max-elements 10 ;
                        key value ;
                        leaf value {
                          description 'Community list name.'
                                      ;
                          type string {
                            length 1..31 ;
                          }
                        }
                      }
                    }
                  }
                  ncd:revise-date 2017-11-20 ;
                }
                case set-community-name-add {
                  description 'Set additive community list name.'
                              ;
                  container with-additive {
                    description 'Set additive community list name.'
                                ;
                    container names {
                      description 'Community list name.'
                                  ;
                      list name {
                        description 'Community list name.'
                                    ;
                        max-elements 10 ;
                        key value ;
                        leaf value {
                          description 'Community list name.'
                                      ;
                          type string {
                            length 1..31 ;
                          }
                        }
                      }
                    }
                  }
                  ncd:revise-date 2017-11-20 ;
                }
              }
            }
            container large-community {
              description 'Set BGP large community attribute.'
                          ;
              choice large-community {
                description 'Set BGP large community attribute.'
                            ;
                case overwrite {
                  description 'Overwrite to the existing large community.'
                              ;
                  container overwrite {
                    description 'Overwrite to the existing large community.'
                                ;
                    container nums {
                      description 'Large community number.'
                                  ;
                      list num {
                        description 'Large community number.'
                                    ;
                        max-elements 10 ;
                        key value ;
                        leaf value {
                          description 'Large community number in n:n:n format <'
                                    + '0-4294967295>:<0-4294967295>:<0-42949672'
                                    + '95>.'
                                      ;
                          type string {
                            length 1..32 ;
                          }
                        }
                      }
                    }
                  }
                }
                case additive {
                  description 'Add to the existing large community.'
                              ;
                  container additive {
                    description 'Add to the existing large community.'
                                ;
                    container nums {
                      description 'Large community number.'
                                  ;
                      list num {
                        description 'Large community number.'
                                    ;
                        max-elements 10 ;
                        key value ;
                        leaf value {
                          description 'Large community number in n:n:n format <'
                                    + '0-4294967295>:<0-4294967295>:<0-42949672'
                                    + '95>.'
                                      ;
                          type string {
                            length 1..32 ;
                          }
                        }
                      }
                    }
                  }
                }
                case delete {
                  description 'Delete from the existing large community.'
                              ;
                  container delete {
                    description 'Delete from the existing large community.'
                                ;
                    container nums {
                      description 'Large community number.'
                                  ;
                      list num {
                        description 'Large community number.'
                                    ;
                        max-elements 10 ;
                        key value ;
                        leaf value {
                          description 'Large community number in n:n:n format <'
                                    + '0-4294967295>:<0-4294967295>:<0-42949672'
                                    + '95>.'
                                      ;
                          type string {
                            length 1..32 ;
                          }
                        }
                      }
                    }
                  }
                }
                case none {
                  description 'No large community attribute.'
                              ;
                  leaf none {
                    description 'No large community attribute.'
                                ;
                    type empty ;
                    mandatory true ;
                  }
                }
              }
              ncd:revise-date 2020-03-25 ;
            }
            container dampening {
              description 'Set BGP route flap dampening parameters.'
                          ;
              presence 'dampening is not Mandatory'
                       ;
              leaf half-life {
                description 'Half-life time for the penalty <1-45>.'
                            ;
                type uint32 {
                  range 1..45 {
                    description 'The range of half-life time for the penalty is'
                              + ' from 1 to 45 min.'
                                ;
                  }
                }
                units min ;
                mandatory true ;
              }
              leaf reusing {
                description 'Penalty to start reusing a route <1-20000>.'
                            ;
                type uint32 {
                  range 1..20000 {
                    description 'The range of penalty to start reusing a route '
                              + 'is from 1 to 20000.'
                                ;
                  }
                }
                mandatory true ;
              }
              leaf suppressing {
                description 'Penalty to start suppressing a route <1-20000>.'
                            ;
                type uint32 {
                  range 1..20000 {
                    description 'The range of penalty to start suppressing a ro'
                              + 'ute is from 1 to 20000.'
                                ;
                  }
                }
                mandatory true ;
              }
              leaf maxsuptime {
                description 'Maximum duration to suppress a stable route <1-255'
                          + '>.'
                            ;
                type uint32 {
                  range 1..255 {
                    description 'The range of maximum duration to suppress a st'
                              + 'able route is from 1 to 255.'
                                ;
                  }
                }
                units min ;
                mandatory true ;
              }
            }
            container dscp {
              description "Set DSCP for PBR;IP TOS(IPv6 Traffic-class),IP Prece"
                        + "dence(IPv6 Precedence) and DSCP can't co-exist in on"
                        + "e sequence."
                          ;
              presence dscp ;
              leaf value {
                description 'Type of service value.'
                            ;
                type uint8 {
                  range 0..63 {
                    description 'The range of DHCP value is from 0 to 63.'
                                ;
                  }
                }
                mandatory true ;
              }
            }
            container extcommunity {
              description 'Set BGP extcommunity attribute.'
                          ;
              presence 'extcommunity is not Mandatory'
                       ;
              container general-asns {
                description 'Set General community.'
                            ;
                presence general-asn ;
                choice general-asns {
                  description 'Set General community.'
                              ;
                  mandatory true ;
                  case general-asn {
                    description 'Set VPN extended community (3-21 characters).'
                                ;
                    container non-adds {
                      description 'Set VPN extended community (3-21 characters).'
                                  ;
                      list non-add {
                        description 'Set General community.'
                                    ;
                        max-elements 10 ;
                        key value ;
                        leaf value {
                          description 'Set General community.'
                                      ;
                          type string {
                            length 3..21 {
                              description 'The length of value is from 3 to 21 char.'
                                          ;
                            }
                          }
                        }
                      }
                    }
                  }
                  case general-asn-add {
                    description 'Add to the existing extcommunity.'
                                ;
                    container with-adds {
                      description 'Add to the existing extcommunity.'
                                  ;
                      list with-add {
                        description 'Add to the existing extcommunity.'
                                    ;
                        max-elements 10 ;
                        key value ;
                        leaf value {
                          description 'Set General community.'
                                      ;
                          type string {
                            length 3..21 {
                              description 'The length of value is from 3 to 21 char.'
                                          ;
                            }
                          }
                        }
                      }
                    }
                  }
                  case general-asn-rm {
                    description 'Remove the existing extcommunity.'
                                ;
                    leaf remove {
                      description 'Remove the existing extcommunity.'
                                  ;
                      type empty ;
                      mandatory true ;
                    }
                  }
                }
              }
              container rt-trans {
                description 'Transitive Route Target extended community.'+"\n"
                          + '<0-65535>:<0-4294967295>       VPN extended commun'
                          + 'ity.'+"\n"
                          + '<1-65535>.<0-65535>:<0-65535>  VPN extended commun'
                          + 'ity.'+"\n"
                          + 'A.B.C.D:<0-65535>              VPN extended commun'
                          + 'ity.'+"\n"
                          + 'additive                       Add to the existing'
                          + ' extcommunity.'+"\n"
                          + 'remove                         Remove the existing'
                          + ' extcommunity.'
                            ;
                presence 'rt-trans is not Mandatory'
                         ;
                choice rt-trans {
                  description 'Transitive Route Target extended community.'+"\n"
                            + '<0-65535>:<0-4294967295>       VPN extended comm'
                            + 'unity.'+"\n"
                            + '<1-65535>.<0-65535>:<0-65535>  VPN extended comm'
                            + 'unity.'+"\n"
                            + 'A.B.C.D:<0-65535>              VPN extended comm'
                            + 'unity.'+"\n"
                            + 'additive                       Add to the existi'
                            + 'ng extcommunity.'+"\n"
                            + 'remove                         Remove the existi'
                            + 'ng extcommunity.'
                              ;
                  mandatory true ;
                  case rt-trans {
                    description 'Set the extcommunity with non-additive label.'+"\n"
                              + '<0-65535>:<0-4294967295>       VPN extended co'
                              + 'mmunity.'+"\n"
                              + '<1-65535>.<0-65535>:<0-65535>  VPN extended co'
                              + 'mmunity.'+"\n"
                              + 'A.B.C.D:<0-65535>              VPN extended co'
                              + 'mmunity.'
                                ;
                    container non-adds {
                      description 'Set the extcommunity with non-additive label'
                                + '.'+"\n"
                                + '<0-65535>:<0-4294967295>       VPN extended '
                                + 'community.'+"\n"
                                + '<1-65535>.<0-65535>:<0-65535>  VPN extended '
                                + 'community.'+"\n"
                                + 'A.B.C.D:<0-65535>              VPN extended '
                                + 'community.'
                                  ;
                      list non-add {
                        description 'Set the extcommunity with non-additive lab'
                                  + 'el.'+"\n"
                                  + '<0-65535>:<0-4294967295>       VPN extende'
                                  + 'd community.'+"\n"
                                  + '<1-65535>.<0-65535>:<0-65535>  VPN extende'
                                  + 'd community.'+"\n"
                                  + 'A.B.C.D:<0-65535>              VPN extende'
                                  + 'd community.'
                                    ;
                        max-elements 10 ;
                        key value ;
                        leaf value {
                          description '<0-65535>:<0-4294967295>       VPN exten'
                                    + 'ded community.'+"\n"
                                    + '<1-65535>.<0-65535>:<0-65535>  VPN exten'
                                    + 'ded community.'+"\n"
                                    + 'A.B.C.D:<0-65535>              VPN exten'
                                    + 'ded community.'
                                      ;
                          type union {
                            type ncd:asn-nn ;
                            type ncd:asnd-nn ;
                            type ncd:ipadd-nn ;
                          }
                        }
                      }
                    }
                  }
                  case rt-trans-add {
                    description 'Set the extcommunity with additive label.'+"\n"
                              + '<0-65535>:<0-4294967295>       VPN extended co'
                              + 'mmunity.'+"\n"
                              + '<1-65535>.<0-65535>:<0-65535>  VPN extended co'
                              + 'mmunity.'+"\n"
                              + 'A.B.C.D:<0-65535>              VPN extended co'
                              + 'mmunity.'
                                ;
                    container with-adds {
                      description 'Set the extcommunity with additive label.'+"\n"
                                + '<0-65535>:<0-4294967295>       VPN extended '
                                + 'community.'+"\n"
                                + '<1-65535>.<0-65535>:<0-65535>  VPN extended '
                                + 'community.'+"\n"
                                + 'A.B.C.D:<0-65535>              VPN extended '
                                + 'community.'
                                  ;
                      list with-add {
                        description 'Set the extcommunity with additive label.'+"\n"
                                  + '<0-65535>:<0-4294967295>       VPN extende'
                                  + 'd community.'+"\n"
                                  + '<1-65535>.<0-65535>:<0-65535>  VPN extende'
                                  + 'd community.'+"\n"
                                  + 'A.B.C.D:<0-65535>              VPN extende'
                                  + 'd community.'
                                    ;
                        max-elements 10 ;
                        key value ;
                        leaf value {
                          description 'Set the extcommunity with additive label'
                                    + '.'+"\n"
                                    + '<0-65535>:<0-4294967295>       VPN exten'
                                    + 'ded community.'+"\n"
                                    + '<1-65535>.<0-65535>:<0-65535>  VPN exten'
                                    + 'ded community.'+"\n"
                                    + 'A.B.C.D:<0-65535>              VPN exten'
                                    + 'ded community.'
                                      ;
                          type union {
                            type ncd:asn-nn ;
                            type ncd:asnd-nn ;
                            type ncd:ipadd-nn ;
                          }
                        }
                      }
                    }
                  }
                  case rt-trans-rm {
                    description 'Remove the existing extcommunity.'
                                ;
                    leaf remove {
                      description 'Remove the existing extcommunity.'
                                  ;
                      type empty ;
                      mandatory true ;
                    }
                  }
                }
              }
              container soo-trans {
                description 'Transitive Site-of-Origin extended community.'+"\n"
                          + '<0-65535>:<0-4294967295>       VPN extended commun'
                          + 'ity.'+"\n"
                          + '<1-65535>.<0-65535>:<0-65535>  VPN extended commun'
                          + 'ity.'+"\n"
                          + 'A.B.C.D:<0-65535>              VPN extended commun'
                          + 'ity.'+"\n"
                          + 'Remove                         Remove the existing'
                          + ' extcommunity.'
                            ;
                presence 'soo-trans is not Mandatory'
                         ;
                choice soo-trans {
                  description 'Transitive Site-of-Origin extended community.'+"\n"
                            + '<0-65535>:<0-4294967295>       VPN extended comm'
                            + 'unity.'+"\n"
                            + '<1-65535>.<0-65535>:<0-65535>  VPN extended comm'
                            + 'unity.'+"\n"
                            + 'A.B.C.D:<0-65535>              VPN extended comm'
                            + 'unity.'+"\n"
                            + 'Remove                         Remove the existi'
                            + 'ng extcommunity.'
                              ;
                  mandatory true ;
                  case soo-trans {
                    description 'Set transitive Site-of-Origin extended communi'
                              + 'ty.'
                                ;
                    leaf value {
                      description 'Set transitive Site-of-Origin extended commu'
                                + 'nity.'+"\n"
                                + '<1-65535>.<0-65535>:<0-65535> VPN extended c'
                                + 'ommunity.'+"\n"
                                + '<0-65535>:<0-4294967295>      VPN extended c'
                                + 'ommunity.'+"\n"
                                + 'A.B.C.D:<0-65535>             VPN extended c'
                                + 'ommunity.'
                                  ;
                      type union {
                        type ncd:asn-nn ;
                        type ncd:asnd-nn ;
                        type ncd:ipadd-nn ;
                      }
                      mandatory true ;
                    }
                  }
                  case soo-trans-rm {
                    description 'Remove the existing extcommunity .'
                                ;
                    leaf remove {
                      description 'Use to romove exsited VPN extcommunity.'
                                  ;
                      type empty ;
                      mandatory true ;
                    }
                  }
                }
              }
              container multicast-rt {
                description 'Set the advertised BGP route carried multicast rou'
                          + 'te-target or remove multicast route-target in the '
                          + 'received  BGP route.'
                            ;
                leaf value {
                  description 'additive  Set the advertised BGP route carried m'
                            + 'ulticast route-target;'+"\n"
                            + 'remove    Remove multicast route-target in the r'
                            + 'eceived  BGP route.'
                              ;
                  type enumeration {
                    enum additive {
                      value 1 ;
                      description 'additive    Set the advertised BGP route car'
                                + 'ried multicast route-target'
                                  ;
                    }
                    enum remove {
                      value 2 ;
                      description 'remove     Remove multicast route-target in '
                                + 'the received  BGP route'
                                  ;
                    }
                  }
                }
                ncd:revise-date 2020-07-02 ;
              }
            }
            container global {
              description "Set global route for PBR.VRF, global and next-hop(or"
                        + " interface) can't co-exist in one sequence."
                          ;
              presence global ;
              leaf set-global {
                description 'Set global label for PBR.The command is as follow:'
                          + 'Set global.'
                            ;
                type empty ;
                mandatory true ;
              }
              container ip {
                description 'Set IP specific information.'
                            ;
                container next-hop {
                  description 'Set IP address of next hop.'
                              ;
                  presence next-hop ;
                  leaf ipv4-addr {
                    description 'Set IP address of next hop.'
                                ;
                    type ncd:ipv4-address ;
                    mandatory true ;
                  }
                }
              }
            }
            container interfaces {
              description "Set output interface.VRF, global and next-hop(or int"
                        + "erface) can't co-exist in one sequence."
                          ;
              list interface {
                description 'Set output interface.'
                            ;
                key ifname ;
                leaf ifname {
                  description 'Set output interface name.'
                              ;
                  type ncd:ifname ;
                }
              }
            }
            container ipv4 {
              description 'Set IPv4 specific information.'
                          ;
              container metric {
                description 'Set metric value for destination routing protocol.'
                            ;
                presence 'metric is not Mandatory'
                         ;
                leaf add-del {
                  description 'Add metric  +;   
Del metric  -.'
                              ;
                  type enumeration {
                    enum + {
                      value 1 ;
                      description 'Add metric  +'
                                  ;
                    }
                    enum - {
                      value 2 ;
                      description 'Del metric  -'
                                  ;
                    }
                  }
                }
                leaf value {
                  description 'Metric value <0-4294967295>.'
                              ;
                  type uint32 {
                    range 0..4294967295 {
                      description 'The range of metric-value is from 0 to 42949'
                                + '67295.'
                                  ;
                    }
                  }
                  mandatory true ;
                }
              }
              container metric-type {
                description 'Set type of metric for destination routing protoco'
                          + 'l.'
                            ;
                presence 'metric-type is not Mandatory'
                         ;
                leaf value {
                  description 'Set type of metric for destination routing proto'
                            + 'col;'+"\n"
                            + 'External  IS-IS external metric;'+"\n"
                            + 'Internal  IS-IS internal metric;'+"\n"
                            + 'Type-1    OSPF external type 1 metric;'+"\n"
                            + 'Type-2    OSPF external type 2 metric.'
                              ;
                  type enumeration {
                    enum internal {
                      value 1 ;
                      description 'Internal  IS-IS internal metric'
                                  ;
                    }
                    enum external {
                      value 2 ;
                      description 'External  IS-IS external metric'
                                  ;
                    }
                    enum type-1 {
                      value 3 ;
                      description 'Type-1    OSPF external type 1 metric'
                                  ;
                    }
                    enum type-2 {
                      value 4 ;
                      description 'Type-2    OSPF external type 2 metric'
                                  ;
                    }
                  }
                  mandatory true ;
                }
              }
              container next-hops {
                description "Set IP next hop address for PBR(max quantity 10).V"
                          + "RF, global and next-hop(or interface) can't co-exi"
                          + "st in one sequence."
                            ;
                list next-hop {
                  description 'Set IP next hop address for PBR.'
                              ;
                  max-elements 10 ;
                  key ipv4-addr ;
                  leaf ipv4-addr {
                    description 'Set IPv4 address.'
                                ;
                    type ncd:ipv4-address ;
                  }
                  leaf track {
                    description 'Set track name.'
                                ;
                    type string {
                      length 1..31 {
                        description 'The length of track name is from 1 to 31 c'
                                  + 'har.'
                                    ;
                      }
                    }
                  }
                }
              }
              container path {
                description 'Set output ethernet interface.'
                            ;
                presence path ;
                container interface {
                  description "Set output ethernet interface.VRF, global and ne"
                            + "xt-hop(or interface) can't co-exist in one seque"
                            + "nce."
                              ;
                  leaf ifname {
                    description 'Set the existence ethernet interface name of t'
                              + 'he supported port type.'
                                ;
                    type ncd:ifname ;
                    mandatory true ;
                  }
                  container next-hop {
                    description 'Set next-hop.'
                                ;
                    leaf ipv4-addr {
                      description 'IP address of next hop.'
                                  ;
                      type ncd:ipv4-address ;
                      mandatory true ;
                    }
                  }
                }
              }
              container precedence {
                description "Set precedence field.IP TOS(IPv6 Traffic-class),IP"
                          + " Precedence(IPv6 Precedence) and DSCP can't co-exi"
                          + "st in one sequence."
                            ;
                presence precedence ;
                choice precedence-value {
                  description '<0-7>           Precedence value;'+"\n"
                            + 'Critical        Set critical precedence (5);'+"\n"
                            + 'Flash           Set flash precedence (3);'+"\n"
                            + 'Flash-override  Set flash override precedence (4'
                            + ');'+"\n"
                            + 'Immediate       Set immediate precedence (2);'+"\n"
                            + 'Internet        Set internetwork control precede'
                            + 'nce (6);'+"\n"
                            + 'Network         Set network control precedence ('
                            + '7);'+"\n"
                            + 'Priority        Set priority precedence (1);'+"\n"
                            + 'Routine         Set routine precedence (0).'
                              ;
                  mandatory true ;
                  case int-type {
                    description 'Set precedence value.'
                                ;
                    leaf int-value {
                      description 'Set precedence value.'
                                  ;
                      type uint16 {
                        range 0..7 {
                          description 'The range of Precedence value is from 0 '
                                    + 'to 7.'
                                      ;
                        }
                      }
                      mandatory true ;
                    }
                  }
                  case enum-type {
                    description 'Critical        Set critical precedence (5);'+"\n"
                              + 'Flash           Set flash precedence (3);'+"\n"
                              + 'Flash-override  Set flash override precedence '
                              + '(4);'+"\n"
                              + 'Immediate       Set immediate precedence (2);'+"\n"
                              + 'Internet        Set internetwork control prece'
                              + 'dence (6);'+"\n"
                              + 'Network         Set network control precedence'
                              + ' (7);'+"\n"
                              + 'Priority        Set priority precedence (1);'+"\n"
                              + 'Routine         Set routine precedence (0).'
                                ;
                    leaf enum-value {
                      description 'Critical        Set critical precedence (5);'
                                + ''+"\n"
                                + 'Flash           Set flash precedence (3);'+"\n"
                                + 'Flash-override  Set flash override precedenc'
                                + 'e (4);'+"\n"
                                + 'Immediate       Set immediate precedence (2)'
                                + ';'+"\n"
                                + 'Internet        Set internetwork control pre'
                                + 'cedence (6);'+"\n"
                                + 'Network         Set network control preceden'
                                + 'ce (7);'+"\n"
                                + 'Priority        Set priority precedence (1);'
                                + ''+"\n"
                                + 'Routine         Set routine precedence (0).'
                                  ;
                      type enumeration {
                        enum routine {
                          value 0 ;
                          description 'Routine         Set routine precedence ('
                                    + '0)'
                                      ;
                        }
                        enum priority {
                          value 1 ;
                          description 'Priority        Set priority precedence '
                                    + '(1)'
                                      ;
                        }
                        enum network {
                          value 7 ;
                          description 'Network         Set network control prec'
                                    + 'edence (7)'
                                      ;
                        }
                        enum internet {
                          value 6 ;
                          description 'Internet        Set internetwork control'
                                    + ' precedence (6)'
                                      ;
                        }
                        enum immediate {
                          value 2 ;
                          description 'Immediate       Set immediate precedence'
                                    + ' (2)'
                                      ;
                        }
                        enum flash-override {
                          value 4 ;
                          description 'Flash-override  Set flash override prece'
                                    + 'dence (4)'
                                      ;
                        }
                        enum flash {
                          value 3 ;
                          description 'Flash           Set flash precedence (3)'
                                      ;
                        }
                        enum critical {
                          value 5 ;
                          description 'Critical        Set critical precedence '
                                    + '(5)'
                                      ;
                        }
                      }
                      mandatory true ;
                    }
                  }
                }
              }
              container tag {
                description 'Set tag value for destination routing protocol.'
                            ;
                presence 'tag is not Mandatory'
                         ;
                leaf value {
                  description 'Tag value.'
                              ;
                  type uint32 {
                    range 0..4294967295 {
                      description 'The range of tag-value is from 0 to 42949672'
                                + '95.'
                                  ;
                    }
                  }
                  mandatory true ;
                }
              }
              container tos {
                description "Set type of service field.IP TOS(IPv6 Traffic-clas"
                          + "s),IP Precedence(IPv6 Precedence) and DSCP can't c"
                          + "o-exist in one sequence."
                            ;
                presence ip-tos ;
                choice tos-value {
                  description 'Max-reliability    Set max reliable TOS (2);'+"\n"
                            + 'Max-throughput     Set max throughput TOS (4);'+"\n"
                            + 'Min-delay          Set min delay TOS (8);'+"\n"
                            + 'Min-monetary-cost  Set min monetary cost TOS (1)'
                            + ';'+"\n"
                            + 'Normal             Set normal TOS (0);'+"\n"
                            + '<0-15>             Type of service value.'
                              ;
                  mandatory true ;
                  case int-type {
                    description 'Set type of service value.'
                                ;
                    leaf int-value {
                      description 'Set type of service value.'
                                  ;
                      type uint16 {
                        range 0..15 {
                          description 'The range of type of service value is fr'
                                    + 'om 0 to 15.'
                                      ;
                        }
                      }
                      mandatory true ;
                    }
                  }
                  case enum-type {
                    description 'Max-reliability    Set max reliable TOS (2);'+"\n"
                              + 'Max-throughput     Set max throughput TOS (4);'
                              + ''+"\n"
                              + 'Min-delay          Set min delay TOS (8);'+"\n"
                              + 'Min-monetary-cost  Set min monetary cost TOS ('
                              + '1);'+"\n"
                              + 'Normal             Set normal TOS (0).'
                                ;
                    leaf enum-value {
                      description 'Max-reliability    Set max reliable TOS (2);'
                                + ''+"\n"
                                + 'Max-throughput     Set max throughput TOS (4'
                                + ');'+"\n"
                                + 'Min-delay          Set min delay TOS (8);'+"\n"
                                + 'Min-monetary-cost  Set min monetary cost TOS'
                                + ' (1);'+"\n"
                                + 'Normal             Set normal TOS (0).'
                                  ;
                      type enumeration {
                        enum normal {
                          value 0 ;
                          description 'Set normal TOS'
                                      ;
                        }
                        enum min-monetary-cost {
                          value 1 ;
                          description 'Set min monetary cost TOS'
                                      ;
                        }
                        enum max-reliability {
                          value 2 ;
                          description 'Set max reliable TOS'
                                      ;
                        }
                        enum max-throughput {
                          value 4 ;
                          description 'Set max throughput TOS'
                                      ;
                        }
                        enum min-delay {
                          value 8 ;
                          description 'Set min delay TOS'
                                      ;
                        }
                      }
                      mandatory true ;
                    }
                  }
                }
              }
              container paths {
                if-feature strict-policy ;
                description 'Set output ethernet interface.'
                            ;
                list path {
                  description 'Set output ethernet interface.'
                              ;
                  key 'ifname ipv4-addr'
                      ;
                  leaf ifname {
                    description 'Set the existed ethernet interface name of the'
                              + ' supported port type.'
                                ;
                    type ncd:ifname ;
                  }
                  leaf ipv4-addr {
                    description 'IP address of next hop.'
                                ;
                    type ncd:ipv4-address ;
                  }
                }
                ncd:revise-date 2016-08-18 ;
              }
              container vxlan-tunnel {
                description 'Set VXLAN tunnel specific information'
                            ;
                presence vxlan-tunnel ;
                leaf source {
                  description 'Set VXLAN tunnel source address.'
                              ;
                  type ncd:ipv4-address ;
                  mandatory true ;
                }
                ncd:revise-date 2016-11-17 ;
              }
              container sr-policy {
                description 'Set sr-policy information.'
                            ;
                presence 'sr-policy is not Mandatory'
                         ;
                leaf color {
                  description 'The color value.'
                              ;
                  type uint32 {
                    range 1..4294967295 {
                      description 'The range of color is from 1 to 4294967295.'
                                  ;
                    }
                  }
                  mandatory true ;
                }
                leaf ipv4-addr {
                  description 'Set IPv4 address.'
                              ;
                  type ncd:ipv4-address ;
                  mandatory true ;
                }
                ncd:revise-date 2020-02-26 ;
              }
            }
            container ipv6 {
              description 'Set IPV6 specific information.'
                          ;
              container metric {
                description 'Set metric value for destination routing protocol.'
                            ;
                presence 'metric is not Mandatory'
                         ;
                leaf add-del {
                  description 'Add metric +;
Del metric -.'
                              ;
                  type enumeration {
                    enum + {
                      value 1 ;
                      description 'Add metric +'
                                  ;
                    }
                    enum - {
                      value 2 ;
                      description 'Del metric -'
                                  ;
                    }
                  }
                }
                leaf value {
                  description 'Metric value  <0-4294967295>.'
                              ;
                  type uint32 {
                    range 0..4294967295 {
                      description 'The range of metric-value is from 0 to 42949'
                                + '67295.'
                                  ;
                    }
                  }
                  mandatory true ;
                }
              }
              container metric-type {
                description 'Set type of metric for destination routing protoco'
                          + 'l.'
                            ;
                presence 'metric-type is not Mandatory'
                         ;
                leaf value {
                  description 'Set type of metric for destination routing proto'
                            + 'col.'+"\n"
                            + 'External  IS-IS external metric.'+"\n"
                            + 'Internal  IS-IS internal metric.'+"\n"
                            + 'Type-1    OSPF external type 1 metric.'+"\n"
                            + 'Type-2    OSPF external type 2 metric.'
                              ;
                  type enumeration {
                    enum internal {
                      value 1 ;
                      description 'Internal  IS-IS internal metric'
                                  ;
                    }
                    enum external {
                      value 2 ;
                      description 'External  IS-IS external metric'
                                  ;
                    }
                    enum type-1 {
                      value 3 ;
                      description 'Type-1    OSPF external type 1 metric'
                                  ;
                    }
                    enum type-2 {
                      value 4 ;
                      description 'Type-2    OSPF external type 2 metric'
                                  ;
                    }
                  }
                  mandatory true ;
                }
              }
              container next-hop {
                description 'Set ipv6 next-hop items contain set ipv6 next-hop '
                          + '<ipv6-addr> and set ipv6 next-hop peer-address.'
                            ;
                presence next-hop ;
                choice next-hop {
                  description 'Set IPv6 Next hop address.'
                              ;
                  case normal {
                    description 'Set IPv6 Next hop address (max quantity 10).'
                                ;
                    container next-hops {
                      description 'Set IPv6 Next hop address (max quantity 10).'
                                  ;
                      list next-hop {
                        description 'Set IPv6 Next hop address.'
                                    ;
                        max-elements 10 ;
                        key ipv6-addr ;
                        leaf ipv6-addr {
                          description 'Set IPV6 address.'
                                      ;
                          type ncd:ipv6-address ;
                        }
                      }
                    }
                  }
                  case peer-addr {
                    description 'Peer-address for BGP'
                                ;
                    container peer {
                      description 'Peer-address for BGP'
                                  ;
                      presence peer ;
                      leaf peer-address {
                        description 'Peer-address for BGP'
                                    ;
                        type empty ;
                        mandatory true ;
                      }
                    }
                  }
                  case blackhole {
                    description 'Blackhole route for BGP'
                                ;
                    container blackholes {
                      description 'blackhole route for BGP'
                                  ;
                      presence blackholes ;
                      leaf blackhole {
                        description 'blackhole route for BGP'
                                    ;
                        type empty ;
                        mandatory true ;
                      }
                    }
                    ncd:revise-date 2020-08-13 ;
                  }
                }
              }
              container path {
                description 'Set output ethernet interface.'
                            ;
                presence ipv6-path-interface ;
                container interface {
                  description 'Set output ethernet interface.'
                              ;
                  leaf ifname {
                    description 'Set the existence ethernet interface name of t'
                              + 'he supported port type.'
                                ;
                    type ncd:ifname ;
                    mandatory true ;
                  }
                  container next-hop {
                    description 'Set next-hop.'
                                ;
                    leaf ipv6-addr {
                      description 'IPv6 address of next hop.'
                                  ;
                      type ncd:ipv6-address ;
                      mandatory true ;
                    }
                  }
                }
              }
              container precedence {
                description "Set precedence field.IP TOS(IPv6 Traffic-class),IP"
                          + " Precedence(IPv6 Precedence) and DSCP can't co-exi"
                          + "st in one sequence."
                            ;
                presence 'ipv6-precedence is not Mandatory'
                         ;
                choice precedence-value {
                  description 'Critical        Set critical precedence (5).'+"\n"
                            + 'Flash           Set flash precedence (3).'+"\n"
                            + 'Flash-override  Set flash override precedence (4'
                            + ').'+"\n"
                            + 'Immediate       Set immediate precedence (2).'+"\n"
                            + 'Internet        Set internetwork control precede'
                            + 'nce (6).'+"\n"
                            + 'Network         Set network control precedence ('
                            + '7).'+"\n"
                            + 'Priority        Set priority precedence (1).'+"\n"
                            + 'Routine         Set routine precedence (0).'+"\n"
                            + '<0-7>           Precedence value.'
                              ;
                  mandatory true ;
                  case int-type {
                    description 'Precedence value<0~7>.'
                                ;
                    leaf int-value {
                      description 'Precedence value<0~7>.'
                                  ;
                      type uint16 {
                        range 0..7 {
                          description 'The range of  Precedence value is from 0'
                                    + ' to 7.'
                                      ;
                        }
                      }
                      mandatory true ;
                    }
                  }
                  case enum-type {
                    description 'Critical        Set critical precedence (5).'+"\n"
                              + 'Flash           Set flash precedence (3).'+"\n"
                              + 'Flash-override  Set flash override precedence '
                              + '(4).'+"\n"
                              + 'Immediate       Set immediate precedence (2).'+"\n"
                              + 'Internet        Set internetwork control prece'
                              + 'dence (6).'+"\n"
                              + 'Network         Set network control precedence'
                              + ' (7).'+"\n"
                              + 'Priority        Set priority precedence (1).'+"\n"
                              + 'Routine         Set routine precedence (0).'
                                ;
                    leaf enum-value {
                      description 'Critical        Set critical precedence (5).'
                                + ''+"\n"
                                + 'Flash           Set flash precedence (3).'+"\n"
                                + 'Flash-override  Set flash override precedenc'
                                + 'e (4).'+"\n"
                                + 'Immediate       Set immediate precedence (2)'
                                + '.'+"\n"
                                + 'Internet        Set internetwork control pre'
                                + 'cedence (6).'+"\n"
                                + 'Network         Set network control preceden'
                                + 'ce (7).'+"\n"
                                + 'Priority        Set priority precedence (1).'
                                + ''+"\n"
                                + 'Routine         Set routine precedence (0).'
                                  ;
                      type enumeration {
                        enum routine {
                          value 0 ;
                          description 'Set routine precedence'
                                      ;
                        }
                        enum priority {
                          value 1 ;
                          description 'Set priority precedence'
                                      ;
                        }
                        enum network {
                          value 7 ;
                          description 'Set network precedence'
                                      ;
                        }
                        enum internet {
                          value 6 ;
                          description 'Set internet precedence'
                                      ;
                        }
                        enum immediate {
                          value 2 ;
                          description 'Set immediate precedence'
                                      ;
                        }
                        enum flash-override {
                          value 4 ;
                          description 'Set flash-override precedence'
                                      ;
                        }
                        enum flash {
                          value 3 ;
                          description 'Set flash precedence'
                                      ;
                        }
                        enum critical {
                          value 5 ;
                          description 'Set critical precedence'
                                      ;
                        }
                      }
                      mandatory true ;
                    }
                  }
                }
              }
              container tag {
                description 'Set tag value for destination routing protocol.'
                            ;
                presence 'tag is not Mandatory'
                         ;
                leaf value {
                  description 'Tag value.'
                              ;
                  type uint32 {
                    range 0..4294967295 {
                      description 'The range of tag-value is from 0 to 42949672'
                                + '95.'
                                  ;
                    }
                  }
                  mandatory true ;
                }
              }
              container traffic-class {
                description "Set IPv6's traffic-class.IP TOS(IPv6 Traffic-class"
                          + "),IP Precedence(IPv6 Precedence) and DSCP can't co"
                          + "-exist in one sequence."
                            ;
                presence 'traffic-class is not Mandatory'
                         ;
                leaf value {
                  description 'Set value of IPv6 traffic-class.'
                              ;
                  type uint8 {
                    range 0..255 {
                      description 'The range of Value of IPv6 traffic-class is '
                                + 'from 0 to 255.'
                                  ;
                    }
                  }
                  mandatory true ;
                }
              }
              container paths {
                if-feature strict-policy ;
                description 'Set output ethernet interface.'
                            ;
                list path {
                  description 'Set output ethernet interface.'
                              ;
                  key 'ifname ipv6-addr'
                      ;
                  leaf ifname {
                    description 'Set the existed ethernet interface name of the'
                              + ' supported port type.'
                                ;
                    type ncd:ifname ;
                  }
                  leaf ipv6-addr {
                    description 'IPv6 address of next hop.'
                                ;
                    type ncd:ipv6-address ;
                  }
                }
                ncd:revise-date 2016-08-18 ;
              }
              container vxlan-tunnel {
                description 'Set VXLAN tunnel specific information'
                            ;
                presence vxlan-tunnel ;
                leaf source {
                  description 'Set VXLAN tunnel source IPv6 address.'
                              ;
                  type ncd:ipv6-address ;
                  mandatory true ;
                }
                ncd:revise-date 2019-11-06 ;
              }
              container gw-ip {
                description 'Gateway IPv6 address.'
                            ;
                presence 'gw-ip is not Mandatory'
                         ;
                leaf ipv6-addr {
                  description 'Set IPv6 address.'
                              ;
                  type ncd:ipv6-address ;
                  mandatory true ;
                }
                ncd:revise-date 2019-09-26 ;
              }
              container sr-policy {
                description 'Set sr-policy information.'
                            ;
                presence 'sr-policy is not Mandatory'
                         ;
                leaf color {
                  description 'The color value.'
                              ;
                  type uint32 {
                    range 1..4294967295 {
                      description 'The range of color is from 1 to 4294967295.'
                                  ;
                    }
                  }
                  mandatory true ;
                }
                leaf ipv6-addr {
                  description 'Set IPv6 address.'
                              ;
                  type ncd:ipv6-address ;
                  mandatory true ;
                }
                ncd:revise-date 2020-02-26 ;
              }
            }
            container level {
              description 'Set where to import route.'
                          ;
              presence 'level is not Mandatory'
                       ;
              leaf value {
                description 'Level-1    Import into a level-1 area;'+"\n"
                          + 'Level-1-2  Import into level-1 and level-2;'+"\n"
                          + 'Level-2    Import into level-2 sub-domain.'
                            ;
                type enumeration {
                  enum level-1 {
                    value 1 ;
                    description 'Level-1    Import into a level-1 area'
                                ;
                  }
                  enum level-2 {
                    value 2 ;
                    description 'Level-2    Import into level-2 sub-domain'
                                ;
                  }
                  enum level-1-2 {
                    value 3 ;
                    description 'Level-1-2  Import into level-1 and level-2'
                                ;
                  }
                }
                mandatory true ;
              }
            }
            container local-preference {
              description 'Set BGP local preference path attribute.'
                          ;
              presence 'local-preference is not Mandatory'
                       ;
              leaf add-del {
                description 'Add local preference  +; Del local preference  -.'
                            ;
                type enumeration {
                  enum + {
                    value 1 ;
                    description 'Add local preference  +'
                                ;
                  }
                  enum - {
                    value 2 ;
                    description 'Del local preference  -'
                                ;
                  }
                }
                ncd:revise-date 2018-12-19 ;
              }
              leaf value {
                description 'Preference value <0~4294967295>.'
                            ;
                type uint32 {
                  range 0..4294967295 {
                    description 'The range of Preference value is from 0 to 429'
                              + '4967295.'
                                ;
                  }
                }
                mandatory true ;
              }
            }
            container mpls-label {
              description 'Set MPLS label for prefix.'
                          ;
              presence 'mpls-lable is not Mandatory'
                       ;
              leaf mpls-label {
                description "Set MPLS label's value for prefix."
                            ;
                type empty ;
                mandatory true ;
              }
            }
            container next-hop {
              description 'Set next-hop items contain set next-hop <ipv4-addr> '
                        + 'and set next-hop peer-address.'
                          ;
              presence next-hop ;
              choice next-hop {
                description "Set IP address of next hop for route(max quantity "
                          + "10).VRF, global and next-hop(or interface) can't c"
                          + "o-exist in one sequence."
                            ;
                case normal {
                  description "Set IP address of next hop for route(max quantit"
                            + "y 10).VRF, global and next-hop(or interface) can"
                            + "'t co-exist in one sequence."
                              ;
                  container next-hops {
                    description "Set IP address of next hop for route(max quant"
                              + "ity 10).VRF, global and next-hop(or interface)"
                              + " can't co-exist in one sequence."
                                ;
                    list next-hop {
                      description 'Set IP address of next hop for route.'
                                  ;
                      max-elements 10 ;
                      key ipv4-addr ;
                      leaf ipv4-addr {
                        description 'Set IPv4 address.'
                                    ;
                        type ncd:ipv4-address ;
                      }
                    }
                  }
                }
                case peer-addr {
                  description 'Peer-address for BGP'
                              ;
                  container peer {
                    description 'Peer-address for BGP'
                                ;
                    presence peer ;
                    leaf peer-address {
                      description 'Peer-address for BGP'
                                  ;
                      type empty ;
                      mandatory true ;
                    }
                  }
                }
                case blackhole {
                  description 'Blackhole route for BGP'
                              ;
                  container blackholes {
                    description 'blackhole route for BGP'
                                ;
                    presence blackholes ;
                    leaf blackhole {
                      description 'blackhole route for BGP'
                                  ;
                      type empty ;
                      mandatory true ;
                    }
                  }
                  ncd:revise-date 2020-08-13 ;
                }
              }
            }
            container origin {
              description 'Set BGP origin code.'
                          ;
              presence 'origin is not Mandatory'
                       ;
              leaf value {
                description 'EGP         Remote EGP;'+"\n"
                          + 'IGP         Local IGP;'+"\n"
                          + 'Incomplete  Unknown heritage.'
                            ;
                type enumeration {
                  enum igp {
                    value 0 ;
                    description 'IGP         Local IGP'
                                ;
                  }
                  enum egp {
                    value 1 ;
                    description 'EGP         Remote EGP'
                                ;
                  }
                  enum incomplete {
                    value 2 ;
                    description 'Incomplete  Unknown heritage'
                                ;
                  }
                }
                mandatory true ;
              }
            }
            container policy-priority {
              description 'Set policy priority for PBR.'
                          ;
              presence policy-priority ;
              leaf value {
                description 'Value of policy priority <0~7>.'
                            ;
                type uint8 {
                  range 0..7 {
                    description 'The range of value is from 0 to 7.'
                                ;
                  }
                }
                mandatory true ;
              }
            }
            container path-selection {
              description 'Set BGP path-selection.'
                          ;
              presence path-selection ;
              leaf path-type {
                description 'All       :Path for imitating iBGP full-mesh;'+"\n"
                          + 'Backup    :Path for rapid convergence;'+"\n"
                          + 'Best-path :Path for load sharing;'+"\n"
                          + 'Group-best:Path for elimination of routing oscilla'
                          + 'tion.'
                            ;
                type enumeration {
                  enum all {
                    value 1 ;
                    description 'Path for imitating iBGP full-mesh'
                                ;
                  }
                  enum backup {
                    value 2 ;
                    description 'Path for rapid convergence'
                                ;
                  }
                  enum best-path {
                    value 3 ;
                    description 'Path for load sharing'
                                ;
                  }
                  enum group-best {
                    value 4 ;
                    description 'Path for elimination of routing oscillation'
                                ;
                  }
                }
                mandatory true ;
              }
              leaf path-number {
                description 'Set path numbers.'
                            ;
                type uint16 {
                  range 1..32 {
                    description 'The range of path-number is from 1 to 32.'
                                ;
                  }
                }
                mandatory true ;
              }
              leaf advertise {
                description 'Advertising the path selected outward.'
                            ;
                type empty ;
              }
              leaf install {
                description 'Manner of sending to forwarding table.'
                            ;
                type empty ;
              }
              leaf multipath-protect {
                description 'Manner of sending to forwarding table.'
                            ;
                type empty ;
              }
            }
            container qos-id {
              description 'Set QoS ID of routing.'
                          ;
              presence 'qos-id is not Mandatory'
                       ;
              leaf value {
                description 'Set QoS ID of routing.'
                            ;
                type uint16 {
                  range 1..16000 {
                    description 'The range of Qos ID is from 1 to 16000.'
                                ;
                  }
                }
                mandatory true ;
              }
            }
            container traffic-index {
              description 'Set BGP traffic index.'
                          ;
              presence traffic-index ;
              leaf value {
                description 'Set BGP traffic index.'
                            ;
                type uint16 {
                  range 1..64 {
                    description 'The range of the value is from 1 to 64.'
                                ;
                  }
                }
                mandatory true ;
              }
            }
            container vrf {
              description "Set virtual route forwarding name.VRF, global and ne"
                        + "xt-hop(or interface) can't co-exist in one sequence."
                          ;
              presence 'vrf is not Mandatory'
                       ;
              leaf name {
                description 'Virtual route forwarding name (1-32 characters).'
                            ;
                type string {
                  length 1..32 {
                    description 'The length of vrfname is from 1 to 32 char.'
                                ;
                  }
                }
                mandatory true ;
              }
              container ip {
                description 'Set IP specific information.'
                            ;
                container next-hop {
                  description 'Set next hop address.'
                              ;
                  presence next-hop ;
                  leaf ipv4-addr {
                    description 'Set next hop address.'
                                ;
                    type ncd:ipv4-address ;
                    mandatory true ;
                  }
                  container track {
                    description 'Set track name.'
                                ;
                    presence track ;
                    leaf value {
                      description 'Track name (1-31 characters).'
                                  ;
                      type string {
                        length 1..31 {
                          description 'The length of track-name is from 1 to 31'
                                    + ' char.'
                                      ;
                        }
                      }
                      mandatory true ;
                    }
                  }
                }
              }
            }
            container monitor-group-id {
              description 'Set monitor group id.'
                          ;
              presence 'monitor-group-id is not Mandatory'
                       ;
              leaf group-id {
                description 'Monitor group id.'
                            ;
                type uint8 {
                  range 1..63 ;
                }
                mandatory true ;
              }
              ncd:revise-date 2017-04-28 ;
            }
            container l3-vni-label {
              description 'Set l3-VNI label.'
                          ;
              presence l3-vni-label ;
              choice l3-vni-label {
                description 'Set l3-VNI label.'
                            ;
                mandatory true ;
                case label {
                  description 'Set the label value.'
                              ;
                  leaf label {
                    description 'Set the label value.'
                                ;
                    type uint32 {
                      range 0..16777215 {
                        description 'The range of l3-vni label is from 0 to 167'
                                  + '77215.'
                                    ;
                      }
                    }
                    mandatory true ;
                  }
                }
                case automatic {
                  description 'Automatically found out VNI-label value.'
                              ;
                  leaf automatic {
                    description 'Automatically found out VNI-label value.'
                                ;
                    type empty ;
                    mandatory true ;
                  }
                  ncd:revise-date 2019-09-26 ;
                }
              }
              ncd:revise-date 2017-02-28 ;
            }
            container evpn-router-mac {
              description "Set EVPN router's MAC extcommunity attribute."
                          ;
              presence evpn-routr-mac ;
              leaf intf-name {
                description "Set EVPN router's MAC interface."
                            ;
                type ncd:ifname {
                  length 1..31 ;
                }
                mandatory true ;
              }
              ncd:revise-date 2017-02-28 ;
            }
            container l2-vni-label {
              description 'Set l2-VNI label.'
                          ;
              presence l2-vni-label ;
              leaf label {
                description 'Set the label value.'
                            ;
                type uint32 {
                  range 1..16777215 {
                    description 'The range of l2-vni label is from 1 to 1677721'
                              + '5.'
                                ;
                  }
                }
                mandatory true ;
              }
              ncd:revise-date 2016-11-17 ;
            }
            container policy-route-id {
              description 'Set policy route id.'
                          ;
              presence policy-route-id ;
              leaf pid {
                description 'Policy route id.'
                            ;
                type uint8 {
                  range 1..63 ;
                }
                mandatory true ;
              }
              ncd:revise-date 2017-04-28 ;
            }
            container router-mac {
              description 'Set router MAC address.'
                          ;
              presence router-mac ;
              leaf mac-addr {
                description 'Set router MAC address.'
                            ;
                type ncd:mac-address ;
                mandatory true ;
              }
              ncd:revise-date 2018-10-15 ;
            }
            container distance {
              description 'Set distance of routing.'
                          ;
              presence distance ;
              leaf value {
                description 'Set distance of routing.'
                            ;
                type uint8 {
                  range 1..255 {
                    description 'The range of distance value is from 1 to 255.'
                                ;
                  }
                }
                mandatory true ;
              }
              ncd:revise-date 2018-11-15 ;
            }
            container split-horizon-scope {
              description 'Set split horizon scope.'
                          ;
              presence split-horizon-scope ;
              leaf name {
                description 'The name of split-horizon scope(<A-Z>).'
                            ;
                type string {
                  length 1 {
                    description 'The length of name is 1.'
                                ;
                  }
                }
                mandatory true ;
              }
              ncd:revise-date 2018-12-04 ;
            }
            container l2-equivalent-vni-label {
              description 'Set L2 equivalent VNI label.'
                          ;
              presence l2-equivalent-vni-label ;
              leaf equivalent-vni-label {
                description 'Set equivalent VNI label.'
                            ;
                type empty ;
                mandatory true ;
              }
              ncd:revise-date 2018-12-04 ;
            }
            container l3-equivalent-vni-label {
              description 'Set L3 equivalent VNI label.'
                          ;
              presence l3-equivalent-vni-label ;
              leaf equivalent-vni-label {
                description 'Set equivalent VNI label.'
                            ;
                type empty ;
                mandatory true ;
              }
              ncd:revise-date 2018-12-04 ;
            }
            container color {
              description 'Set BGP color.'
                          ;
              presence color ;
              choice color {
                description "Set BGP color, value and list-name and remove can'"
                          + "t co-exist in one sequence."
                            ;
                mandatory true ;
                case value {
                  description 'The color value.'
                              ;
                  leaf value {
                    description 'The color value.'
                                ;
                    type uint32 {
                      range 1..4294967295 {
                        description 'The range of color is from 1 to 4294967295.'
                                    ;
                      }
                    }
                    mandatory true ;
                  }
                }
                case clear-color {
                  description 'Clear color flag.'
                              ;
                  leaf clear-color {
                    description 'Clear color flag.'
                                ;
                    type empty ;
                    mandatory true ;
                    ncd:revise-date 2019-03-21 ;
                  }
                }
                case list-name {
                  description 'The color list name.'
                              ;
                  leaf name {
                    description 'The color list name.'
                                ;
                    type string {
                      length 1..31 ;
                    }
                    mandatory true ;
                  }
                  ncd:revise-date 2019-05-31 ;
                }
              }
              ncd:revise-date 2019-02-27 ;
            }
            container urpf {
              description 'Set BGP path URPF.'
                          ;
              presence urpf ;
              leaf urpf-id {
                description 'The ID of URPF.'
                            ;
                type uint16 {
                  range 1..65534 {
                    description 'The range of URPF ID is from 1 to 65534'
                                ;
                  }
                }
                mandatory true ;
              }
              ncd:revise-date 2019-02-27 ;
            }
            container aigp-metric {
              description 'Set AIGP metric.'
                          ;
              presence aigp-metric ;
              choice aigp-metric {
                description "Set AIGP metric, metric-value and igp-metric can't"
                          + " co-exist in one sequence."
                            ;
                mandatory true ;
                case metric-value {
                  description 'Set AIGP metric value.'
                              ;
                  leaf value {
                    description 'The AGIP metric value.'
                                ;
                    type uint64 {
                      range 0..4294967295 {
                        description 'the range of metric-value is from 0 to 429'
                                  + '4967295.'
                                    ;
                      }
                    }
                    mandatory true ;
                  }
                }
                case igp-metric {
                  description 'Set IGP metric as AIGP metric.'
                              ;
                  leaf igp-metric {
                    description 'Set IGP metric value as AIGP metric.'
                                ;
                    type empty ;
                    mandatory true ;
                  }
                }
              }
              ncd:revise-date 2019-02-27 ;
            }
            container metric {
              description 'Set metric value for destination routing protocol.'
                          ;
              choice metric {
                description 'Set metric value for destination routing protocol.'
                            ;
                case metric {
                  description 'Set metric value for destination routing protoco'
                            + 'l.'
                              ;
                  leaf add-del {
                    description 'Add metric  +;   
Del metric  -.'
                                ;
                    type enumeration {
                      enum + {
                        value 1 ;
                        description 'Add metric  +'
                                    ;
                      }
                      enum - {
                        value 2 ;
                        description 'Del metric  -'
                                    ;
                      }
                    }
                  }
                  leaf value {
                    description 'Metric value <0-4294967295>.'
                                ;
                    type uint32 {
                      range 0..4294967295 {
                        description 'The range of metric-value is from 0 to 429'
                                  + '4967295.'
                                    ;
                      }
                    }
                    mandatory true ;
                  }
                }
                case inherit-metric {
                  description 'Set inherit metric flag for destination routing '
                            + 'protocol.'
                              ;
                  leaf inherit {
                    description 'Set inherit metric flag for destination routin'
                              + 'g protocol.'
                                ;
                    type empty ;
                    mandatory true ;
                  }
                  ncd:revise-date 2019-07-22 ;
                }
                case inherit-igp-metric {
                  description 'Set inherit igp metric flag for destination rout'
                            + 'ing protocol.'
                              ;
                  leaf inherit-igp-metric {
                    description 'Set inherit igp metric flag for destination ro'
                              + 'uting protocol.'
                                ;
                    type empty ;
                    mandatory true ;
                  }
                  ncd:revise-date 2019-07-22 ;
                }
              }
              ncd:revise-date 2019-04-17 ;
            }
            container metric-type {
              description 'Set type of metric for destination routing protocol.'
                          ;
              presence 'metric-type is not Mandatory'
                       ;
              leaf value {
                description 'Set type of metric for destination routing protoco'
                          + 'l;'+"\n"
                          + 'External  IS-IS external metric;'+"\n"
                          + 'Internal  IS-IS internal metric;'+"\n"
                          + 'Type-1    OSPF external type 1 metric;'+"\n"
                          + 'Type-2    OSPF external type 2 metric.'
                            ;
                type enumeration {
                  enum internal {
                    value 1 ;
                    description 'Internal  IS-IS internal metric'
                                ;
                  }
                  enum external {
                    value 2 ;
                    description 'External  IS-IS external metric'
                                ;
                  }
                  enum type-1 {
                    value 3 ;
                    description 'Type-1    OSPF external type 1 metric'
                                ;
                  }
                  enum type-2 {
                    value 4 ;
                    description 'Type-2    OSPF external type 2 metric'
                                ;
                  }
                }
                mandatory true ;
              }
              ncd:revise-date 2019-04-17 ;
            }
            container tag {
              description 'Set tag value for destination routing protocol.'
                          ;
              presence 'tag is not Mandatory'
                       ;
              leaf value {
                description 'Tag value.'
                            ;
                type uint32 {
                  range 0..4294967295 {
                    description 'The range of tag-value is from 0 to 4294967295.'
                                ;
                  }
                }
                mandatory true ;
              }
              ncd:revise-date 2019-04-17 ;
            }
            container tunnel-encapsulation {
              description 'Tunnel encapsulation.'
                          ;
              presence tunnel-encapsulation ;
              leaf value {
                description 'mpls   MPLS tunnel;
vxlan  VXLAN tunnel;'
                            ;
                type enumeration {
                  enum mpls {
                    value 1 ;
                  }
                  enum vxlan {
                    value 2 ;
                  }
                }
                mandatory true ;
              }
              ncd:revise-date 2019-05-08 ;
            }
            container equivalent-evi-label {
              description 'Set equivalent EVI label.'
                          ;
              presence equivalent-evi-label ;
              leaf equivalent-evi-label {
                description 'Set equivalent EVI label.'
                            ;
                type empty ;
                mandatory true ;
              }
              ncd:revise-date 2019-09-09 ;
            }
            container evi-label {
              description 'Set EVI label.'
                          ;
              presence evi-label ;
              leaf label {
                description 'Set the label value.'
                            ;
                type uint32 {
                  range 16..1048575 {
                    description 'The range of evi label is from 16 to 1048575.'
                                ;
                  }
                }
                mandatory true ;
              }
              ncd:revise-date 2019-09-09 ;
            }
            container gw-ip {
              description 'Gateway IP address.'
                          ;
              presence 'gw-ip is not Mandatory'
                       ;
              leaf ipv4-addr {
                description 'Set IPv4 address.'
                            ;
                type ncd:ipv4-address ;
                mandatory true ;
              }
              ncd:revise-date 2019-09-26 ;
            }
            container l2-srv6-function-id {
              description 'Set l2-srv6-function-id.'
                          ;
              presence l2-srv6-function-id ;
              container dt2m {
                description 'DT2M function code.'
                            ;
                presence dt2m ;
                leaf value {
                  description 'Set the DT2M function code value.'
                              ;
                  type ncd:ipv6-address ;
                  mandatory true ;
                }
              }
              container dt2u {
                description 'DT2U function code.'
                            ;
                presence dt2u ;
                leaf value {
                  description 'Set the DT2U function code value.'
                              ;
                  type ncd:ipv6-address ;
                  mandatory true ;
                }
              }
              ncd:revise-date 2020-12-04 ;
            }
            container l2-srv6-equivalent-sid {
              description 'Set l2-srv6-equivalent-sid.'
                          ;
              presence l2-srv6-equivalent-sid ;
              leaf equivalent-sid {
                description 'Set equivalent sid.'
                            ;
                type empty ;
                mandatory true ;
              }
              ncd:revise-date 2020-12-04 ;
            }
            container cpu {
              description 'Set cpu flag.'
                          ;
              presence 'cpu is not Mandatory'
                       ;
              leaf cpu {
                description 'Set cpu flag.'
                            ;
                type empty ;
                mandatory true ;
              }
              ncd:revise-date 2020-12-30 ;
            }
          }
          container continues {
            description 'Continue match action.'
                        ;
            choice continue {
              description 'Continue match action.'
                          ;
              case continue-next {
                description 'Continue to match next sequence.'
                            ;
                leaf next {
                  description 'Continue to match next sequence.'
                              ;
                  type empty ;
                }
              }
              case continue-sequence {
                description 'Continue to match specify sequence.'
                            ;
                leaf sequence {
                  description 'Continue to match specify sequence.'
                              ;
                  type uint32 {
                    range 0..65535 ;
                  }
                }
              }
            }
            ncd:revise-date 2015-09-01 ;
          }
          container time-range {
            description 'Sequence of route-map binds time-range.'
                        ;
            presence 'time range'
                     ;
            leaf time-range {
              description 'Time range.'
                          ;
              type string {
                length 1..31 ;
              }
              mandatory true ;
            }
            ncd:revise-date 2016-05-24 ;
          }
          container load-share {
            description 'Forward mode enable load-share.'
                        ;
            leaf load-share {
              description 'Forward mode enable load-share.'
                          ;
              type empty ;
            }
            ncd:revise-date 2016-05-24 ;
          }
          container default-route {
            description 'Default route.'
                        ;
            leaf default-route-enable {
              description 'Default route enable.'
                          ;
              type empty ;
            }
            ncd:revise-date 2016-07-18 ;
          }
          container blackhole-route {
            description 'Blackhole route.'
                        ;
            leaf blackhole-route-enable {
              description 'Blackhole route enable.'
                          ;
              type empty ;
            }
            ncd:revise-date 2016-07-18 ;
          }
          container strict-policy {
            if-feature strict-policy ;
            description 'Enable strict policy.'
                        ;
            leaf strict-policy {
              description 'Enable strict policy.'
                          ;
              type empty ;
            }
            ncd:revise-date 2016-08-18 ;
          }
          ncd:select rmap-name ;
          ncd:select 'rmap-name rseq-no'
                     ;
        }
        container route-map-seq-required {
          description 'Route-map sequence required.'
                      ;
          leaf seq-required {
            description 'Route-map sequence required.'
                        ;
            type empty ;
          }
          ncd:revise-date 2021-04-02 ;
        }
        container trigger-delay {
          description "Configure route-map's trigger delay."
                      ;
          presence trigger-delay ;
          leaf delay-time {
            description 'The delay time value (second) of trigger delay.'
                        ;
            type uint32 {
              range 0..30 {
                description 'The range of delay time is from 0 to 30.'
                            ;
              }
            }
          }
          ncd:revise-date 2019-02-27 ;
        }
      }
    }
  }
}
