module zxr10-bgp {
  namespace 'http://www.zte.com.cn/zxr10/netconf/schema/rosng/bgp'
            ;
  prefix bgp ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe BGP.This netconf module contains '
            + 'managed object definitions of BGP.'
              ;
  revision 2021-04-21 {
    description 'Add leaf node bgp-attr-set,announce-msid and non-segmented.'
                ;
  }
  revision 2021-03-25 {
    description '1.Obsolete node /configuration/bgp/bgp-instances/bgp-inst/bgp/'
              + 'bestpath-bgp-lu-nexthop-compare.'+"\n"
              + '2.Add leaf /configuration/bgp/bgp-instances/bgp-inst/address-f'
              + 'amily-ipv4-uni/bestpath-bgp-lu-nexthop-compare.'
                ;
  }
  revision 2021-03-01 {
    description '1. Add container /configuration/bgp/bgp-instances/bgp-inst/add'
              + 'ress-family-vrf/safi-link-state.'+"\n"
              + '2. Add container /configuration/bgp/bgp-instances/bgp-inst/add'
              + 'ress-family-vrf/safi-link-state-vpn.'+"\n"
              + '3. Add leaf /configuration/bgp/bgp-remote-prefixsid/bgp-remote'
              + '-prefixsid/bgp-remote-prefixsid-delete-delay.'
                ;
  }
  revision 2021-02-01 {
    description 'Add leaf neighbor-stalepath-time and leaf neighbor-stalepath-t'
              + 'ime-permanent in address-family ipv4 unicast,address-family ip'
              + 'v4 vrf,address-family ipv6 vrf,address-family vrf.'
                ;
  }
  revision 2021-01-19 {
    description '1.Add leaf configuration/bgp/bgp-instances/bgp-inst/address-fa'
              + 'mily-ipv6-flowspec/neighbor-ipv6-flowspec/neighbor-group/neigh'
              + 'bor-peergroup/send-community;'+"\n"
              + '2.Add leaf configuration/bgp/bgp-instances/bgp-inst/address-fa'
              + 'mily-ipv6-flowspec/neighbor-ipv6-flowspec/neighbor-group/neigh'
              + 'bor-peergroup/send-large-community;'+"\n"
              + '3.Add leaf configuration/bgp/bgp-instances/bgp-inst/address-fa'
              + 'mily-ipv6-flowspec/neighbor-ipv6-flowspec/neighbor-group/neigh'
              + 'bor-peergroup/neighbor-extend;'+"\n"
              + '4.Add leaf configuration/bgp/bgp-instances/bgp-inst/address-fa'
              + 'mily-ipv6-flowspec/neighbor-ipv6-flowspec/neighbor-ipv4/neighb'
              + 'or/send-community;'+"\n"
              + '5.Add leaf configuration/bgp/bgp-instances/bgp-inst/address-fa'
              + 'mily-ipv6-flowspec/neighbor-ipv6-flowspec/neighbor-ipv4/neighb'
              + 'or/send-large-community;'+"\n"
              + '6.Add container configuration/bgp/bgp-instances/bgp-inst/addre'
              + 'ss-family-ipv6-flowspec/neighbor-ipv6-flowspec/neighbor-ipv4/n'
              + 'eighbor/neighbor-extend;'+"\n"
              + '7.Add leaf configuration/bgp/bgp-instances/bgp-inst/address-fa'
              + 'mily-ipv6-flowspec/neighbor-ipv6-flowspec/neighbor-ipv6/neighb'
              + 'or/send-community;'+"\n"
              + '8.Add leaf configuration/bgp/bgp-instances/bgp-inst/address-fa'
              + 'mily-ipv6-flowspec/neighbor-ipv6-flowspec/neighbor-ipv6/neighb'
              + 'or/send-large-community;'+"\n"
              + '9.Add container configuration/bgp/bgp-instances/bgp-inst/addre'
              + 'ss-family-ipv6-flowspec/neighbor-ipv6-flowspec/neighbor-ipv6/n'
              + 'eighbor/neighbor-extend;'+"\n"
              + '10.Add leaf configuration/bgp/bgp-instances/bgp-inst/address-f'
              + 'amily-vpnv6-flowspec/neighbor-vpnv6-flowspec/neighbor-group/ne'
              + 'ighbor-peergroup/send-community;'+"\n"
              + '11.Add leaf configuration/bgp/bgp-instances/bgp-inst/address-f'
              + 'amily-vpnv6-flowspec/neighbor-vpnv6-flowspec/neighbor-group/ne'
              + 'ighbor-peergroup/send-large-community;'+"\n"
              + '12.Add container configuration/bgp/bgp-instances/bgp-inst/addr'
              + 'ess-family-vpnv6-flowspec/neighbor-vpnv6-flowspec/neighbor-gro'
              + 'up/neighbor-peergroup/neighbor-extend;'+"\n"
              + '13.Add leaf configuration/bgp/bgp-instances/bgp-inst/address-f'
              + 'amily-vpnv6-flowspec/neighbor-vpnv6-flowspec/neighbor-ipv4/nei'
              + 'ghbor/send-community;'+"\n"
              + '14.Add leaf configuration/bgp/bgp-instances/bgp-inst/address-f'
              + 'amily-vpnv6-flowspec/neighbor-vpnv6-flowspec/neighbor-ipv4/nei'
              + 'ghbor/send-large-community;'+"\n"
              + '15.Add container configuration/bgp/bgp-instances/bgp-inst/addr'
              + 'ess-family-vpnv6-flowspec/neighbor-vpnv6-flowspec/neighbor-ipv'
              + '4/neighbor/neighbor-extend;'+"\n"
              + '16.Add leaf configuration/bgp/bgp-instances/bgp-inst/address-f'
              + 'amily-vpnv6-flowspec/neighbor-vpnv6-flowspec/neighbor-ipv6/nei'
              + 'ghbor/send-community;'+"\n"
              + '17.Add leaf configuration/bgp/bgp-instances/bgp-inst/address-f'
              + 'amily-vpnv6-flowspec/neighbor-vpnv6-flowspec/neighbor-ipv6/nei'
              + 'ghbor/send-large-community;'+"\n"
              + '18.Add container configuration/bgp/bgp-instances/bgp-inst/addr'
              + 'ess-family-vpnv6-flowspec/neighbor-vpnv6-flowspec/neighbor-ipv'
              + '6/neighbor/neighbor-extend;'
                ;
  }
  revision 2021-01-15 {
    description 'Discard redundant nodes:'+"\n"
              + '/configuration/bgp/bgp-instances/bgp-inst/address-family-vrf/a'
              + 'ddress-family/safi-ipv4-unicast/neighbors/neighbor-group/neigh'
              + 'bor-peergroup/originate-interval'+"\n"
              + '/configuration/bgp/bgp-instances/bgp-inst/address-family-vrf/a'
              + 'ddress-family/safi-ipv4-unicast/neighbors/neighbor-ipv4/neighb'
              + 'or/originate-interval'+"\n"
              + '/configuration/bgp/bgp-instances/bgp-inst/address-family-vrf/a'
              + 'ddress-family/safi-ipv4-multicast/redistribute-v4-vrf/redistri'
              + 'bute-ospf-vrf/redistribute-ospf/set-metric/route-policy'
                ;
  }
  revision 2021-01-07 {
    description 'Add an enumration value srv6-locator for redistribute/protocol.'
                ;
  }
  revision 2020-12-31 {
    description 'Exchange the positions between as-path-loopcheck-ibgp-in and b'
              + 'estpath-bgp-lu-nexthop-compare.'
                ;
  }
  revision 2020-12-20 {
    description '1)Add leaf /bgp:configuration/bgp:bgp/bgp:bgp-instances/bgp:bg'
              + 'p-inst/bgp:address-family-ipv4-uni/bgp:bestpath-rpki-validatio'
              + 'n.'+"\n"
              + '2)Add leaf /bgp:configuration/bgp:bgp/bgp:bgp-instances/bgp:bg'
              + 'p-inst/bgp:address-family-ipv6-uni/bgp:bestpath-rpki-validatio'
              + 'n.'+"\n"
              + '3)Add container /bgp:configuration/bgp:bgp/bgp:bgp-instances/b'
              + 'gp:bgp-inst/bgp:rpki-rtr/bgp:neighbor/bgp:neighbor-ipv4/bgp:ne'
              + 'ighbor/bgp:maximum-roa.'+"\n"
              + '4)Add container /bgp:configuration/bgp:bgp/bgp:bgp-instances/b'
              + 'gp:bgp-inst/bgp:rpki-rtr/bgp:neighbor/bgp:neighbor-ipv6/bgp:ne'
              + 'ighbor/bgp:maximum-roa.'+"\n"
              + '5)Add container /bgp:operation/bgp:bgp/bgp:reset/bgp:rpki-rtr.'
                ;
  }
  revision 2020-12-09 {
    description 'Add leaf nodes:nexthop-recursive-null1.'
                ;
  }
  revision 2020-12-02 {
    description '(1)Add leaf /configuration/bgp/bgp-instances/bgp-inst/address-'
              + 'family-evpn/neighbor-evpn/neighbor-group/neighbor-peergroup/ne'
              + 'ighbor-extend/add-paths-send/prefixlist'+"\n"
              + '(2)Add leaf /configuration/bgp/bgp-instances/bgp-inst/address-'
              + 'family-evpn/neighbor-evpn/neighbor-ipv4/neighbor/neighbor-exte'
              + 'nd/add-paths-send/prefixlist'+"\n"
              + '(3)Add leaf /configuration/bgp/bgp-instances/bgp-inst/address-'
              + 'family-evpn/neighbor-evpn/neighbor-ipv6/neighbor/neighbor-exte'
              + 'nd/add-paths-send/prefixlist;'+"\n"
              + '(4)Add a leaf:as-path-loopcheck-ibgp-in;'+"\n"
              + '(5)Add new container /configuration/bgp/bgp-instances/bgp-inst'
              + '/address-family-evpn/additional-paths;'+"\n"
              + '(6)Modify enumration description of bestpath-external,bestpath'
              + '-igp-metric-compare and bestpath-igp-metric-ignore in address-'
              + 'family-ipv6-vrf and address-family-vrf/address-family/safi-ipv'
              + '6-unicast.'
                ;
  }
  revision 2020-11-23 {
    description '(1)Add leaf bestpath-external,bestpath-igp-metric-compare,best'
              + 'path-igp-metric-ignore for address-family-evpn,address-family-'
              + 'ipv4-vrf,address-family-ipv6-vrf,address-family-vrf/address-fa'
              + 'mily/safi-ipv4-unicast and address-family-vrf/address-family/s'
              + 'afi-ipv6-unicast.'+"\n"
              + '(2)Add an enumration value nptv6 for redistribute/protocol.'
                ;
  }
  revision 2020-11-11 {
    description '1)Add container /configuration/bgp/bgp-instances/bgp-inst/addr'
              + 'ess-family-ipv4-uni/neighbor-ipv4-uni/neighbor-uni-group/neigh'
              + 'bor-uni-peergroup/srv6-epe-peernode.'+"\n"
              + 'Add case /configuration/bgp/bgp-instances/bgp-inst/address-fam'
              + 'ily-ipv4-uni/neighbor-ipv4-uni/neighbor-uni-ipv6/neighbor-uni/'
              + 'srv6-epe/srv6-epe-dyn.'+"\n"
              + 'Add case /configuration/bgp/bgp-instances/bgp-inst/address-fam'
              + 'ily-ipv4-uni/neighbor-ipv4-uni/neighbor-uni-ipv6/neighbor-uni/'
              + 'srv6-epe-peer-adj/ipv6-number/srv6-sid/srv6-epe-dyn.'+"\n"
              + '2)Add choice-clear case for choice agg-policy.'
                ;
  }
  revision 2020-10-28 {
    description 'Add leaf nexthop-recursive-lookup-srv6-sid node for address-fa'
              + 'mily ipv4 unicast,ipv6 uncast,vpnv4 unicast,vpnv6 unicast,l2vp'
              + 'n evpn.'
                ;
  }
  revision 2020-10-15 {
    description '(1)Add leaf /configuration/bgp/bgp-instances/bgp-inst/address-'
              + 'family-ipv4-uni/neighbor-ipv4-uni/neighbor-uni-group/neighbor-'
              + 'uni-peergroup/redirect-ipv6-type.'+"\n"
              + '(2)Add leaf /configuration/bgp/bgp-instances/bgp-inst/address-'
              + 'family-ipv4-uni/neighbor-ipv4-uni/neighbor-uni-ipv4/neighbor-u'
              + 'ni/redirect-ipv6-type.'+"\n"
              + '(3)Add leaf /configuration/bgp/bgp-instances/bgp-inst/address-'
              + 'family-ipv4-uni/neighbor-ipv4-uni/neighbor-uni-ipv6/neighbor-u'
              + 'ni/redirect-ipv6-type.'
                ;
  }
  revision 2020-10-10 {
    description "(1)Add new container /configuration/bgp/bgp-instances/bgp-inst"
              + "/bgp/neighbor-damp.
\n(2)Add route-policy nodes by referring t"
              + "o route-map. The related functions include redistribute, netwo"
              + "rk, BGP rib-only, BGP dampening and originate default route of"
              + " neighbor.
\n(3)Change route-policy name's maximum length from"
              + " 31 to 200.
\n(4)Add range of leaf slow-peer-detection-thresho"
              + "ld and slow-peer-detection-recover.\n(5)Add download-community"
              + " leaf for address-family ipv4-uni\ipv6-uni\ipv4-vrf\ipv6-vrf.\n"
              + "(6)Add some leaf nodes:
\n/configuration/bgp/bgp-instances/bgp"
              + "-inst/address-family-vrf/address-family/neighbor-vrf/neighbor-"
              + "group/neighbor/enhanced-route-refresh-disable
\n/configuration"
              + "/bgp/bgp-instances/bgp-inst/address-family-vrf/address-family/"
              + "neighbor-vrf/neighbor-group/neighbor/four-byte-as-disable
\n/c"
              + "onfiguration/bgp/bgp-instances/bgp-inst/address-family-vrf/add"
              + "ress-family/neighbor-vrf/neighbor-ipv4/neighbor/enhanced-route"
              + "-refresh-disable
\n/configuration/bgp/bgp-instances/bgp-inst/a"
              + "ddress-family-vrf/address-family/neighbor-vrf/neighbor-ipv4/ne"
              + "ighbor/four-byte-as-disable
\n/configuration/bgp/bgp-instances"
              + "/bgp-inst/address-family-vrf/address-family/neighbor-vrf/neigh"
              + "bor-ipv6/neighbor/enhanced-route-refresh-disable
\n/configurat"
              + "ion/bgp/bgp-instances/bgp-inst/address-family-vrf/address-fami"
              + "ly/neighbor-vrf/neighbor-ipv6/neighbor/four-byte-as-disable
\n"
              + "/configuration/bgp/bgp-instances/bgp-inst/address-family-vrf/a"
              + "ddress-family/neighbor-vrf/neighbor-ipv6/neighbor/receive-sing"
              + "le-label
\n/configuration/bgp/bgp-instances/bgp-inst/address-f"
              + "amily-vrf/address-family/neighbor-vrf/neighbor-ipv6/neighbor/i"
              + "gnore-error-packet
\n/configuration/bgp/bgp-instances/bgp-inst"
              + "/address-family-vrf/address-family/safi-ipv4-unicast/neighbors"
              + "/neighbor-group/neighbor-peergroup/originate-interval"
                ;
  }
  revision 2020-09-27 {
    description 'Add leaf configuration/bgp/bgp-instances/bgp-inst/bgp/sr-epe-m'
              + 'ode.'
                ;
  }
  revision 2020-09-24 {
    description '(1)Add new leaf remove-private-as for address-family-l2vpn-evp'
              + 'n.'+"\n"
              + '(2)Add enumeration value l2vpn-evpn of leaf afi for clear upda'
              + 'te-group.'+"\n"
              + '(3)Add default value for leaf slow-peer-detection-threshold an'
              + 'd slow-peer-detection-recover.'+"\n"
              + '(4)Modify description of distance-route-map in address-family-'
              + 'evpn.'
                ;
  }
  revision 2020-09-08 {
    description '(1)Add leaf /bgp:configuration/bgp:bgp/bgp:bgp-instances/bgp:b'
              + 'gp-inst/bgp:address-family-ipv4-uni/bgp:distance-route-map.'+"\n"
              + '(2)Add leaf /bgp:configuration/bgp:bgp/bgp:bgp-instances/bgp:b'
              + 'gp-inst/bgp:address-family-ipv4-multi/bgp:distance-route-map.'+"\n"
              + '(3)Add leaf /bgp:configuration/bgp:bgp/bgp:bgp-instances/bgp:b'
              + 'gp-inst/bgp:address-family-ipv4-vrf/bgp:address-family-vrf/bgp'
              + ':distance-route-map.'+"\n"
              + '(4)Add leaf /bgp:configuration/bgp:bgp/bgp:bgp-instances/bgp:b'
              + 'gp-inst/bgp:address-family-evpn/bgp:distance-bgp-internal.'+"\n"
              + '(5)Add leaf /bgp:configuration/bgp:bgp/bgp:bgp-instances/bgp:b'
              + 'gp-inst/bgp:address-family-evpn/bgp:distance-bgp-external.'+"\n"
              + '(6)Add leaf /bgp:configuration/bgp:bgp/bgp:bgp-instances/bgp:b'
              + 'gp-inst/bgp:address-family-evpn/bgp:distance-route-map.'+"\n"
              + '(7)Add leaf /bgp:configuration/bgp:bgp/bgp:bgp-instances/bgp:b'
              + 'gp-inst/bgp:address-family-ipv6-uni/bgp:distance-route-map.'+"\n"
              + '(8)Add leaf /bgp:configuration/bgp:bgp/bgp:bgp-instances/bgp:b'
              + 'gp-inst/bgp:address-family-ipv6-vrf/bgp:address-family-vrf/bgp'
              + ':distance-route-map.'+"\n"
              + '(9)Add leaf /bgp:configuration/bgp:bgp/bgp:bgp-instances/bgp:b'
              + 'gp-inst/bgp:address-family-ipv6-multi/bgp:distance-route-map.'+"\n"
              + '(10)Add leaf /bgp:configuration/bgp:bgp/bgp:bgp-instances/bgp:'
              + 'bgp-inst/bgp:address-family-vrf/bgp:address-family/bgp:safi-ip'
              + 'v4-unicast/bgp:distance-route-map.'+"\n"
              + '(11)Add leaf /bgp:configuration/bgp:bgp/bgp:bgp-instances/bgp:'
              + 'bgp-inst/bgp:address-family-vrf/bgp:address-family/bgp:safi-ip'
              + 'v6-unicast/bgp:distance-route-map.'+"\n"
              + '(12)Add leaf /bgp:configuration/bgp:bgp/bgp:bgp-instances/bgp:'
              + 'bgp-inst/bgp:address-family-ipv4-sr-policy/bgp:distance-route-'
              + 'map.'+"\n"
              + '(13)Add leaf /bgp:configuration/bgp:bgp/bgp:bgp-instances/bgp:'
              + 'bgp-inst/bgp:address-family-ipv6-sr-policy/bgp:distance-route-'
              + 'map.'+"\n"
              + '(14)Add new leafs slow-peer-detection and  slow-peer-detection'
              + '-threshold and slow-peer-detection-recover for address-family-'
              + 'ipv4-uni,address-family-ipv4-vrf,address-family-ipv6-uni,addre'
              + 'ss-family-ipv6-vrf,address-family-l2vpn-evpn,address-family-vp'
              + 'nv4 and address-family-vpnv6,safi-ipv4-unicast,safi-ipv6-unica'
              + 'st.'
                ;
  }
  revision 2020-08-29 {
    description '(1)/bgp:configuration/bgp:bgp/bgp:bgp-instances/bgp:bgp-inst/b'
              + 'gp:address-family-ipv4-vrf/bgp:address-family-vrf/bgp:bgp-best'
              + 'path-nexthop-priority'+"\n"
              + '(2)/bgp:configuration/bgp:bgp/bgp:bgp-instances/bgp:bgp-inst/b'
              + 'gp:address-family-ipv6-vrf/bgp:address-family-vrf/bgp:bgp-best'
              + 'path-nexthop-priority'+"\n"
              + '(3)Add leaf /bgp:configuration/bgp:bgp/bgp:bgp-instances/bgp:b'
              + 'gp-inst/bgp:address-family-vrf/bgp:address-family/bgp:safi-ipv'
              + '4-unicast/bgp:bgp-bestpath-nexthop-priority'+"\n"
              + '(4)Add leaf /bgp:configuration/bgp:bgp/bgp:bgp-instances/bgp:b'
              + 'gp-inst/bgp:address-family-vrf/bgp:address-family/bgp:safi-ipv'
              + '6-unicast/bgp:bgp-bestpath-nexthop-priority'
                ;
  }
  revision 2020-08-18 {
    description '(1)Add leaf /configuration/bgp/bgp-instances/bgp-inst/address-'
              + 'family-ipv4-uni/dampening-ibgp.'+"\n"
              + '(2)Add leaf /configuration/bgp/bgp-instances/bgp-inst/address-'
              + 'family-ipv6-uni/dampening-ibgp.'+"\n"
              + '(3)Add leaf adv-tunnel-encap for address-family VPNV4/VPNV6.'+"\n"
              + '(4)Add choice /bgp:configuration/bgp:bgp/bgp:bgp-instances/bgp'
              + ':bgp-inst/bgp:address-family-ipv6-vrf/bgp:address-family-vrf/b'
              + 'gp:neighbor-v6-vrf/bgp:neighbor-group/bgp:neighbor-peergroup/b'
              + 'gp:neighbor-extend/bgp:transport/bgp:transport;'+"\n"
              + '(5)Add choice /bgp:configuration/bgp:bgp/bgp:bgp-instances/bgp'
              + ':bgp-inst/bgp:address-family-ipv6-vrf/bgp:address-family-vrf/b'
              + 'gp:neighbor-v6-vrf/bgp:neighbor-ipv6/bgp:neighbor/bgp:neighbor'
              + '-extend/bgp:transport/bgp:transport;'
                ;
  }
  revision 2020-08-11 {
    description '(1)Add leaf /configuration/bgp/bgp-instances/bgp-inst/address-'
              + 'family-ipv4-flowspec/neighbor-ipv4-flowspec/neighbor-group/nei'
              + 'ghbor-peergroup/allowas-in.'+"\n"
              + '(2)Add leaf /configuration/bgp/bgp-instances/bgp-inst/address-'
              + 'family-ipv4-flowspec/neighbor-ipv4-flowspec/neighbor-ipv4/neig'
              + 'hbor/allowas-in.'+"\n"
              + '(3)Add leaf /configuration/bgp/bgp-instances/bgp-inst/address-'
              + 'family-vpnv4-flowspec/neighbor-vpnv4-flowspec/neighbor-group/n'
              + 'eighbor-peergroup/allowas-in.'+"\n"
              + '(4)Add leaf /configuration/bgp/bgp-instances/bgp-inst/address-'
              + 'family-vpnv4-flowspec/neighbor-vpnv4-flowspec/neighbor-ipv4/ne'
              + 'ighbor/allowas-in.'+"\n"
              + '(5)Add leaf /configuration/bgp/bgp-instances/bgp-inst/address-'
              + 'family-ipv6-flowspec/neighbor-ipv6-flowspec/neighbor-group/nei'
              + 'ghbor-peergroup/allowas-in.'+"\n"
              + '(6)Add leaf /configuration/bgp/bgp-instances/bgp-inst/address-'
              + 'family-ipv6-flowspec/neighbor-ipv6-flowspec/neighbor-ipv4/neig'
              + 'hbor/allowas-in.'+"\n"
              + '(7)Add leaf /configuration/bgp/bgp-instances/bgp-inst/address-'
              + 'family-ipv6-flowspec/neighbor-ipv6-flowspec/neighbor-ipv6/neig'
              + 'hbor/allowas-in.'+"\n"
              + '(8)Add leaf /configuration/bgp/bgp-instances/bgp-inst/address-'
              + 'family-vpnv6-flowspec/neighbor-vpnv6-flowspec/neighbor-group/n'
              + 'eighbor-peergroup/allowas-in.'+"\n"
              + '(9)Add leaf /configuration/bgp/bgp-instances/bgp-inst/address-'
              + 'family-vpnv6-flowspec/neighbor-vpnv6-flowspec/neighbor-ipv4/ne'
              + 'ighbor/allowas-in.'+"\n"
              + '(10)Add leaf /configuration/bgp/bgp-instances/bgp-inst/address'
              + '-family-vpnv6-flowspec/neighbor-vpnv6-flowspec/neighbor-ipv6/n'
              + 'eighbor/allowas-in.'+"\n"
              + '(11)Add leaf configuration/bgp/bgp-instances/bgp-inst/bgp/srv6'
              + '-epe-locator.'
                ;
  }
  revision 2020-07-28 {
    description '(1)Add /configuration/bgp/bgp-instances/bgp-inst/address-famil'
              + 'y-vrf container.'+"\n"
              + '(2)Add new leaf node default-originate-routemap depend on defa'
              + 'ult-originate.'+"\n"
              + '(3)ipv6 multicast add v4-peeraddr.'+"\n"
              + '(4)Change the encrypted password range from 81-120 to 64-172.'+"\n"
              + '(5)Add leaf /configuration/bgp/bgp-instances/bgp-inst/address-'
              + 'family-ipv4-uni/neighbor-ipv4-uni/neighbor-uni-group/neighbor-'
              + 'uni-peergroup/receive-single-label-compatible.'+"\n"
              + '(6)Add leaf /configuration/bgp/bgp-instances/bgp-inst/address-'
              + 'family-ipv4-uni/neighbor-ipv4-uni/neighbor-uni-ipv4/neighbor-u'
              + 'ni/receive-single-label-compatible.'+"\n"
              + '(7)Add leaf /configuration/bgp/bgp-instances/bgp-inst/address-'
              + 'family-ipv4-uni/neighbor-ipv4-uni/neighbor-uni-ipv6/neighbor-u'
              + 'ni/receive-single-label-compatible.'+"\n"
              + '(8)Add leaf /configuration/bgp/bgp-instances/bgp-inst/address-'
              + 'family-ipv4-vrf/address-family-vrf/neighbor-v4-vrf/neighbor-gr'
              + 'oup/neighbor-peergroup/receive-single-label-compatible.'+"\n"
              + '(9)Add leaf /configuration/bgp/bgp-instances/bgp-inst/address-'
              + 'family-ipv4-vrf/address-family-vrf/neighbor-v4-vrf/neighbor-ip'
              + 'v4/neighbor/receive-single-label-compatible.'+"\n"
              + '(10)Add leaf /configuration/bgp/bgp-instances/bgp-inst/address'
              + '-family-ipv6-vrf/address-family-vrf/neighbor-v6-vrf/neighbor-g'
              + 'roup/neighbor-peergroup/receive-single-label-compatible.'+"\n"
              + '(11)Add leaf /configuration/bgp/bgp-instances/bgp-inst/address'
              + '-family-ipv6-vrf/address-family-vrf/neighbor-v6-vrf/neighbor-i'
              + 'pv6/neighbor/receive-single-label-compatible.'+"\n"
              + '(12)Add new value per-vrf-by-vni to leaf bgp-label and ip-pref'
              + 'ix-mode in address-family-evpn.'
                ;
  }
  revision 2020-07-21 {
    description '1.Obselete contianer configuration/bgp/bgp-instances/bgp-inst/'
              + 'address-family-ipv4-uni/neighbor-ipv4-uni/neighbor-uni-ipv4/sr'
              + '-epe-peer-adj;'+"\n"
              + '2.Obselete contianer configuration/bgp/bgp-instances/bgp-inst/'
              + 'address-family-ipv4-uni/neighbor-ipv4-uni/neighbor-uni-ipv6/sr'
              + '-epe-peer-adj;'+"\n"
              + '3.Add contianer configuration/bgp/bgp-instances/bgp-inst/addre'
              + 'ss-family-ipv4-uni/neighbor-ipv4-uni/neighbor-uni-ipv4/epe-pee'
              + 'r-adj;'+"\n"
              + '4.Add contianer configuration/bgp/bgp-instances/bgp-inst/addre'
              + 'ss-family-ipv4-uni/neighbor-ipv4-uni/neighbor-uni-ipv6/epe-pee'
              + 'r-adj;'
                ;
  }
  revision 2020-07-10 {
    description 'add ipv4-unicast over v6-peer-address'
                ;
  }
  revision 2020-06-29 {
    description 'Obselete container /configuration/bgp/bgp-instances/bgp-inst/a'
              + 'ddress-family-ipv4-uni/neighbor-ipv4-uni/neighbor-uni-group/ne'
              + 'ighbor-uni-peergroup/srv6-epe.'+"\n"
              + 'Obselete case /configuration/bgp/bgp-instances/bgp-inst/addres'
              + 's-family-ipv4-uni/neighbor-ipv4-uni/neighbor-uni-ipv6/neighbor'
              + '-uni/srv6-epe/srv6-epe-auto.'+"\n"
              + 'Obselete case /configuration/bgp/bgp-instances/bgp-inst/addres'
              + 's-family-ipv4-uni/neighbor-ipv4-uni/neighbor-uni-ipv6/neighbor'
              + '-uni/srv6-epe-peer-adj/ipv6-number/srv6-sid/srv6-epe-auto.'
                ;
  }
  revision 2020-06-08 {
    description "Add new value srv6 to leaf adv-tunnel-encap for neighbor-evpn."
              + "\nChange route-map or route-policy name's maximum length from "
              + "31 to 200 and change prefix-list name's maximum length from 31"
              + " to 169."
                ;
  }
  revision 2020-05-29 {
    description 'Add state node /bgp:state/bgp:bgp/bgp:all-routes/bgp:l2vpn-evp'
              + 'n.'+"\n"
              + 'Add container protector-ip-address in address-family-evpn.'
                ;
  }
  revision 2020-05-11 {
    description 'Add container /configuration/bgp/bgp-instances/bgp-inst/addres'
              + 's-family-ipv4-uni/neighbor-ipv4-uni/neighbor-uni-group/neighbo'
              + 'r-uni-peergroup/srv6-epe.'+"\n"
              + 'Add container /configuration/bgp/bgp-instances/bgp-inst/addres'
              + 's-family-ipv4-uni/neighbor-ipv4-uni/neighbor-uni-ipv6/neighbor'
              + '-uni/srv6-epe.'+"\n"
              + 'Add container /configuration/bgp/bgp-instances/bgp-inst/addres'
              + 's-family-ipv4-uni/neighbor-ipv4-uni/neighbor-uni-ipv6/neighbor'
              + '-uni/srv6-epe-peer-adj.'
                ;
  }
  revision 2020-04-28 {
    description 'Add leaf esi-index-ignore-rd in address-family-evpn.'
                ;
  }
  revision 2020-04-26 {
    description 'Add container rt3-originator-ip-address in address-family-evpn.'
                ;
  }
  revision 2020-04-16 {
    description 'Add leaf named send-large-community for the neighbors and grou'
              + 'ps of address-family-ipv4-uni,'+"\n"
              + 'address-family-vpls,address-family-mdt,address-family-rt,addre'
              + 'ss-family-ipv4-multi,address-family-vpnv4,address-family-ipv4-'
              + 'vrf,address-family-evpn,address-family-ipv6-uni,address-family'
              + '-ipv6-vrf,address-family-ipv6-multi,address-family-vpnv6,addre'
              + 'ss-family-ipv4-flowspec,address-family-vpnv4-flowspec,address-'
              + 'family-ipv4-sr-policy,address-family-ipv6-sr-policy.'
                ;
  }
  revision 2020-04-07 {
    description 'Modify leaf neighbor-gr,add value graceful-restart-low-priorit'
              + 'y-only.'+"\n"
              + 'Add choice nh-unchanged for address family ipv4 unicast/ipv6 u'
              + 'nicast/vpnv4 unicast/vpnv6 unicast/l2vpn evpn/ipv4 sr-policy/i'
              + 'pv6 sr-policy/ipv4 mcast vpn/ipv6 mcast vpn/vpnv4 multicast/vp'
              + 'nv6 multicast/ipv4 mdt/l2vpn vpls.'+"\n"
              + 'Add container for address family ipv4 unicast/ipv6 unicast/vpn'
              + 'v4/vpnv6/ipv4 multicast/ipv6 multicast/ipv4 multicast vpn/ipv6'
              + ' multicast vpn/L2vpn evpn.'
                ;
  }
  revision 2020-03-31 {
    description 'Add choice bfd-parameters for address family ipv4 unicast;'+"\n"
              + 'Add choice bfd-parameters for address family ipv4 vrf;'+"\n"
              + 'Add choice bfd-parameters for address family ipv6 vrf;'
                ;
  }
  revision 2020-03-02 {
    description 'Add leaf /bgp:configuration/bgp:bgp/bgp:bgp-instances/bgp:bgp-'
              + 'inst/bgp:address-family-evpn/bgp:neighbor-evpn/bgp:neighbor-gr'
              + 'oup/bgp:neighbor-peergroup/bgp:allowas-in.'+"\n"
              + 'Add leaf /bgp:configuration/bgp:bgp/bgp:bgp-instances/bgp:bgp-'
              + 'inst/bgp:address-family-evpn/bgp:neighbor-evpn/bgp:neighbor-ip'
              + 'v4/bgp:neighbor/bgp:allowas-in.'+"\n"
              + 'Add leaf /bgp:configuration/bgp:bgp/bgp:bgp-instances/bgp:bgp-'
              + 'inst/bgp:address-family-evpn/bgp:neighbor-evpn/bgp:neighbor-ip'
              + 'v6/bgp:neighbor/bgp:allowas-in.'+"\n"
              + 'Add leaf srv6-l2-service-type and srv6-l3-service-type for nei'
              + 'ghbor-ipv4-uni.'+"\n"
              + 'Add leaf /bgp:configuration/bgp:bgp/bgp:bgp-instances/bgp:bgp-'
              + 'inst/bgp:address-family-evpn/bgp:neighbor-evpn/bgp:neighbor-ip'
              + 'v6/bgp:neighbor/bgp:allowas-in.'+"\n"
              + 'Add leaf srv6-l2-service-type and srv6-l3-service-type for nei'
              + 'ghbor-ipv4-uni.'+"\n"
              + 'Add container /bgp:configuration/bgp:bgp/bgp:bgp-instances/bgp'
              + ':bgp-inst/bgp:address-family-ipv4-vpn-mcast/bgp:neighbor-ipv4/'
              + 'bgp:neighbor/bgp:neighbor-extend.'+"\n"
              + 'Add container /bgp:configuration/bgp:bgp/bgp:bgp-instances/bgp'
              + ':bgp-inst/bgp:address-family-ipv4-vpn-multi/bgp:neighbor-ipv4/'
              + 'bgp:neighbor/bgp:neighbor-extend.'+"\n"
              + 'Add container /bgp:configuration/bgp:bgp/bgp:bgp-instances/bgp'
              + ':bgp-inst/bgp:address-family-ipv6-vpn-mcast/bgp:neighbor-ipv4/'
              + 'bgp:neighbor/bgp:neighbor-extend.'+"\n"
              + 'Add container /bgp:configuration/bgp:bgp/bgp:bgp-instances/bgp'
              + ':bgp-inst/bgp:address-family-ipv6-vpn-multi/bgp:neighbor-ipv4/'
              + 'bgp:neighbor/bgp:neighbor-extend.'+"\n"
              + 'Add leaf /bgp:configuration/bgp:bgp/bgp:bgp-instances/bgp:bgp-'
              + 'inst/bgp:address-family-ipv4-vpn-mcast/bgp:neighbor-ipv4/bgp:n'
              + 'eighbor/bgp:neighbor-extend/bgp:route-map-in-name.'+"\n"
              + 'Add leaf /bgp:configuration/bgp:bgp/bgp:bgp-instances/bgp:bgp-'
              + 'inst/bgp:address-family-ipv4-vpn-mcast/bgp:neighbor-ipv4/bgp:n'
              + 'eighbor/bgp:neighbor-extend/bgp:route-map-out-name.'+"\n"
              + 'Add leaf /bgp:configuration/bgp:bgp/bgp:bgp-instances/bgp:bgp-'
              + 'inst/bgp:address-family-ipv4-vpn-mcast/bgp:neighbor-ipv4/bgp:n'
              + 'eighbor/bgp:weight.'+"\n"
              + 'Add leaf /bgp:configuration/bgp:bgp/bgp:bgp-instances/bgp:bgp-'
              + 'inst/bgp:address-family-ipv4-vpn-multi/bgp:neighbor-ipv4/bgp:n'
              + 'eighbor/bgp:neighbor-extend/bgp:route-map-in-name.'+"\n"
              + 'Add leaf /bgp:configuration/bgp:bgp/bgp:bgp-instances/bgp:bgp-'
              + 'inst/bgp:address-family-ipv4-vpn-multi/bgp:neighbor-ipv4/bgp:n'
              + 'eighbor/bgp:neighbor-extend/bgp:route-map-out-name.'+"\n"
              + 'Add leaf /bgp:configuration/bgp:bgp/bgp:bgp-instances/bgp:bgp-'
              + 'inst/bgp:address-family-ipv4-vpn-multi/bgp:neighbor-ipv4/bgp:n'
              + 'eighbor/bgp:weight.'+"\n"
              + 'Add leaf /bgp:configuration/bgp:bgp/bgp:bgp-instances/bgp:bgp-'
              + 'inst/bgp:address-family-ipv6-vpn-mcast/bgp:neighbor-ipv4/bgp:n'
              + 'eighbor/bgp:neighbor-extend/bgp:route-map-in-name.'+"\n"
              + 'Add leaf /bgp:configuration/bgp:bgp/bgp:bgp-instances/bgp:bgp-'
              + 'inst/bgp:address-family-ipv6-vpn-mcast/bgp:neighbor-ipv4/bgp:n'
              + 'eighbor/bgp:neighbor-extend/bgp:route-map-out-name.'+"\n"
              + 'Add leaf /bgp:configuration/bgp:bgp/bgp:bgp-instances/bgp:bgp-'
              + 'inst/bgp:address-family-ipv6-vpn-mcast/bgp:neighbor-ipv4/bgp:n'
              + 'eighbor/bgp:weight.'+"\n"
              + 'Add leaf /bgp:configuration/bgp:bgp/bgp:bgp-instances/bgp:bgp-'
              + 'inst/bgp:address-family-ipv6-vpn-multi/bgp:neighbor-ipv4/bgp:n'
              + 'eighbor/bgp:neighbor-extend/bgp:route-map-in-name.'+"\n"
              + 'Add leaf /bgp:configuration/bgp:bgp/bgp:bgp-instances/bgp:bgp-'
              + 'inst/bgp:address-family-ipv6-vpn-multi/bgp:neighbor-ipv4/bgp:n'
              + 'eighbor/bgp:neighbor-extend/bgp:route-map-out-name.'+"\n"
              + 'Add leaf /bgp:configuration/bgp:bgp/bgp:bgp-instances/bgp:bgp-'
              + 'inst/bgp:address-family-ipv6-vpn-multi/bgp:neighbor-ipv4/bgp:n'
              + 'eighbor/bgp:weight.'+"\n"
              + 'Add leaf /bgp:configuration/bgp:bgp/bgp:bgp-instances/bgp:bgp-'
              + 'inst/bgp:address-family-ipv4-vrf/bgp:address-family-vrf/bgp:ri'
              + 'b-only.'+"\n"
              + 'Add leaf /bgp:configuration/bgp:bgp/bgp:bgp-instances/bgp:bgp-'
              + 'inst/bgp:address-family-ipv6-vrf/bgp:address-family-vrf/bgp:ri'
              + 'b-only.'+"\n"
              + 'Add leaf /bgp:configuration/bgp:bgp/bgp:bgp-instances/bgp:bgp-'
              + 'inst/bgp:address-family-evpn/bgp:frr-capability.'+"\n"
              + 'Add leaf /bgp:configuration/bgp:bgp/bgp:bgp-instances/bgp:bgp-'
              + 'inst/bgp:address-family-evpn/bgp:frr-wtr.'
                ;
  }
  revision 2020-02-26 {
    description 'Change leaf /bgp:configuration/bgp:bgp/bgp:error-packet/bgp:re'
              + 'cord-num default value from 10 to 70.'
                ;
  }
  revision 2020-02-13 {
    description 'Add leaf default-metric for link-state vpn.'+"\n"
              + 'Add leaf bgp sr-lsr in /configuration/bgp/bgp-instances/bgp-in'
              + 'st/address-family-ipv4-uni.'+"\n"
              + 'Add leaf bgp sr-lsr in /configuration/bgp/bgp-instances/bgp-in'
              + 'st/address-family-ipv6-uni.'
                ;
  }
  revision 2020-02-08 {
    description 'Add leaf graceful-stalepath-time-permanent.'+"\n"
              + 'Add leaf vpn-orf for bgp:address-family-vpnv4/vpnv6/evpn.'+"\n"
              + 'Add leaf vpn-orf for bgp:neighbor-vpnv4/vpnv6/evpn.'
                ;
  }
  revision 2020-02-03 {
    description '1.Obsolete passive-only and active-only nodes under /configura'
              + 'tion/bgp/bgp-instances/bgp-inst/bmp/neighbor.'+"\n"
              + '2.Add new container nodes named connection under /configuratio'
              + 'n/bgp/bgp-instances/bgp-inst/bmp/neighbor to define the mutex '
              + 'exclusion of passive-only and active-only nodes.'
                ;
  }
  revision 2020-01-13 {
    description 'Add leaf ignore-error-packet:'+"\n"
              + '/configuration/bgp/bgp-instances/bgp-inst/address-family-ipv4-'
              + 'uni/neighbor-ipv4-uni/neighbor-uni-group/neighbor-uni-peergrou'
              + 'p/ignore-error-packet;'+"\n"
              + '/configuration/bgp/bgp-instances/bgp-inst/address-family-ipv4-'
              + 'uni/neighbor-ipv4-uni/neighbor-uni-ipv4/neighbor-uni/ignore-er'
              + 'ror-packet;'+"\n"
              + '/configuration/bgp/bgp-instances/bgp-inst/address-family-ipv4-'
              + 'uni/neighbor-ipv4-uni/neighbor-uni-ipv6/neighbor-uni/ignore-er'
              + 'ror-packet;'+"\n"
              + '/configuration/bgp/bgp-instances/bgp-inst/address-family-ipv4-'
              + 'vrf/address-family-vrf/neighbor-v4-vrf/neighbor-group/neighbor'
              + '-peergroup/ignore-error-packet;'+"\n"
              + '/configuration/bgp/bgp-instances/bgp-inst/address-family-ipv4-'
              + 'vrf/address-family-vrf/neighbor-v4-vrf/neighbor-ipv4/neighbor/'
              + 'ignore-error-packet;'+"\n"
              + '/configuration/bgp/bgp-instances/bgp-inst/address-family-ipv6-'
              + 'vrf/address-family-vrf/neighbor-v6-vrf/neighbor-group/neighbor'
              + '-peergroup/ignore-error-packet;'+"\n"
              + '/configuration/bgp/bgp-instances/bgp-inst/address-family-ipv6-'
              + 'vrf/address-family-vrf/neighbor-v6-vrf/neighbor-ipv6/neighbor/'
              + 'ignore-error-packet;'
                ;
  }
  revision 2019-12-31 {
    description 'Add leaf for container virtual in address-family-vpnv4,address'
              + '-family-vpnv6 and address-family-evpn.'
                ;
  }
  revision 2019-12-05 {
    description 'Add leaf /bgp:configuration/bgp:bgp/bgp:bgp-instances/bgp:bgp-'
              + 'inst/bgp:bmp/bgp:neighbor/bgp:neighbor/bgp:neighbor-ipv4/bgp:n'
              + 'eighbor/bgp:connect-retry-interval'+"\n"
              + ''+"\n"
              + 'Add leaf /bgp:configuration/bgp:bgp/bgp:bgp-instances/bgp:bgp-'
              + 'inst/bgp:bmp/bgp:neighbor/bgp:neighbor/bgp:neighbor-ipv6/bgp:n'
              + 'eighbor/bgp:connect-retry-interval'+"\n"
              + ''+"\n"
              + 'Add leaf /bgp:configuration/bgp:bgp/bgp:bgp-instances/bgp:bgp-'
              + 'inst/bgp:bmp/bgp:neighbor/bgp:neighbor-vrf/bgp:neighbor-ipv4/b'
              + 'gp:neighbor/bgp:connect-retry-interval'+"\n"
              + ''+"\n"
              + 'Add leaf /bgp:configuration/bgp:bgp/bgp:bgp-instances/bgp:bgp-'
              + 'inst/bgp:bmp/bgp:neighbor/bgp:neighbor-vrf/bgp:neighbor-ipv6/b'
              + 'gp:neighbor/bgp:connect-retry-interval'
                ;
  }
  revision 2019-11-29 {
    description 'Add leaf receive-single-label:'+"\n"
              + '/configuration/bgp/bgp-instances/bgp-inst/address-family-ipv4-'
              + 'uni/neighbor-ipv4-uni/neighbor-uni-group/neighbor-uni-peergrou'
              + 'p/receive-single-label;'+"\n"
              + '/configuration/bgp/bgp-instances/bgp-inst/address-family-ipv4-'
              + 'uni/neighbor-ipv4-uni/neighbor-uni-ipv4/neighbor-uni/receive-s'
              + 'ingle-label;'+"\n"
              + '/configuration/bgp/bgp-instances/bgp-inst/address-family-ipv4-'
              + 'uni/neighbor-ipv4-uni/neighbor-uni-ipv6/neighbor-uni/receive-s'
              + 'ingle-label;'+"\n"
              + '/configuration/bgp/bgp-instances/bgp-inst/address-family-ipv4-'
              + 'vrf/address-family-vrf/neighbor-v4-vrf/neighbor-group/neighbor'
              + '-peergroup/receive-single-label;'+"\n"
              + '/configuration/bgp/bgp-instances/bgp-inst/address-family-ipv4-'
              + 'vrf/address-family-vrf/neighbor-v4-vrf/neighbor-ipv4/neighbor/'
              + 'receive-single-label;'+"\n"
              + '/configuration/bgp/bgp-instances/bgp-inst/address-family-ipv6-'
              + 'vrf/address-family-vrf/neighbor-v6-vrf/neighbor-group/neighbor'
              + '-peergroup/receive-single-label;'+"\n"
              + '/configuration/bgp/bgp-instances/bgp-inst/address-family-ipv6-'
              + 'vrf/address-family-vrf/neighbor-v6-vrf/neighbor-ipv6/neighbor/'
              + 'receive-single-label;'
                ;
  }
  revision 2019-11-27 {
    description '1.Add container/configuration/bgp/bgp-instances/bgp-inst/addre'
              + 'ss-family-ipv6-flowspec;'+"\n"
              + '2.Add container/configuration/bgp/bgp-instances/bgp-inst/addre'
              + 'ss-family-vpnv6-flowspec;'+"\n"
              + '3.modify leaf /operation/bgp/clear/update-group/common/v4-peer'
              + '-address/peer/afi;'+"\n"
              + '4.modify leaf /operation/bgp/clear/update-group/common/v6-peer'
              + '-address/peer/afi;'+"\n"
              + '5.modify leaf /operation/bgp/clear/update-group/common/indexes'
              + '/peer/afi;'+"\n"
              + '6.modify leaf /operation/bgp/clear/update-group/common/all/mod'
              + 'e/afi;'
                ;
  }
  revision 2019-11-06 {
    description 'Add adv-tunnel-encap leaf for neighbor-evpn.'
                ;
  }
  revision 2019-10-22 {
    description '1.Add leaf link-bandwidth-download to address-family-ipv4,addr'
              + 'ess-family-ipv6,address-family-ipv4-vrf,address-family-ipv6-vr'
              + 'f.'+"\n"
              + '2.Add leaf neighbor send-link-bandwidth to address-family-ipv4'
              + ',address-family-ipv6,address-family-vpnv4,address-family-vpnv6'
              + '.'
                ;
  }
  revision 2019-10-11 {
    description 'Add container /configuration/bgp/bgp-instances/bgp-inst/addres'
              + 's-family-link-state-vpn;'+"\n"
              + ''+"\n"
              + 'Add leaf  /configuration/bgp/bgp-instances/bgp-inst/address-fa'
              + 'mily-link-state-vpn/neighbor-group/neighbor-peergroup/neighbor'
              + '-group;'+"\n"
              + 'Add leaf  /configuration/bgp/bgp-instances/bgp-inst/address-fa'
              + 'mily-link-state-vpn/neighbor-group/neighbor-peergroup/active;'+"\n"
              + 'Add leaf  /configuration/bgp/bgp-instances/bgp-inst/address-fa'
              + 'mily-link-state-vpn/neighbor-group/neighbor-peergroup/route-re'
              + 'flector-client;'+"\n"
              + 'Add leaf  /configuration/bgp/bgp-instances/bgp-inst/address-fa'
              + 'mily-link-state-vpn/neighbor-ipv4/neighbor/ipv4-address;'+"\n"
              + 'Add leaf  /configuration/bgp/bgp-instances/bgp-inst/address-fa'
              + 'mily-link-state-vpn/neighbor-ipv4/neighbor/joined-group;'+"\n"
              + 'Add leaf  /configuration/bgp/bgp-instances/bgp-inst/address-fa'
              + 'mily-link-state-vpn/neighbor-ipv4/neighbor/active;'+"\n"
              + 'Add leaf  /configuration/bgp/bgp-instances/bgp-inst/address-fa'
              + 'mily-link-state-vpn/neighbor-ipv4/neighbor/route-reflector-cli'
              + 'ent;'+"\n"
              + ''+"\n"
              + 'Add leaf  /configuration/bgp/bgp-instances/bgp-inst/address-fa'
              + 'mily-link-state-vpn/neighbor-ipv6/neighbor/ipv6-address;'+"\n"
              + 'Add leaf  /configuration/bgp/bgp-instances/bgp-inst/address-fa'
              + 'mily-link-state-vpn/neighbor-ipv6/neighbor/joined-group;'+"\n"
              + 'Add leaf  /configuration/bgp/bgp-instances/bgp-inst/address-fa'
              + 'mily-link-state-vpn/neighbor-ipv6/neighbor/active;'+"\n"
              + 'Add leaf  /configuration/bgp/bgp-instances/bgp-inst/address-fa'
              + 'mily-link-state-vpn/neighbor-ipv6/neighbor/route-reflector-cli'
              + 'ent;'+"\n"
              + 'modify leaf /operation/clear/soft/common/v4-peer-address/peer/'
              + 'direction'+"\n"
              + 'modify leaf /operation/bgp/clear/soft/common/v6-peer-address/p'
              + 'eer/direction'+"\n"
              + 'modify leaf /operation/bgp/clear/soft/common/peer-groups/peer-'
              + 'group/direction'+"\n"
              + 'modify leaf /operation/bgp/clear/soft/common/all/mode/directio'
              + 'n'+"\n"
              + 'modify leaf /state/bgp/peer-afi/peer/afi'
                ;
  }
  revision 2019-09-24 {
    description '1.Add leaf configuration/bgp/bgp-instances/bgp-inst/address-fa'
              + 'mily-ipv4-uni/neighbor-ipv4-uni/neighbor-uni-ipv4/sr-epe-peer-'
              + 'set;'+"\n"
              + '2.Add contianer configuration/bgp/bgp-instances/bgp-inst/addre'
              + 'ss-family-ipv4-uni/neighbor-ipv4-uni/neighbor-uni-ipv4/sr-epe-'
              + 'peer-adj;'+"\n"
              + '3.Add leaf configuration/bgp/bgp-instances/bgp-inst/address-fa'
              + 'mily-ipv4-uni/neighbor-ipv4-uni/neighbor-uni-group/sr-epe-peer'
              + '-set;'+"\n"
              + '4.Add leaf configuration/bgp/bgp-instances/bgp-inst/address-fa'
              + 'mily-ipv4-uni/neighbor-ipv4-uni/neighbor-uni-ipv6/sr-epe-peer-'
              + 'set;'+"\n"
              + '5.Add contianer configuration/bgp/bgp-instances/bgp-inst/addre'
              + 'ss-family-ipv4-uni/neighbor-ipv4-uni/neighbor-uni-ipv6/sr-epe-'
              + 'peer-adj;'+"\n"
              + '6.Add leaf configuration/bgp/bgp-instances/bgp-inst/address-fa'
              + 'mily-ipv4-uni/neighbor-ipv4-uni/neighbor-uni-ipv4/backup-addrv'
              + '6;'+"\n"
              + '7.Add leaf configuration/bgp/bgp-instances/bgp-inst/address-fa'
              + 'mily-ipv4-uni/neighbor-ipv4-uni/neighbor-uni-group/backup-addr'
              + 'v6;'+"\n"
              + '8.Add leaf configuration/bgp/bgp-instances/bgp-inst/address-fa'
              + 'mily-ipv4-uni/neighbor-ipv4-uni/neighbor-uni-ipv6/backup-addrv'
              + '6;'
                ;
  }
  revision 2019-09-10 {
    description 'Add leaf border-gateway /configuration/bgp/bgp-instances/bgp-i'
              + 'nst/address-family-evpn/neighbor-evpn/neighbor-group/neighbor-'
              + 'peergroup/border-gateway;'+"\n"
              + 'Add leaf border-gateway /configuration/bgp/bgp-instances/bgp-i'
              + 'nst/address-family-evpn/neighbor-evpn/neighbor-ipv4/neighbor/b'
              + 'order-gateway;'+"\n"
              + 'Add leaf border-gateway /configuration/bgp/bgp-instances/bgp-i'
              + 'nst/address-family-evpn/neighbor-evpn/neighbor-ipv6/neighbor/b'
              + 'order-gateway;'
                ;
  }
  revision 2019-09-04 {
    description 'Add vrf-peer-list leaf for address-family-vpnv4 and address-fa'
              + 'mily-vpnv6, address-family-l2vpn-evpnx.'
                ;
  }
  revision 2019-08-26 {
    description 'Add /configuration/bgp/bgp-instances/bgp-inst/address-family-i'
              + 'pv4-sr-policy and /configuration/bgp/bgp-instances/bgp-inst/ad'
              + 'dress-family-ipv6-sr-policy container'
                ;
  }
  revision 2019-08-19 {
    description '/configuration/bgp/bgp-instances/bgp-inst/address-family-ipv4-'
              + 'vrf/address-family-vrf/neighbor-v4-vrf/neighbor-group/neighbor'
              + '-peergroup/route-reflector-client;'+"\n"
              + '/configuration/bgp/bgp-instances/bgp-inst/address-family-ipv4-'
              + 'vrf/address-family-vrf/neighbor-v4-vrf/neighbor-ipv4/neighbor/'
              + 'route-reflector-client;'+"\n"
              + '/configuration/bgp/bgp-instances/bgp-inst/address-family-ipv6-'
              + 'vrf/address-family-vrf/neighbor-v6-vrf/neighbor-group/neighbor'
              + '-peergroup/route-reflector-client;'+"\n"
              + '/configuration/bgp/bgp-instances/bgp-inst/address-family-ipv6-'
              + 'vrf/address-family-vrf/neighbor-v6-vrf/neighbor-ipv6/neighbor/'
              + 'route-reflector-client;'+"\n"
              + 'Add leaf orig-map configuration/bgp/bgp-instances/bgp-inst/add'
              + 'ress-family-ipv4-uni/aggregate-v4-uni/aggregate-nosub/aggregat'
              + 'e-without-sub/agg-policy/route-map/orig-map;'+"\n"
              + 'Add leaf orig-map configuration/bgp/bgp-instances/bgp-inst/add'
              + 'ress-family-ipv4-vrf/address-family-vrf/aggregate-v4-vrf/aggre'
              + 'gate/agg-policy/route-map/orig-map;'+"\n"
              + 'Add leaf orig-map configuration/bgp/bgp-instances/bgp-inst/add'
              + 'ress-family-ipv6-uni/aggregate-v6-uni/aggregate/agg-policy/rou'
              + 'te-map/orig-map;'+"\n"
              + 'Add leaf orig-map configuration/bgp/bgp-instances/bgp-inst/add'
              + 'ress-family-ipv6-vrf/address-family-vrf/aggregate-v6-vrf/aggre'
              + 'gate/agg-policy/route-map/orig-map;'
                ;
  }
  revision 2019-08-16 {
    description 'Obsolete type /bgp:configuration/bgp:bgp/bgp:bgp-instances/bgp'
              + ':bgp-inst/bgp:address-family-evpn/bgp:vtep-group-address/bgp:v'
              + 'tep-group-address/bgp:address-v6/bgp:vtep-group-address-v6 and'
              + ' add /bgp:configuration/bgp:bgp/bgp:bgp-instances/bgp:bgp-inst'
              + '/bgp:address-family-evpn/bgp:vtep-group-address/bgp:vtep-group'
              + '-address/bgp:address-v6/bgp:vtep-group-address-v6-ex'
                ;
  }
  revision 2019-08-08 {
    description 'Add global maximum paths for bgp instance.'+"\n"
              + 'Add container maximum-prefix for address family evpn;'+"\n"
              + 'Add leaf configuration/bgp/bgp-instances/bgp-inst/address-fami'
              + 'ly-vpnv4/bgp-bestpath-origin;'+"\n"
              + 'Add leaf configuration/bgp/bgp-instances/bgp-inst/address-fami'
              + 'ly-vpnv6/bgp-bestpath-origin;'+"\n"
              + 'Add leaf configuration/bgp/bgp-instances/bgp-inst/address-fami'
              + 'ly-ipv4-vrf/bgp-bestpath-origin;'+"\n"
              + 'Add leaf configuration/bgp/bgp-instances/bgp-inst/address-fami'
              + 'ly-ipv6-vrf/bgp-bestpath-origin;'+"\n"
              + 'Add leaf configuration/bgp/bgp-instances/bgp-inst/address-fami'
              + 'ly-evpn/bgp-bestpath-origin;'+"\n"
              + 'Add leaf configuration/bgp/bgp-instances/bgp-inst/address-fami'
              + 'ly-vpnv4/neighbor-vpnv4/neighbor-group/neighbor-peergroup/soft'
              + '-reconfig;'+"\n"
              + 'Add leaf configuration/bgp/bgp-instances/bgp-inst/address-fami'
              + 'ly-vpnv4/neighbor-vpnv4/neighbor-ipv4/neighbor/soft-reconfig;'+"\n"
              + 'Add leaf configuration/bgp/bgp-instances/bgp-inst/address-fami'
              + 'ly-vpnv4/neighbor-vpnv4/neighbor-ipv6/neighbor/soft-reconfig;'+"\n"
              + 'Add leaf configuration/bgp/bgp-instances/bgp-inst/address-fami'
              + 'ly-vpnv6/neighbor-vpnv6/neighbor-group/neighbor-peergroup/soft'
              + '-reconfig;'+"\n"
              + 'Add leaf configuration/bgp/bgp-instances/bgp-inst/address-fami'
              + 'ly-vpnv6/neighbor-vpnv6/neighbor-ipv4/neighbor/soft-reconfig;'+"\n"
              + 'Add leaf configuration/bgp/bgp-instances/bgp-inst/address-fami'
              + 'ly-vpnv6/neighbor-vpnv6/neighbor-ipv6/neighbor/soft-reconfig;'+"\n"
              + 'Add leaf configuration/bgp/bgp-instances/bgp-inst/address-fami'
              + 'ly-evpn/neighbor-evpn/neighbor-group/neighbor-peergroup/soft-r'
              + 'econfig;'+"\n"
              + 'Add leaf configuration/bgp/bgp-instances/bgp-inst/address-fami'
              + 'ly-evpn/neighbor-evpn/neighbor-ipv4/neighbor/soft-reconfig;'+"\n"
              + 'Add leaf configuration/bgp/bgp-instances/bgp-inst/address-fami'
              + 'ly-evpn/neighbor-evpn/neighbor-ipv6/neighbor/soft-reconfig;'
                ;
  }
  revision 2019-07-29 {
    description 'Add leaf statistics-timer,route-mode,monitor all-peers for /co'
              + 'nfiguration/bgp/bgp-instances/bgp-inst/bmp.'+"\n"
              + 'Add leaf neighbor monitor for address-family-ipv4-uni,address-'
              + 'family-ipv6-uni,address-family-ipv4-vrf and address-family-ipv'
              + '6-vrf,address-family-vpnv4,address-family-vpnv6,address-family'
              + '-evpn,.'+"\n"
              + 'Add address of leaf redistribute protocol configuration/bgp/bg'
              + 'p-instances/bgp-inst/address-family-ipv4-multi/redistribute-ip'
              + 'v4-multi/redistribute-multi/redistribute/protocol;'+"\n"
              + 'Add address of leaf redistribute protocol configuration/bgp/bg'
              + 'p-instances/bgp-inst/address-family-ipv4-uni/redistribute-ipv4'
              + '-uni/redistribute-uni/redistribute/protocol;'+"\n"
              + 'Add address of leaf redistribute protocol configuration/bgp/bg'
              + 'p-instances/bgp-inst/address-family-ipv4-vrf/address-family-vr'
              + 'f/redistribute-v4-vrf/redistribute-vrf/redistribute/protocol;'+"\n"
              + 'Add address of leaf redistribute protocol configuration/bgp/bg'
              + 'p-instances/bgp-inst/address-family-ipv4-vrf/address-family-vr'
              + 'f/multicast/redistribute/redistribute/redistribute/protocol;'+"\n"
              + 'Add address of leaf redistribute protocol configuration/bgp/bg'
              + 'p-instances/bgp-inst/address-family-ipv6-uni/redistribute-v6-u'
              + 'ni/redistribute-v6-uni/redistribute/protocol;'+"\n"
              + 'Add address of leaf redistribute protocol configuration/bgp/bg'
              + 'p-instances/bgp-inst/address-family-ipv6-multi/redistribute-ip'
              + 'v6-multi/redistribute-multi/redistribute/protocol;'+"\n"
              + 'Add address of leaf redistribute protocol configuration/bgp/bg'
              + 'p-instances/bgp-inst/address-family-ipv6-vrf/address-family-vr'
              + 'f/redistribute-v6-vrf/redistribute-vrf/redistribute/protocol;'+"\n"
              + 'Add address of leaf redistribute protocol configuration/bgp/bg'
              + 'p-instances/bgp-inst/address-family-ipv6-vrf/address-family-vr'
              + 'f/multicast/redistribute/redistribute/redistribute/protocol;'
                ;
  }
  revision 2019-07-24 {
    description '1.Add leaf configuration/bgp/bgp-instances/bgp-inst/address-fa'
              + 'mily-ipv4-flowspec/neighbor-ipv4-flowspec/neighbor-group/neigh'
              + 'bor-peergroup/send-community;'+"\n"
              + '2.Add leaf configuration/bgp/bgp-instances/bgp-inst/address-fa'
              + 'mily-ipv4-flowspec/neighbor-ipv4-flowspec/neighbor-group/neigh'
              + 'bor-peergroup/neighbor-extend;'+"\n"
              + '3.Add leaf configuration/bgp/bgp-instances/bgp-inst/address-fa'
              + 'mily-ipv4-flowspec/neighbor-ipv4-flowspec/neighbor-ipv4/neighb'
              + 'or/send-community;'+"\n"
              + '4.Add container configuration/bgp/bgp-instances/bgp-inst/addre'
              + 'ss-family-ipv4-flowspec/neighbor-ipv4-flowspec/neighbor-ipv4/n'
              + 'eighbor/neighbor-extend;'+"\n"
              + '5.Add leaf configuration/bgp/bgp-instances/bgp-inst/address-fa'
              + 'mily-vpnv4-flowspec/neighbor-vpnv4-flowspec/neighbor-group/nei'
              + 'ghbor-peergroup/send-community;'+"\n"
              + '6.Add container configuration/bgp/bgp-instances/bgp-inst/addre'
              + 'ss-family-vpnv4-flowspec/neighbor-vpnv4-flowspec/neighbor-grou'
              + 'p/neighbor-peergroup/neighbor-extend;'+"\n"
              + '7.Add leaf configuration/bgp/bgp-instances/bgp-inst/address-fa'
              + 'mily-vpnv4-flowspec/neighbor-vpnv4-flowspec/neighbor-ipv4/neig'
              + 'hbor/send-community;'+"\n"
              + '8.Add container configuration/bgp/bgp-instances/bgp-inst/addre'
              + 'ss-family-vpnv4-flowspec/neighbor-vpnv4-flowspec/neighbor-ipv4'
              + '/neighbor/neighbor-extend;'
                ;
  }
  revision 2019-07-11 {
    description '1.Obsolete leaf configuration/bgp/bgp-instances/bgp-inst/addre'
              + 'ss-family-link-state/neighbor-link-state/neighbor-group/neighb'
              + 'or-peergroup/link-state.'+"\n"
              + '2.Obsolete leaf configuration/bgp/bgp-instances/bgp-inst/addre'
              + 'ss-family-link-state/neighbor-link-state/neighbor-group/neighb'
              + 'or-peergroup/backup.'+"\n"
              + '3.Obsolete leaf configuration/bgp/bgp-instances/bgp-inst/addre'
              + 'ss-family-link-state/neighbor-link-state/neighbor-ipv4/neighbo'
              + 'r/link-state.'+"\n"
              + '4.Obsolete leaf configuration/bgp/bgp-instances/bgp-inst/addre'
              + 'ss-family-link-state/neighbor-link-state/neighbor-ipv4/neighbo'
              + 'r/backup.'+"\n"
              + '5.Obsolete leaf configuration/bgp/bgp-instances/bgp-inst/addre'
              + 'ss-family-link-state/neighbor-link-state/neighbor-ipv6/neighbo'
              + 'r/link-state.'+"\n"
              + '6.Obsolete leaf configuration/bgp/bgp-instances/bgp-inst/addre'
              + 'ss-family-link-state/neighbor-link-state/neighbor-ipv6/neighbo'
              + 'r/backup.'+"\n"
              + '7.Add leaf configuration/bgp/bgp-instances/bgp-inst/address-fa'
              + 'mily-ipv4-uni/neighbor-ipv4-uni/neighbor-uni-group/neighbor-un'
              + 'i-peergroup/sr-epe.'+"\n"
              + '8.Add leaf configuration/bgp/bgp-instances/bgp-inst/address-fa'
              + 'mily-ipv4-uni/neighbor-ipv4-uni/neighbor-uni-group/neighbor-un'
              + 'i-peergroup/backup.'+"\n"
              + '9.Add leaf configuration/bgp/bgp-instances/bgp-inst/address-fa'
              + 'mily-ipv4-uni/neighbor-ipv4-uni/neighbor-uni-ipv4/neighbor-uni'
              + '/sr-epe.'+"\n"
              + '10.Add leaf configuration/bgp/bgp-instances/bgp-inst/address-f'
              + 'amily-ipv4-uni/neighbor-ipv4-uni/neighbor-uni-ipv4/neighbor-un'
              + 'i/backup.'+"\n"
              + '11.Add leaf configuration/bgp/bgp-instances/bgp-inst/address-f'
              + 'amily-ipv4-uni/neighbor-ipv4-uni/neighbor-uni-ipv6/neighbor-un'
              + 'i/sr-epe.'+"\n"
              + '12.Add leaf configuration/bgp/bgp-instances/bgp-inst/address-f'
              + 'amily-ipv4-uni/neighbor-ipv4-uni/neighbor-uni-ipv6/neighbor-un'
              + 'i/backup.'+"\n"
              + '13.Obsolete link-state of enumeration link-state.'
                ;
  }
  revision 2019-07-07 {
    description 'Add import-l2vpn-evpn leaf for address-family-vpnv4 and addres'
              + 's-family-vpnv6,add import-vpnv4-uni and import-vpnv6-uni for a'
              + 'ddress-family-l2vpn-evpn,and add update-source-ipv6 choice for'
              + ' update-source-ex.'
                ;
  }
  revision 2019-07-01 {
    description '1. Add leaf configuration/bgp/bgp-instances/bgp-inst/address-f'
              + 'amily-ipv4-uni/additional-paths-send-igp-path.'+"\n"
              + '2. Add leaf configuration/bgp/bgp-instances/bgp-inst/address-f'
              + 'amily-ipv6-uni/additional-paths-send-igp-path.'+"\n"
              + '3. Add leaf configuration/bgp/bgp-instances/bgp-inst/address-f'
              + 'amily-ipv4-uni/additional-paths-different-color.'+"\n"
              + '4. Add leaf configuration/bgp/bgp-instances/bgp-inst/address-f'
              + 'amily-ipv6-uni/additional-paths-different-color.'
                ;
  }
  revision 2019-06-25 {
    description 'Add evpn damp for address-family-evpn.'
                ;
  }
  revision 2019-06-22 {
    description 'Add some send-ope nodes for address-family-l2vpn-evpn.'
                ;
  }
  revision 2019-06-19 {
    description '1.Adjust the order of configuration/bgp/bgp-instances/bgp-inst'
              + '/bgp/bestpath-bgp-lu-nexthop-compare to ensure that the leaf i'
              + 's the last node of the container.Because the mim object mapped'
              + ' by this node is different from other nodes in the same contai'
              + 'ner, or the merge-replace will not be correct.'+"\n"
              + '2.When creating a BGP instance, only one IPv4 unicast address '
              + 'family record is generated, and no other address family record'
              + 's are created. VRF multicast address family is not created whe'
              + 'n creating VRF address family.This change started with version'
              + ' ZXROSNGV8.00.11R2.'
                ;
  }
  revision 2019-06-10 {
    description 'Add enumeration value to node /bgp:operation/bgp:bgp/bgp:clear'
              + '/bgp:soft/bgp:common.'
                ;
  }
  revision 2019-06-04 {
    description '1.Add next-hop-unchanged to address-family-ipv4,address-family'
              + '-ipv6,address-family-ipv4-vpn-mcast,address-family-ipv6-vpn-mc'
              + 'ast,address-family-ipv4-vpn-multi,address-family-ipv6-vpn-mult'
              + 'i,address-family-mdt.'
                ;
  }
  revision 2019-05-20 {
    description 'Add container /configuration/bgp/bgp-instances/bgp-inst/addres'
              + 's-family-vpls/neighbor-ipv6.'
                ;
  }
  revision 2019-05-13 {
    description 'Add enumeration value to node /bgp:state/bgp:bgp/bgp:peer-afi/'
              + 'bgp:peer/bgp:afi.'
                ;
  }
  revision 2019-04-23 {
    description 'Add bfd-hop leaf'
                ;
  }
  revision 2019-04-10 {
    description '1.Add presence to address-family-vpls,address-family-mdt,addre'
              + 'ss-family-ipv4-vpn-mcast,address-family-ipv4-vpn-multi,address'
              + '-family-rt,address-family-ipv4-multi,address-family-vpnv4,addr'
              + 'ess-family-evpn,address-family-link-state,address-family-ipv6-'
              + 'uni,address-family-ipv6-multi,address-family-vpnv6,address-fam'
              + 'ily-ipv6-vpn-mcast,address-family-ipv6-vpn-multi,address-famil'
              + 'y-ipv4-flowspec and address-family-vpnv4-flowspec.'+"\n"
              + '2.Add leaf node default-metric to address-family-vpls,address-'
              + 'family-mdt,address-family-ipv4-vpn-mcast,address-family-ipv4-v'
              + 'pn-multi,address-family-link-state,address-family-ipv6-vpn-mca'
              + 'st,address-family-ipv6-vpn-multi,address-family-ipv4-flowspec,'
              + 'address-family-vpnv4-flowspec.'+"\n"
              + '3.Add presence to multicast in address-family-ipv4-vrf and add'
              + 'ress-family-ipv6-vrf.'+"\n"
              + '4.Add leaf node default-metric to multicast in address-family-'
              + 'ipv4-vrf and address-family-ipv6-vrf.'+"\n"
              + '5.Add leaf node ip-route-esi-index-ex for address-family-evpn.'
              + ''+"\n"
              + '6.Obsolete leaf node ip-route-esi-index.'
                ;
  }
  revision 2019-02-21 {
    description '1. Add leaf configuration/bgp/bgp-instances/bgp-inst/address-f'
              + 'amily-ipv4-uni/entropy-label.'+"\n"
              + '2. Add leaf configuration/bgp/bgp-instances/bgp-inst/address-f'
              + 'amily-ipv4-vrf/address-family-vrf/entropy-label.'+"\n"
              + '3. Add leaf configuration/bgp/bgp-instances/bgp-inst/address-f'
              + 'amily-ipv6-uni/entropy-label.'+"\n"
              + '4. Add leaf configuration/bgp/bgp-instances/bgp-inst/address-f'
              + 'amily-ipv6-vrf/address-family-vrf/entropy-label.'
                ;
  }
  revision 2019-02-15 {
    description 'Add bestpath-virtual-spoke leaf.'
                ;
  }
  revision 2019-01-15 {
    description 'Add leaf node tracking-ex for tracking.'+"\n"
              + '    Obsolete leaf node tracking of tracking.'+"\n"
              + '    Add redistribute-v4-uni protocol type dyn-leasedline.'+"\n"
              + '    Add redistribute-ipv4-multi protocol type dyn-leasedline.'+"\n"
              + '    Add redistribute-v4-vrf protocol type dyn-leasedline.'+"\n"
              + '    Add redistribute-v4-vrf-multi protocol type dyn-leasedline'
              + '.'+"\n"
              + '    Add redistribute-v6-uni protocol type dyn-leasedline.'+"\n"
              + '    Add redistribute-ipv6-multi protocol type dyn-leasedline.'+"\n"
              + '    Add redistribute-v6-vrf protocol type dyn-leasedline.'+"\n"
              + '    Add redistribute-v6-vrf-multi protocol type dyn-leasedline'
              + '.'+"\n"
              + '    Add four-byte-as-disable for ipv4-unicast,ipv4-vrf and ipv'
              + '6-vrf.'
                ;
  }
  revision 2019-01-10 {
    description 'Add peer-list-name leaf for address-family-evpn and address-fa'
              + 'mily-vpnv6.'
                ;
  }
  revision 2019-01-01 {
    description 'Add leaf neighbor-gr;'+"\n"
              + 'Add route-scan-time,interval-wait,Initial,max-wait node in add'
              + 'ress-family-evpn.'
                ;
  }
  revision 2018-12-24 {
    description 'Add bgp bestpath ecmp-as-path-value-ignore node .'
                ;
  }
  revision 2018-12-12 {
    description '1. Add the container of configuration/bgp/bgp-instances/bgp-in'
              + 'st/address-family-link-state/neighbor-link-state/neighbor-ipv6'
              + '.'+"\n"
              + '2. Add leaf configuration/bgp/bgp-instances/bgp-inst/address-f'
              + 'amily-link-state/neighbor-link-state/neighbor-ipv6/neighbor/ip'
              + 'v6-address.'+"\n"
              + '3. Add leaf configuration/bgp/bgp-instances/bgp-inst/address-f'
              + 'amily-link-state/neighbor-link-state/neighbor-ipv6/neighbor/jo'
              + 'ined-group.'+"\n"
              + '4. Add leaf configuration/bgp/bgp-instances/bgp-inst/address-f'
              + 'amily-link-state/neighbor-link-state/neighbor-ipv6/neighbor/ac'
              + 'tivate.'+"\n"
              + '5. Add leaf configuration/bgp/bgp-instances/bgp-inst/address-f'
              + 'amily-link-state/neighbor-link-state/neighbor-ipv6/neighbor/ro'
              + 'ute-reflector-client.'+"\n"
              + '6. Add leaf configuration/bgp/bgp-instances/bgp-inst/address-f'
              + 'amily-link-state/neighbor-link-state/neighbor-ipv6/neighbor/li'
              + 'nk-state.'+"\n"
              + '7. Add leaf configuration/bgp/bgp-instances/bgp-inst/address-f'
              + 'amily-link-state/neighbor-link-state/neighbor-ipv6/neighbor/ba'
              + 'ckup.'
                ;
  }
  revision 2018-12-11 {
    description 'Add ebgp-interface-sensitive for address-family-ipv4-uni,addre'
              + 'ss-family-ipv4-vrf and address-family-ipv6-vrf.'
                ;
  }
  revision 2018-11-27 {
    description 'Add update-source in address-family ipv4,address-family-ipv4-v'
              + 'rf and address-family-ipv6-vrf.'
                ;
  }
  revision 2018-11-16 {
    description 'Add container "bgp-routes-label" in path "/bgp:configuration/b'
              + 'gp:bgp/bgp:bgp-instances/bgp:bgp-inst/bgp:address-family-evpn"'
              + '.'
                ;
  }
  revision 2018-11-06 {
    description 'Add send-label for peer-group in address-family ipv4,address-f'
              + 'amily ipv6,address-family-ipv4-vrf and address-family-ipv6-vrf'
              + '.'
                ;
  }
  revision 2018-10-31 {
    description 'Add additional-paths-send-igp-path node for address-family-l2v'
              + 'pn-evpn.'
                ;
  }
  revision 2018-10-23 {
    description 'Add enhanced-route-refresh-disable for address-family-ipv4-uni'
              + ',address-family-ipv4-vrf and address-family-ipv6-vrf.'
                ;
  }
  revision 2018-10-12 {
    description 'Add leaf "bgp-label" in path "/bgp:configuration/bgp:bgp/bgp:b'
              + 'gp-instances/bgp:bgp-inst/bgp:address-family-evpn".'
                ;
  }
  revision 2018-10-11 {
    description 'Add vtep-group-address node for address-family-l2vpn-evpn.'
                ;
  }
  revision 2018-09-03 {
    description 'Add default-set-mpls-label leaf.'
                ;
  }
  revision 2018-08-29 {
    description 'Add neighbor tracking container for address-family-ipv4-uni,ad'
              + 'dress-family-ipv4-vrf and address-family-ipv6-vrf.'
                ;
  }
  revision 2018-08-04 {
    description 'Add group-to-group container.'
                ;
  }
  revision 2018-07-21 {
    description 'add route-policy for aggregate.'+"\n"
              + 'Add neighbor send-local-route without-esi-reference node for a'
              + 'ddress-family-l2vpn-evpn.'
                ;
  }
  revision 2018-07-12 {
    description 'Add second-withdraw for neighbor-extend list.'
                ;
  }
  revision 2018-07-11 {
    description 'Add local-inclusive-multicast-auto-generate node for address-f'
              + 'amily-l2vpn-evpn.'
                ;
  }
  revision 2018-06-20 {
    description 'Add withdraw track-group node for address-family-evpn.'
                ;
  }
  revision 2018-06-11 {
    description 'Obsolete node rpki-validation of address-family-ipv4-vrf and a'
              + 'ddress-family-ipv6-vrf.'
                ;
  }
  revision 2018-05-14 {
    description 'Add announce-sid node for address-family-ipv4-uni,address-fami'
              + 'ly-ipv6-uni,address-family-ipv4-vrf,address-family-ipv6-vrf,ad'
              + 'dress-family-vpnv4,address-family-vpnv6,address-family-evpn an'
              + 'd Add neighbor-ipv6 container node for address-family-vpnv4,ad'
              + 'd virtual-spoke and default-originate node for address-family-'
              + 'evpn.'
                ;
  }
  revision 2018-04-23 {
    description 'Add bgp tcp-linger-on node for bgp instance configuration.'
                ;
  }
  revision 2018-04-16 {
    description 'Add bgp-as-notation-plain node for global configuration.'
                ;
  }
  revision 2018-04-08 {
    description 'Add bgp-lu-nexthop-compare node for address-family-ipv4-uni,ad'
              + 'dress-family-ipv6-uni.'
                ;
  }
  revision 2018-01-31 {
    description 'Discard some soft-reconfiguration nodes for address-family-ipv'
              + '4-uni,address-family-ipv4-vrf and address-family-ipv6-vrf,addr'
              + 'ess-family-ipv6-uni.'+"\n"
              + 'Add some soft-reconfig nodes for address-family-ipv4-uni,addre'
              + 'ss-family-ipv4-vrf and address-family-ipv6-vrf,address-family-'
              + 'ipv6-uni.'+"\n"
              + 'Add defaults-set-flag for address-family-evpn.'
                ;
  }
  revision 2018-01-10 {
    description 'Add evpn track vpn-frr node for address-family-l2vpn-evpn.'+"\n"
              + 'Add error-packet node for bgp.'+"\n"
              + 'The operation nodes add the optional parameters and the state '
              + 'nodes add keywords.'+"\n"
              + 'Add enforce-first-as-disable node for address-family-ipv4-uni,'
              + 'address-family-ipv4-vrf,address-family-ipv6-vrf.'
                ;
  }
  revision 2017-11-28 {
    description 'Add configuration/bgp/bgp-instances/bgp-inst/address-family-ev'
              + 'pn/neighbor-evpn/neighbor-ipv6,add operation/bgp/clear/in-pref'
              + 'ix-list/common/v6-peer-address.'
                ;
  }
  revision 2017-11-16 {
    description 'Add urpf-id-download container node for address-family-ipv4-un'
              + 'i,address-family-ipv4-vrf,address-family-ipv6-uni,address-fami'
              + 'ly-ipv6-vrf'
                ;
  }
  revision 2017-11-01 {
    description 'Add bestpath-aigp-ignore node for bgp instance.'+"\n"
              + 'Add aigp node for address-family-ipv4-uni,address-family-vpnv4'
              + ',address-family-ipv4-vrf,address-family-ipv6-uni,address-famil'
              + 'y-ipv6-vrf,address-family-vpnv6 and address-family-evpn.'
                ;
  }
  revision 2017-10-23 {
    description 'Add cluster-id container node for address-family-ipv4-uni'
                ;
  }
  revision 2017-08-25 {
    description 'Add select-resolved-nexthop node for bgp-instances.'+"\n"
              + '                 Add mac-route-esi-index and ip-route-esi-inde'
              + 'x for address-family-l2vpn-evpn.'
                ;
  }
  revision 2017-08-16 {
    description 'Add redistribute-v4-uni protocol type hagp.'+"\n"
              + '				 Add redistribute-ipv4-multi protocol type hagp.'+"\n"
              + '				 Add redistribute-v4-vrf protocol type hagp.'+"\n"
              + '				 Add redistribute-v4-vrf-multi protocol type hagp.'+"\n"
              + '				 Add redistribute-v6-uni protocol type hagp.'+"\n"
              + '				 Add redistribute-ipv6-multi protocol type hagp.'+"\n"
              + '				 Add redistribute-v6-vrf protocol type hagp.'+"\n"
              + '				 Add redistribute-v6-vrf-multi protocol type hagp.'
                ;
  }
  revision 2017-07-26 {
    description 'Add link-state node for address-family-link-state;'+"\n"
              + '                 Add backup node for address-family-link-state'
              + ';'
                ;
  }
  revision 2017-07-25 {
    description 'Add inherit-igp-metric container node for address-family-ipv4-'
              + 'uni,address-family-vpnv4,address-family-ipv4-vrf,address-famil'
              + 'y-ipv6-uni,address-family-ipv6-vrf,address-family-vpnv6.'
                ;
  }
  revision 2017-07-05 {
    description 'Add  bestpath-igp-metric-compare node for address-family-ipv4-'
              + 'uni,address-family-vpnv4,address-family-ipv6-uni,address-famil'
              + 'y-vpnv6.'
                ;
  }
  revision 2017-06-12 {
    description 'Add route-filter-group container node for address-family-ipv4-'
              + 'uni,address-family-vpnv4,address-family-ipv4-vrf,address-famil'
              + 'y-ipv6-uni,address-family-ipv6-vrf,address-family-vpnv6.'
                ;
  }
  revision 2017-05-24 {
    description 'Add vpn-frr-capability/vpn-frr-wtr node for address-family-vpn'
              + 'v4;'+"\n"
              + 'Add vpn-frr-capability/vpn-frr-wtr node for address-family-vpn'
              + 'v6;'
                ;
  }
  revision 2017-04-05 {
    description 'Add capability-orf-prefix-list node for address-family-evpn;ad'
              + 'd prefix-list-in-name prefix-list-out-name node for address-fa'
              + 'mily-evpn;add enumeration value l2vpn-evpn.'
                ;
  }
  revision 2017-03-28 {
    description 'Add redistribute-v4-uni protocol type ipsec.'+"\n"
              + '                 Add redistribute-ipv4-multi protocol type ips'
              + 'ec.'+"\n"
              + '                 Add redistribute-v4-vrf protocol type ipsec.'+"\n"
              + '                 Add redistribute-v4-vrf-multi protocol type i'
              + 'psec.'
                ;
  }
  revision 2017-02-23 {
    description 'Add update-lowest-priority-time node for bgp_inst;add default-'
              + 'metric node for address-family-evpn;add send-med node for addr'
              + 'ess-family-evpn.'
                ;
  }
  revision 2017-01-16 {
    description 'Add redistribute-v4-uni protocol type bras-pool.'+"\n"
              + 'Add redistribute-ipv4-multi protocol type bras-pool.'+"\n"
              + 'Add redistribute-v4-vrf protocol type bras-pool.'+"\n"
              + 'Add redistribute-v4-vrf-multi protocol type bras-pool.'+"\n"
              + 'Add redistribute-v6-uni protocol type bras-pool.'+"\n"
              + 'Add redistribute-ipv6-multi protocol type bras-pool.'+"\n"
              + 'Add redistribute-v6-vrf protocol type bras-pool.'+"\n"
              + 'Add redistribute-v6-vrf-multi protocol type bras-pool.'
                ;
  }
  revision 2016-11-15 {
    description 'Add advertise-map-uni nodes for address-family-ipv6-uni,addres'
              + 's-family-ipv6-vrf,address-family-vpnv6.'
                ;
  }
  revision 2016-10-25 {
    description 'Add next-hop-self  nodes for address-family-l2vpn-evpn.'
                ;
  }
  revision 2016-07-07 {
    description 'Add some additional-path capability nodes for address-family-l'
              + '2vpn-evpn.'
                ;
  }
  revision 2016-06-12 {
    description 'Add some bgp-label nodes for address-family-vpnv4   address-fa'
              + 'mily-vpnv6.'+"\n"
              + 'Discard some label-per-nexthop nodes for address-family-vpnv4 '
              + '  address-family-vpnv6.'+"\n"
              + 'Discard some shut-down nodes for address-family-ipv4-uni,addre'
              + 'ss-family-ipv4-vrf and address-family-ipv6-vrf.'+"\n"
              + 'Add some shutdown containers for address-family-ipv4-uni,addre'
              + 'ss-family-ipv4-vrf and address-family-ipv6-vrf.'
                ;
  }
  revision 2016-05-30 {
    description 'Add some nodes about notifying VPN defalut routes for address-'
              + 'family-vpnv6.'
                ;
  }
  revision 2016-05-26 {
    description 'Add range of values for all distance-bgp-local nodes.'
                ;
  }
  revision 2016-05-16 {
    description 'Add some joined-group nodes for neighbor-vpls,neighbor-mdt,nei'
              + 'ghbor-evpn/neighbor-ipv4,neighbor-ipv4-flowspec/neighbor-ipv4,'
              + 'neighbor-vpnv4-flowspec/neighbor-ipv4 and neighbor-link-state/'
              + 'neighbor-ipv4.'
                ;
  }
  revision 2016-05-10 {
    description 'Add some distance-bgp-local nodes for address-family-ipv4-uni,'
              + 'address-family-ipv4-vrf,address-family-ipv6-uni and address-fa'
              + 'mily-ipv6-vrf.'+"\n"
              + 'Add redistribute-v6uni protocol type subscriber-aggregation an'
              + 'd user-special.'+"\n"
              + 'Add redistribute-v6-vrf protocol type subscriber-aggregation a'
              + 'nd user-special.'
                ;
  }
  revision 2016-04-08 {
    description 'Add a container for address family IPv4 Flowspec.'+"\n"
              + 'Add a container for address family VPNv4 Flowspec.'+"\n"
              + 'Add IPv4/VPNv4 Flowspec information for clear soft node and cl'
              + 'ear update-group node. '+"\n"
              + 'Add IPv4/VPNv4 Flowspec information for show peer-afi node.'
                ;
  }
  revision 2016-03-23 {
    description 'Add idle-hold-time for neighbor-extend list.'
                ;
  }
  revision 2016-03-07 {
    description 'Add wait-ctrlr-arp for neighbor-extend container, add controll'
              + 'er-notify container.'+"\n"
              + 'Add a container for address family LINK-STATE.'+"\n"
              + 'Add keychain-name node for RPKI RTR.'
                ;
  }
  revision 2016-02-22 {
    description 'Modify time unit according to the standard.'+"\n"
              + 'Add enumeration value to node /bgp:state/bgp:bgp/bgp:peer-afi/'
              + 'bgp:peer/bgp:afi.'
                ;
  }
  revision 2016-02-06 {
    description 'Add withdraw for neighbor-extend list.'
                ;
  }
  revision 2016-01-29 {
    description 'Modify address-family-ipv4-vrf-multi and address-family-ipv6-v'
              + 'rf-multi container.'
                ;
  }
  revision 2016-01-27 {
    description 'Add a leaf node:'+"\n"
              + '/bgp:configuration/bgp:bgp/bgp:bgp-instances/bgp:bgp-inst/bgp:'
              + 'bgp/bgp:select-global-nexthop.'
                ;
  }
  revision 2016-01-19 {
    description 'Add a container for address family L2VPN-EVPN.'
                ;
  }
  revision 2016-01-06 {
    description 'Add ipv6-uni,ipv6-vrf,ipv6-multi,vpnv6,ipv6-vpn-mcast,ipv6-vpn'
              + '-multi address family.Add rpki-rtr and bmp container.'
                ;
  }
  revision 2015-12-21 {
    description 'Add keychain-name for neighbor-extend list.'
                ;
  }
  revision 2015-12-08 {
    description 'Add peer-list-name node in default-originate-vrf list.'
                ;
  }
  revision 2015-11-20 {
    description 'Add route-scan-time,interval-wait,Initial,max-wait node in ipv'
              + '4 unicast, vpnv4 unicast and ipv4 vrf unicast address family.'
                ;
  }
  revision 2015-09-01 {
    description 'Modify desciption:/bgp:operation/bgp:bgp/bgp:reset/bgp:all/bgp'
              + ':peer-type.'
                ;
  }
  revision 2015-07-24 {
    description 'Add node operation/bgp/set and node operation/bgp/reset.'
                ;
  }
  revision 2015-07-15 {
    description 'Obsolete node '+"\n"
              + '/bgp:state/bgp:bgp/bgp:in-routes/bgp:ipv4-unicast/bgp:route/bg'
              + 'p:label-out'+"\n"
              + '/bgp:state/bgp:bgp/bgp:in-routes/bgp:vpnv4-unicast/bgp:route/b'
              + 'gp:label-out'+"\n"
              + '/bgp:state/bgp:bgp/bgp:in-routes/bgp:ipv6-unicast/bgp:route/bg'
              + 'p:label-out'+"\n"
              + '/bgp:state/bgp:bgp/bgp:in-routes/bgp:vpnv6-unicast/bgp:route/b'
              + 'gp:label-out'+"\n"
              + '/bgp:state/bgp:bgp/bgp:out-routes/bgp:ipv4-unicast/bgp:route/b'
              + 'gp:label-in'+"\n"
              + '/bgp:state/bgp:bgp/bgp:out-routes/bgp:vpnv4-unicast/bgp:route/'
              + 'bgp:label-in'+"\n"
              + '/bgp:state/bgp:bgp/bgp:out-routes/bgp:ipv6-unicast/bgp:route/b'
              + 'gp:label-in'+"\n"
              + '/bgp:state/bgp:bgp/bgp:out-routes/bgp:vpnv6-unicast/bgp:route/'
              + 'bgp:label-in'+"\n"
              + 'Modify desciption'+"\n"
              + '/bgp:state/bgp:bgp/bgp:in-routes/bgp:ipv4-unicast/bgp:route/bg'
              + 'p:label-in'+"\n"
              + '/bgp:state/bgp:bgp/bgp:in-routes/bgp:vpnv4-unicast/bgp:route/b'
              + 'gp:label-in'+"\n"
              + '/bgp:state/bgp:bgp/bgp:in-routes/bgp:ipv6-unicast/bgp:route/bg'
              + 'p:label-in'+"\n"
              + '/bgp:state/bgp:bgp/bgp:in-routes/bgp:vpnv4-unicast/bgp:route/b'
              + 'gp:label-in'+"\n"
              + '/bgp:state/bgp:bgp/bgp:out-routes/bgp:ipv4-unicast/bgp:route/b'
              + 'gp:label-out'+"\n"
              + '/bgp:state/bgp:bgp/bgp:out-routes/bgp:vpnv4-unicast/bgp:route/'
              + 'bgp:label-out'+"\n"
              + '/bgp:state/bgp:bgp/bgp:out-routes/bgp:ipv6-unicast/bgp:route/b'
              + 'gp:label-out'+"\n"
              + '/bgp:state/bgp:bgp/bgp:out-routes/bgp:vpnv6-unicast/bgp:route/'
              + 'bgp:label-out.'
                ;
  }
  revision 2015-06-29 {
    description 'Obsolete node best.'+"\n"
              + '/bgp:state/bgp:bgp/bgp:out-routes/bgp:ipv4-unicast/bgp:route/b'
              + 'gp:best'+"\n"
              + '/bgp:state/bgp:bgp/bgp:out-routes/bgp:vpnv4-unicast/bgp:route/'
              + 'bgp:best'+"\n"
              + '/bgp:state/bgp:bgp/bgp:out-routes/bgp:ipv6-unicast/bgp:route/b'
              + 'gp:best'+"\n"
              + '/bgp:state/bgp:bgp/bgp:out-routes/bgp:vpnv6-unicast/bgp:route/'
              + 'bgp:best'+"\n"
              + 'Modify node type of established-time and in-update-elapsed-tim'
              + 'e.'+"\n"
              + '/bgp:state/bgp:bgp/bgp:peer-session/bgp:peer/bgp:established-t'
              + 'ime'+"\n"
              + '/bgp:state/bgp:bgp/bgp:peer-session/bgp:peer/bgp:in-update-ela'
              + 'psed-time.'
                ;
  }
  revision 2015-06-02 {
    description 'Add leaf defaults-set-flag for configuring commands with defau'
              + 'lt value.'
                ;
  }
  revision 2015-05-18 {
    description 'Add routepolicy-in-name,routepolicy-out-name node in ipv4 , vp'
              + 'ls,ipv4-mdt,route-target,vpnv4, ipv4-multi, ipv4-vrf address f'
              + 'amily.'+"\n"
              + '    Add table-policy node in ipv4,ipv4-vrf address family.'
                ;
  }
  revision 2015-05-06 {
    description 'Remove default value in neighbor related node.'
                ;
  }
  revision 2015-04-30 {
    description 'Remove enumeration value disable in <activate>.'
                ;
  }
  revision 2015-04-20 {
    description 'Modify status of <nouse-peergroup-config> to current.'
                ;
  }
  revision 2015-03-09 {
    description 'Add operation and state.'
                ;
  }
  revision 2015-02-09 {
    description 'Obsolete node nouse-peergroup-config.'+"\n"
              + 'Obsolete node frr of address-family-vpnv4.'+"\n"
              + 'Obsolete node neighbor-group of address-family-mdt.'+"\n"
              + 'Add IF-filter 1231 to node update-source and track-interface.'
                ;
  }
  revision 2014-10-09 {
    description 'Add default originate vrf in vpnv4 address family.'+"\n"
              + 'Add joined group node in vpnv4, ipv4-multi, rt address family.'
              + ''+"\n"
              + 'Add frr wtr in vpnv4 address family.'+"\n"
              + 'Add peer use group config node in ipv4 , vrf ,vpnv4, ipv4-mult'
              + 'i, rt address family.'
                ;
  }
  revision 2014-09-06 {
    description 'Change sequence of peergroup conatiner and peer conatiner.'
                ;
  }
  revision 2014-08-06 {
    description 'Remove filter from BGP timer.'+"\n"
              + 'Remove filter from maxiprefix.'+"\n"
              + 'Remove filter from local-as.'+"\n"
              + 'Change leaf of choice to mandtary.'+"\n"
              + 'Change the maximum-paths type from choice to leaf.'+"\n"
              + 'Reomve next-hop-self enumeration "disalbe".'
                ;
  }
  revision 2014-07-26 {
    description 'Add container node for choice type node:'+"\n"
              + 'cluster-id,set-ttl,diverse-path-receive, password'+"\n"
              + 'Modify the default value:'+"\n"
              + 'connect-retry-interval'+"\n"
              + 'Add the Max-elements:'+"\n"
              + 'track-adjust-type-without-interface.'
                ;
  }
  revision 2014-06-26 {
    description 'Change maximum-prefix container to maximum-prefix choice.'+"\n"
              + 'Add network-ipv4-multi list.'+"\n"
              + 'Change leaf type from  enumeration to empty.'+"\n"
              + 'Add Mandatory attribute for necessary parameters.'
                ;
  }
  revision 2014-06-16 {
    description 'Add delete2reset type.'+"\n"
              + 'Add mim action.'+"\n"
              + 'Change advertise-map struct to advertise-map choice.'
                ;
  }
  revision 2013-10-10 {
    description 'Initial version.'
                ;
  }
  feature urpf {
    description URPF ;
  }
  typedef disable-or-enable-type {
    type enumeration {
      enum disable {
        value 0 ;
      }
      enum enable {
        value 1 ;
      }
    }
  }
  typedef link-state {
    type enumeration {
      enum null {
        value 0 ;
        description 'Disable neighbor egress peer engineering'
                    ;
      }
      enum link-state {
        value 1 ;
        description link-state ;
        status obsolete ;
      }
      enum sr-epe {
        value 2 ;
        description 'Enable neighbor egress peer engineering'
                    ;
      }
    }
    default null ;
    description 'Configure neighbor egress peer engineering'
                ;
  }
  container configuration {
    container bgp {
      description 'BGP configuration.'
                  ;
      container bgp-instances {
        description 'BGP configuration.'
                    ;
        list bgp-inst {
          description 'BGP configuration.'
                      ;
          max-elements 4 ;
          key local-as ;
          leaf local-as {
            description 'the Autonomy system number of BGP in local equipment.'
                        ;
            type ncd:asn-dot ;
          }
          container bgp {
            description 'BGP specific commands.'
                        ;
            leaf advertise-by-sequence {
              description 'Advertise routes by sequence strictly.'
                          ;
              type empty ;
              ncd:revise-date 2016-01-06 ;
            }
            leaf always-compare-med {
              description "enable route's med to always be compared."
                          ;
              type empty ;
            }
            leaf client-to-client-reflection {
              description 'Configure client to client route reflection.'
                          ;
              type enumeration {
                enum disable {
                  value 0 ;
                  description 'Reflection of routes denyed.'
                              ;
                }
                enum enable {
                  value 1 ;
                  description 'Reflection of routes allowed.'
                              ;
                }
              }
              default enable ;
            }
            leaf enforce-first-as {
              description 'Enforce the first AS for EBGP routes(default).'
                          ;
              type enumeration {
                enum disable {
                  value 0 ;
                  description 'Not enforce the first AS for EBGP routes.'
                              ;
                }
                enum enable {
                  value 1 ;
                  description 'Enforce the first AS for EBGP routes(default).'
                              ;
                }
              }
              default enable ;
            }
            leaf confederation-identifier {
              description 'AS number of confederation.'
                          ;
              type ncd:asn-dot ;
            }
            leaf default-local-preference {
              description 'Configure default local preference value.'
                          ;
              type uint32 {
                range 0..4294967295 {
                  description 'Local preference (higher=more preferred).'
                              ;
                }
              }
              default 100 ;
            }
            leaf fast-external-fallover {
              description 'Immediately reset session if a link to a directly co'
                        + 'nnected external peer goes down.'
                          ;
              type enumeration {
                enum disable {
                  value 0 ;
                  description 'Not immediately reset session if a link to a dir'
                            + 'ectly connected external peer goes down.'
                              ;
                }
                enum enable {
                  value 1 ;
                  description 'Immediately reset session if a link to a directl'
                            + 'y connected external peer goes down.'
                              ;
                }
              }
              default enable ;
            }
            leaf default-ipv4 {
              description 'Activate ipv4-unicast for a peer by default.'
                          ;
              type enumeration {
                enum disable {
                  value 0 ;
                  description 'Not activate ipv4-unicast for a peer by default.'
                              ;
                }
                enum enable {
                  value 1 ;
                  description 'Activate ipv4-unicast for a peer by default.'
                              ;
                }
              }
              default enable ;
            }
            leaf ext-community-type-compatible {
              description 'Send extended community compatible use old type.'
                          ;
              type empty ;
            }
            leaf route-target-filter {
              description 'Control behavior based on Route-Target attributes.'
                          ;
              type enumeration {
                enum disable {
                  value 0 ;
                  description 'Discontrol automatic VPN Route-Target filtering.'
                              ;
                }
                enum enable {
                  value 1 ;
                  description 'Control automatic VPN Route-Target filtering.'
                              ;
                }
              }
              default enable ;
            }
            leaf deterministic-med {
              description 'Set BGP deterministic-med parameters.'
                          ;
              type empty ;
            }
            leaf connect-delay {
              description 'Set the connect delay time needed to restart.'
                          ;
              type uint32 {
                range 1..3600 {
                  description 'Delay value.'
                              ;
                }
              }
              units s ;
            }
            leaf enhanced-error {
              description 'Enable BGP enhanced error handling.'
                          ;
              type empty ;
            }
            leaf bestpath-as-path-ignore {
              description 'Ignore as-path in bestpath selection and maximum-pat'
                        + 'hs.'
                          ;
              type empty ;
            }
            leaf bestpath-router-id-ignore {
              description 'Ignore router-id in bestpath selection.'
                          ;
              type empty ;
            }
            leaf attribute-download-ipv4 {
              description 'IPv4 address family.'
                          ;
              type empty ;
            }
            leaf attribute-download-ipv6 {
              description 'IPv6 address family.'
                          ;
              type empty ;
            }
            leaf graceful-restart-time {
              description 'Set the max time needed to restart and come back up.'
                          ;
              type uint32 {
                range 1..3600 {
                  description 'Delay value.'
                              ;
                }
              }
              units s ;
              default 120 ;
            }
            leaf graceful-stalepath-time {
              description "Set the max time to hold on to restarting peer's sta"
                        + "le paths."
                          ;
              type uint32 {
                range 1..604800 {
                  description 'Delay value.'
                              ;
                }
              }
              units s ;
              default 360 ;
            }
            leaf enable-graceful-restart {
              description 'Enable the graceful-restart capability of BGP.'
                          ;
              type empty ;
            }
            leaf delay-value {
              description 'set the update-delay of graceful restart.'
                          ;
              type uint32 {
                range 1..3600 {
                  description 'Delay value.'
                              ;
                }
              }
              units s ;
              default 120 ;
            }
            leaf delay-always {
              description 'The timer overflow must occur.'
                          ;
              type empty ;
            }
            container cluster-id {
              description 'Set Route-Reflector cluster-id type.'
                          ;
              choice cluster-id {
                description 'Set Route-Reflector cluster-id type.'
                            ;
                case quantity-type {
                  description 'Route-Reflector Cluster-id as 32 bit quantity.'
                              ;
                  leaf cluster-id-quantity {
                    description 'Route-Reflector Cluster-id as 32 bit quantity.'
                                ;
                    type uint32 {
                      range 1..4294967295 {
                        description 'Route-Reflector Cluster-id as 32 bit quant'
                                  + 'ity.'
                                    ;
                      }
                    }
                  }
                }
                case address-type {
                  description 'Route-Reflector Cluster-id in IP address format.'
                              ;
                  leaf cluster-id-addr {
                    description 'Route-Reflector Cluster-id in IP address forma'
                              + 't.'
                                ;
                    type ncd:ipv4-address {
                      pattern '([1-9][0-9]*\.[1-9][0-9]*\.[1-9][0-9]*\.[1-9][0-'
                            + '9]*)|([1-9][0-9]*\.0\.0\.0)|(0\.[1-9][0-9]*\.0\.'
                            + '0)|(0\.0\.[1-9][0-9]*\.0)|(0\.0\.0\.[1-9][0-9]*)'
                            + '|([1-9][0-9]*\.[1-9][0-9]*\.0\.0)|(0\.[1-9][0-9]'
                            + '*\.[1-9][0-9]*\.0)|(0\.0\.[1-9][0-9]*\.[1-9][0-9'
                            + ']*)|([1-9][0-9]*\.0\.0\.[1-9][0-9]*)|(0\.[1-9][0'
                            + '-9]*\.0\.[1-9][0-9]*)|([1-9][0-9]*\.0\.[1-9][0-9'
                            + ']*\.0)|([1-9][0-9]*\.[1-9][0-9]*\.[1-9][0-9]*\.0'
                            + ')|([1-9][0-9]*\.[1-9][0-9]*\.0\.[1-9][0-9]*)|([1'
                            + '-9][0-9]*\.0\.[1-9][0-9]*\.[1-9][0-9]*)|(0\.[1-9'
                            + '][0-9]*\.[1-9][0-9]*\.[1-9][0-9]*)'
                              ;
                    }
                  }
                }
              }
            }
            container timers {
              description 'Adjust routing timers.'
                          ;
              presence timers ;
              leaf keepalive-interval {
                description 'Keepalive interval.'
                            ;
                type uint32 {
                  range 0..65535 ;
                }
                units s ;
                mandatory true ;
              }
              leaf holdtime {
                description 'Hold time interval.'
                            ;
                type uint32 {
                  range '0 | 3..65535'
                        ;
                }
                units s ;
                mandatory true ;
              }
            }
            container neighbor-damp {
              description 'Enable neighbor flap dampening.'
                          ;
              presence damp-v4-uni ;
              choice damp {
                description 'Enable neighbor flap dampening.'
                            ;
                case route-map {
                  description 'Route-map to specify criteria for dampening.'
                              ;
                  leaf route-map-name {
                    description 'Route-map to specify criteria for dampening.'
                                ;
                    type string {
                      length 1..200 ;
                    }
                  }
                  leaf route-policy-name {
                    description 'Route-policy to specify criteria for dampening.'
                                ;
                    type string {
                      length 1..200 ;
                    }
                  }
                }
                case parameter {
                  description 'Damp parameter.'
                              ;
                  leaf half-time {
                    description 'Half-life time for the penalty.'
                                ;
                    type uint32 {
                      range 1..45 ;
                    }
                    units min ;
                    mandatory true ;
                  }
                  leaf reuse-value {
                    description 'Value to start reusing a neighbor.'
                                ;
                    type uint32 {
                      range 1..20000 ;
                    }
                    mandatory true ;
                  }
                  leaf suppress-value {
                    description 'Value to start suppressing a neighbor.'
                                ;
                    type uint32 {
                      range 1..20000 ;
                    }
                    mandatory true ;
                  }
                  leaf max-suppress {
                    description 'Maximum duration to suppress a neighbor.'
                                ;
                    type uint32 {
                      range 1..255 ;
                    }
                    units min ;
                    mandatory true ;
                  }
                }
              }
              ncd:revise-date 2020-10-10 ;
            }
            leaf select-global-nexthop {
              description 'Download global nexthop instand of link-local nextho'
                        + 'p.'
                          ;
              type empty ;
              ncd:revise-date 2016-01-27 ;
            }
            leaf select-resolved-nexthop {
              description "Download resolved nexthop for BGP route that don't h"
                        + "ave out-label."
                          ;
              type empty ;
              ncd:revise-date 2017-08-25 ;
            }
            leaf update-lowest-priority-time {
              description 'Set the time when advertising lowest priority routes.'
                          ;
              type uint32 {
                range 1..3600 {
                  description 'time value.'
                              ;
                }
              }
              units s ;
              ncd:revise-date 2017-02-23 ;
            }
            leaf bestpath-aigp-ignore {
              description 'Ignore AIGP in bestpath selection.'
                          ;
              type empty ;
              ncd:revise-date 2017-11-01 ;
            }
            leaf fast-close-tcp {
              description 'Immediately close TCP connections after bgp peers cl'
                        + 'osed.'
                          ;
              type empty ;
              ncd:revise-date 2018-04-23 ;
            }
            leaf neighbor-gr {
              description 'Enable graceful restart when neighbor is down.'
                          ;
              type enumeration {
                enum graceful-restart {
                  value 1 ;
                  description 'Enable graceful restart.'
                              ;
                }
                enum graceful-restart-route-withdraw {
                  value 2 ;
                  description 'Enable graceful restart,withdraw routes and lowe'
                            + 'r route priority.'
                              ;
                }
                enum graceful-restart-low-priority-only {
                  value 3 ;
                  description 'Enable graceful restart,lower route priority onl'
                            + 'y.'
                              ;
                }
              }
              ncd:revise-date 2019-01-01 ;
            }
            leaf bestpath-ecmp-as-path-value-ignore {
              description 'Ignore as-path value in maximum-paths.'
                          ;
              type empty ;
              ncd:revise-date 2018-12-24 ;
            }
            leaf bestpath-virtual-spoke {
              description 'Routes from virtual-spoke peer are preferred in best'
                        + 'path selection.'
                          ;
              type empty ;
              ncd:revise-date 2019-01-21 ;
            }
            leaf global-maximum-paths-eibgp {
              description 'Set EIBGP-multipath globally. Mutex with maximum-pat'
                        + 'hs-ibgp and maximum-paths-ebgp.'
                          ;
              type uint32 {
                range 1..32 ;
              }
              default 1 ;
              ncd:revise-date 2019-08-08 ;
            }
            leaf global-maximum-paths-ibgp {
              description 'Set IBGP-multipath globally.'
                          ;
              type uint32 {
                range 1..32 ;
              }
              default 1 ;
              ncd:revise-date 2019-08-08 ;
            }
            leaf global-maximum-paths-ebgp {
              description 'Set EBGP-multipath globally.'
                          ;
              type uint32 {
                range 1..32 ;
              }
              default 1 ;
              ncd:revise-date 2019-08-08 ;
            }
            leaf graceful-stalepath-time-permanent {
              description 'Hold on stale paths permanently.'
                          ;
              type empty ;
              ncd:revise-date 2020-02-08 ;
            }
            leaf as-path-loopcheck-ibgp-in {
              description 'Check as-path receiving routes from IBGP neighbor.'
                          ;
              type enumeration {
                enum enable {
                  value 1 ;
                  description 'Function is enabled.'
                              ;
                }
                enum disable {
                  value 0 ;
                  description 'Function is disabled.'
                              ;
                }
              }
              ncd:revise-date 2020-12-02 ;
            }
            leaf srv6-epe-locator {
              description 'SRv6 locator name for EPE'
                          ;
              type string {
                length 1..31 {
                  description 'SRv6 epe locator name.'
                              ;
                }
              }
              ncd:revise-date 2020-08-11 ;
            }
            leaf sr-epe-mode {
              description 'Set SR EPE MPLS sid assignment mode.'
                          ;
              type enumeration {
                enum hybrid {
                  value 1 ;
                  description Hybrid ;
                }
                enum static {
                  value 0 ;
                  description Static ;
                }
              }
              default hybrid ;
              ncd:revise-date 2020-09-27 ;
            }
            leaf bestpath-bgp-lu-nexthop-compare {
              status obsolete {
                ncd:revise-date 2021-03-25 ;
              }
              description 'Compare nexthop that rely on BGP-LU path in bestpath'
                        + ' selection'
                          ;
              type enumeration {
                enum disable {
                  value 0 ;
                  description 'Disable this function'
                              ;
                }
                enum enable {
                  value 1 ;
                  description 'Enable this function'
                              ;
                }
              }
              ncd:revise-date 2018-04-08 ;
            }
          }
          container global-as-weight {
            description 'Set the weight of as-path (lower=more preferred).'
                        ;
            list as-weight {
              description 'Set the weight of as-path (lower=more preferred).'
                          ;
              key weight-as ;
              leaf weight-as {
                description 'Autonomous system number (normal or 4 Octets).'
                            ;
                type ncd:asn-dot ;
              }
              leaf weight-value {
                description 'Weight of AS.'
                            ;
                type uint32 {
                  range 0..255 ;
                }
                mandatory true ;
              }
            }
          }
          container global-confederation-peers {
            description 'AS confederation parameters.'
                        ;
            list confederation-peers {
              description 'AS confederation parameters.'
                          ;
              max-elements 255 ;
              key confed-peer-as ;
              leaf confed-peer-as {
                description 'Peer ASs in BGP confederation.'
                            ;
                type ncd:asn-dot ;
              }
            }
          }
          container address-family-ipv4-uni {
            description 'Configuration in address family IPv4 mode.'
                        ;
            leaf advertise-active-only {
              description 'Advertise the active routes only.'
                          ;
              type empty ;
            }
            leaf default-information-originate {
              description 'Notify default route.'
                          ;
              type empty ;
            }
            leaf default-metric {
              description 'Set the metric of BGP routes without MED.'
                          ;
              type uint32 {
                range 0..4294967295 ;
              }
              default 0 ;
            }
            leaf synchronization {
              description 'Perform IGP synchronization.'
                          ;
              type empty ;
            }
            leaf table-map {
              description 'Map external entry attributes into routing table.'
                          ;
              type string {
                length 1..200 ;
              }
            }
            leaf nexthop-trigger-delay {
              description 'Set the delay time to trigger nexthop tracking.'
                          ;
              type uint32 {
                range 1..1200 ;
              }
              units s ;
            }
            leaf router-id-addr {
              description 'Manually configured router identifier.'
                          ;
              type ncd:ipv4-address {
                pattern '([1-9][0-9]*\.[1-9][0-9]*\.[1-9][0-9]*\.[1-9][0-9]*)|('
                      + '[1-9][0-9]*\.0\.0\.0)|(0\.[1-9][0-9]*\.0\.0)|(0\.0\.[1'
                      + '-9][0-9]*\.0)|(0\.0\.0\.[1-9][0-9]*)|([1-9][0-9]*\.[1-'
                      + '9][0-9]*\.0\.0)|(0\.[1-9][0-9]*\.[1-9][0-9]*\.0)|(0\.0'
                      + '\.[1-9][0-9]*\.[1-9][0-9]*)|([1-9][0-9]*\.0\.0\.[1-9]['
                      + '0-9]*)|(0\.[1-9][0-9]*\.0\.[1-9][0-9]*)|([1-9][0-9]*\.'
                      + '0\.[1-9][0-9]*\.0)|([1-9][0-9]*\.[1-9][0-9]*\.[1-9][0-'
                      + '9]*\.0)|([1-9][0-9]*\.[1-9][0-9]*\.0\.[1-9][0-9]*)|([1'
                      + '-9][0-9]*\.0\.[1-9][0-9]*\.[1-9][0-9]*)|(0\.[1-9][0-9]'
                      + '*\.[1-9][0-9]*\.[1-9][0-9]*)'
                        ;
              }
            }
            leaf distance-bgp-internal {
              description 'Distance for routes internal to the AS.'
                          ;
              type uint32 {
                range 1..255 ;
              }
              default 200 ;
            }
            leaf distance-bgp-external {
              description 'Distance for routes external to the AS.'
                          ;
              type uint32 {
                range 1..255 ;
              }
              default 20 ;
            }
            leaf distance-bgp-local {
              description 'Distance for BGP local routes.'
                          ;
              type uint32 {
                range 1..255 ;
              }
              default 254 ;
              ncd:revise-date 2016-05-10 ;
            }
            leaf distance-route-map {
              description 'Define distance by route-map.This node has higher pr'
                        + 'iority than distance-bgp-internal,distance-bgp-exter'
                        + 'nal and distance-bgp-local.'
                          ;
              type string {
                length 1..200 ;
              }
              ncd:revise-date 2020-09-08 ;
            }
            leaf distance-route-policy {
              description 'Define distance by route-policy.This node has higher'
                        + ' priority than distance-bgp-internal,distance-bgp-ex'
                        + 'ternal and distance-bgp-local.'
                          ;
              type string {
                length 1..200 ;
              }
              ncd:revise-date 2020-10-10 ;
            }
            leaf bestpath-external {
              description 'Routes from external peer or RR client are preferred'
                        + ' in bestpath selection.'
                          ;
              type empty ;
            }
            leaf bestpath-igp-metric-ignore {
              description 'Ignore IGP metric in bestpath selection.'
                          ;
              type empty ;
            }
            leaf bestpath-bgp-lu-nexthop-compare {
              description 'Compare nexthop that rely on BGP-LU path in bestpath'
                        + ' selection'
                          ;
              type enumeration {
                enum disable {
                  value 0 ;
                  description 'Disable this function'
                              ;
                }
                enum enable {
                  value 1 ;
                  description 'Enable this function'
                              ;
                }
              }
              ncd:revise-date 2021-03-25 ;
            }
            leaf frr-capability {
              description 'Enable FRR capability.'
                          ;
              type empty ;
            }
            leaf frr-wtr {
              description 'Set the WTR time.'
                          ;
              type int32 {
                range 1..12 ;
              }
              units min ;
            }
            leaf frr-enhanced {
              description 'If there is no BGP route as a backup route, then cho'
                        + 'ose the default route for FRR.'
                          ;
              type empty ;
              ncd:revise-date 2016-01-06 ;
            }
            leaf maximum-paths-ibgp {
              description 'Set IBGP-multipath.'
                          ;
              type uint32 {
                range 1..32 ;
              }
              default 1 ;
            }
            leaf maximum-paths-ebgp {
              description 'Set EBGP-multipath.'
                          ;
              type uint32 {
                range 1..32 ;
              }
              default 1 ;
            }
            leaf maximum-paths-eibgp {
              description 'Set EIBGP-multipath. Mutex with maximum-paths-ibgp a'
                        + 'nd maximum-paths-ebgp.'
                          ;
              type uint32 {
                range 1..32 ;
              }
              default 1 ;
            }
            leaf rpki-validation {
              description 'Set the BGP origin-AS validation parameters.'
                          ;
              type disable-or-enable-type ;
              default enable ;
              ncd:revise-date 2016-01-06 ;
            }
            leaf bestpath-igp-metric-compare {
              description 'Compare IGP metric in maximum-paths.'
                          ;
              type empty ;
              ncd:revise-date 2017-07-05 ;
            }
            leaf bgp-local-as {
              description 'the Autonomy system number of BGP in local equipment.'
                          ;
              type ncd:asn-dot ;
              ncd:revise-date 2020-07-28 ;
            }
            leaf send-label {
              description 'Send null label.'
                          ;
              type enumeration {
                enum explicit-null {
                  value 1 ;
                  description 'Explicit-null label.'
                              ;
                }
                enum implicit-null {
                  value 2 ;
                  description 'Implicit-null label.'
                              ;
                }
              }
              ncd:revise-date 2018-05-14 ;
            }
            leaf nexthop-recursive-default-route {
              description 'Nexthop recursive lookup default-route.'
                          ;
              type enumeration {
                enum enable {
                  value 1 ;
                }
                enum disable {
                  value 0 ;
                }
              }
              default enable ;
              ncd:revise-date 2020-07-28 ;
            }
            leaf nexthop-recursive-null1 {
              description 'Nexthop recursive lookup null1.'
                          ;
              type enumeration {
                enum enable {
                  value 1 ;
                }
                enum disable {
                  value 0 ;
                }
              }
              default enable ;
              ncd:revise-date 2020-12-09 ;
            }
            container rib-only {
              description 'BGP routes are not delivered to the IP routing table.'
                          ;
              presence 'BGP routes are not delivered to the IP routing table'
                       ;
              leaf rib-only-set {
                description 'Enable rib-only.'
                            ;
                type empty ;
                mandatory true ;
              }
              leaf rib-only-routemap {
                description 'Routing policy.'
                            ;
                type string {
                  length 1..200 ;
                }
              }
              leaf rib-only-routepolicy {
                description 'Routing policy.'
                            ;
                type string {
                  length 1..200 ;
                }
                ncd:revise-date 2020-10-10 ;
              }
            }
            container damp-v4-uni {
              description 'Enable route-flap dampening.'
                          ;
              presence damp-v4-uni ;
              choice damp {
                description 'Enable route-flap dampening.'
                            ;
                case route-map {
                  description 'Route-map to specify criteria for dampening.'
                              ;
                  leaf route-map-name {
                    description 'Route-map to specify criteria for dampening.'
                                ;
                    type string {
                      length 1..200 ;
                    }
                  }
                  leaf route-policy-name {
                    description 'Route-policy to specify criteria for dampening.'
                                ;
                    type string {
                      length 1..200 ;
                    }
                    ncd:revise-date 2020-10-10 ;
                  }
                }
                case parameter {
                  description 'Damp parameter.'
                              ;
                  leaf half-time {
                    description 'Half-life time for the penalty.'
                                ;
                    type uint32 {
                      range 1..45 ;
                    }
                    units min ;
                    mandatory true ;
                  }
                  leaf reuse-value {
                    description 'Value to start reusing a route.'
                                ;
                    type uint32 {
                      range 1..20000 ;
                    }
                    mandatory true ;
                  }
                  leaf suppress-value {
                    description 'Value to start suppressing a route.'
                                ;
                    type uint32 {
                      range 1..20000 ;
                    }
                    mandatory true ;
                  }
                  leaf max-suppress {
                    description 'Maximum duration to suppress a route.'
                                ;
                    type uint32 {
                      range 1..255 ;
                    }
                    units min ;
                    mandatory true ;
                  }
                }
              }
            }
            leaf dampening-ibgp {
              description 'IBGP route-flap dampening.'
                          ;
              type enumeration {
                enum disable {
                  value 0 ;
                }
                enum enable {
                  value 1 ;
                }
              }
              default enable ;
              ncd:revise-date 2020-08-18 ;
            }
            container aggregate-v4-uni {
              description 'Configure BGP aggregate entries.'
                          ;
              presence aggregate-v4-uni ;
              container aggreate-nosub {
                description 'Configure BGP aggregate entries without subnet.'
                            ;
                list aggregate-without-sub {
                  description 'Configure BGP aggregate entries without subnet.'
                              ;
                  key 'aggregate-address aggregate-mask'
                      ;
                  leaf aggregate-address {
                    description 'Aggregate address.'
                                ;
                    type ncd:ipv4-address ;
                  }
                  leaf aggregate-mask {
                    description 'Aggregate mask.'
                                ;
                    type ncd:ipv4-mask ;
                  }
                  leaf as-set {
                    description 'Generate AS set path information.'
                                ;
                    type empty ;
                  }
                  leaf count {
                    description 'Count of aggregate subnet.'
                                ;
                    type uint32 {
                      range 0..255 ;
                    }
                    default 1 ;
                  }
                  leaf strict {
                    description 'Strict condition.'
                                ;
                    type empty ;
                  }
                  leaf summary-only {
                    description 'Filter more specific routes from updates.'
                                ;
                    type empty ;
                  }
                  leaf attribute-map {
                    status obsolete {
                      ncd:revise-date 2018-07-21 ;
                    }
                    description 'Attribute map name.'
                                ;
                    type string {
                      length 1..200 ;
                    }
                    ncd:revise-date 2016-01-06 ;
                  }
                  leaf suppress-map-name {
                    status obsolete {
                      ncd:revise-date 2018-07-21 ;
                    }
                    description 'Suppress map name.'
                                ;
                    type string {
                      length 1..200 ;
                    }
                    ncd:revise-date 2016-01-06 ;
                  }
                  choice agg-policy {
                    description 'Apply policy to aggregate route.'
                                ;
                    case agg-policy-choice-clear {
                      description 'Remove value of any entities which belong to'
                                + ' any case within this choice.'
                                  ;
                      container agg-policy-all-clear {
                        description 'Remove this entitiy means to remove value '
                                  + 'of any entities which belong to any case w'
                                  + 'ithin this choice.'
                                    ;
                        presence clear-agg-policy ;
                      }
                      ncd:revise-date 2020-11-11 ;
                    }
                    case route-map {
                      description 'Apply route map to aggregate route.'
                                  ;
                      leaf attr-map {
                        description 'Attribute map name.'
                                    ;
                        type string {
                          length 1..200 ;
                        }
                      }
                      leaf supp-map {
                        description 'Suppress map name.'
                                    ;
                        type string {
                          length 1..200 ;
                        }
                      }
                      leaf orig-map {
                        description 'Origin map name.'
                                    ;
                        type string {
                          length 1..200 ;
                        }
                        ncd:revise-date 2019-08-19 ;
                      }
                    }
                    case route-policy {
                      description 'Apply route-policy to aggregate route.'
                                  ;
                      leaf policy {
                        description 'Route-policy name.'
                                    ;
                        type string {
                          length 1..200 ;
                        }
                      }
                    }
                    ncd:revise-date 2018-07-21 ;
                  }
                }
              }
              container aggreate-sub {
                description 'Configure BGP aggregate entries with subnet.'
                            ;
                list aggregate-with-sub {
                  description 'Configure BGP aggregate entries with subnet.'
                              ;
                  key 'aggregate-address aggregate-mask sub-ip-address sub-ip-m'
                    + 'ask'
                      ;
                  leaf aggregate-address {
                    description 'Aggregate address.'
                                ;
                    type ncd:ipv4-address ;
                  }
                  leaf aggregate-mask {
                    description 'Aggregate mask.'
                                ;
                    type ncd:ipv4-mask ;
                  }
                  leaf sub-ip-address {
                    description 'Aggregate subnet.'
                                ;
                    type ncd:ipv4-address ;
                  }
                  leaf sub-ip-mask {
                    description 'Aggregate subnet Network mask.'
                                ;
                    type ncd:ipv4-mask ;
                  }
                }
              }
            }
            container redistribute-v4-uni {
              description 'Redistribute information from another routing protoc'
                        + 'ol.'
                          ;
              presence redistribute-v4-uni ;
              container redistribute-uni {
                description 'Redistribute information from another routing prot'
                          + 'ocol.'
                            ;
                list redistribute {
                  description 'Redistribute information from another routing pr'
                            + 'otocol.'
                              ;
                  key protocol ;
                  leaf protocol {
                    description 'Routing protocol type.'
                                ;
                    type enumeration {
                      enum connected {
                        value 1 ;
                        description 'Connected routes.'
                                    ;
                      }
                      enum static {
                        value 2 ;
                        description 'Static routes.'
                                    ;
                      }
                      enum rip {
                        value 3 ;
                        description 'Routing information protocol(RIP).'
                                    ;
                      }
                      enum ps-busi-addr {
                        value 10 ;
                        description 'Ps-busi-addr routes.'
                                    ;
                      }
                      enum ps-user-addr {
                        value 11 ;
                        description 'Ps-user-addr routes.'
                                    ;
                      }
                      enum nat {
                        value 12 ;
                        description 'NAT routes.'
                                    ;
                      }
                      enum natpt {
                        value 13 ;
                        description 'Port-address Translation routes.'
                                    ;
                      }
                      enum subscriber-host {
                        value 14 ;
                        description "Bras subscriber's host routes."
                                    ;
                      }
                      enum subscriber-aggregation {
                        value 15 ;
                        description "Bras subscriber's aggregation routes."
                                    ;
                      }
                      enum ldp {
                        value 16 ;
                        description 'Label distribution protocol(LDP).'
                                    ;
                      }
                      enum user-special {
                        value 17 ;
                        description 'User-special routes.'
                                    ;
                      }
                      enum sl-nat64-ipv4 {
                        value 18 ;
                        description 'Stateless NAT64 prefix.'
                                    ;
                      }
                      enum bras-pool {
                        value 24 ;
                        description 'Broadband Remote Access Server pool routes.'
                                    ;
                      }
                      enum ipsec {
                        value 25 ;
                        description 'IPsec routes'
                                    ;
                      }
                      enum hagp {
                        value 26 ;
                        description 'Hybrid access gateway protocol routes.'
                                    ;
                      }
                      enum dyn-leasedline {
                        value 29 ;
                        description 'Dynamic-leased-line routes assigned by AAA.'
                                    ;
                      }
                      enum address {
                        value 9 ;
                        description 'Address routes.'
                                    ;
                      }
                    }
                  }
                  leaf route-map {
                    description 'Apply route-map to redistribute.'
                                ;
                    type string {
                      length 1..200 ;
                    }
                  }
                  leaf route-policy {
                    description 'Apply route-policy to redistribute.'
                                ;
                    type string {
                      length 1..200 ;
                    }
                    ncd:revise-date 2020-10-10 ;
                  }
                  container set-metric {
                    description 'Set route metric.'
                                ;
                    leaf metric {
                      description 'Set route metric.'
                                  ;
                      type uint32 {
                        range 0..4294967295 ;
                      }
                    }
                  }
                }
              }
              container redistribute-isis-v4uni {
                description 'Redistribute information from ISIS protocol.'
                            ;
                list redistribute-isis {
                  description 'Redistribute information from ISIS protocol.'
                              ;
                  key 'protocol process-id'
                      ;
                  leaf protocol {
                    description 'Routing protocol type(ISIS-1,ISIS-2 or ISIS-1-'
                              + '2).'
                                ;
                    type enumeration {
                      enum isis-1 {
                        value 4 ;
                        description 'IS-IS level-1 routes only.'
                                    ;
                      }
                      enum isis-2 {
                        value 5 ;
                        description 'IS-IS level-2 routes only.'
                                    ;
                      }
                    }
                  }
                  leaf process-id {
                    description 'ISIS process ID.'
                                ;
                    type uint32 {
                      range 0..65535 ;
                    }
                  }
                  leaf route-map {
                    description 'Apply route-map to redistribute.'
                                ;
                    type string {
                      length 1..200 ;
                    }
                  }
                  leaf route-policy {
                    description 'Apply route-policy to redistribute.'
                                ;
                    type string {
                      length 1..200 ;
                    }
                    ncd:revise-date 2020-10-10 ;
                  }
                  container set-metric {
                    description 'Set route metric.'
                                ;
                    leaf metric {
                      description 'Set route metric.'
                                  ;
                      type uint32 {
                        range 0..4294967295 ;
                      }
                    }
                  }
                }
              }
              container redistribute-ospf-v4uni {
                description 'Redistribute information from OSPF protocol.'
                            ;
                list redistribute-ospf {
                  description 'Redistribute information from OSPF protocol.'
                              ;
                  key 'protocol process-id'
                      ;
                  leaf protocol {
                    description 'Routing protocol type(OSPF-EXT or OSPF-INT).'
                                ;
                    type enumeration {
                      enum ospf-ext {
                        value 7 ;
                        description 'Open shortest path first(OSPF) external ro'
                                  + 'utes.'
                                    ;
                      }
                      enum ospf-int {
                        value 8 ;
                        description 'Open shortest path first(OSPF) internal ro'
                                  + 'utes.'
                                    ;
                      }
                    }
                  }
                  leaf process-id {
                    description 'OSPF process ID.'
                                ;
                    type uint32 {
                      range 1..65535 ;
                    }
                  }
                  leaf route-map {
                    description 'Apply route-map to redistribute.'
                                ;
                    type string {
                      length 1..200 ;
                    }
                  }
                  leaf route-policy {
                    description 'Apply route-policy to redistribute.'
                                ;
                    type string {
                      length 1..200 ;
                    }
                    ncd:revise-date 2020-10-10 ;
                  }
                  container set-metric {
                    description 'Set route metric.'
                                ;
                    leaf metric {
                      description 'Set route metric.'
                                  ;
                      type uint32 {
                        range 0..4294967295 ;
                      }
                    }
                  }
                }
              }
            }
            container network-v4-uni {
              description 'Specify a network to announce via BGP.'
                          ;
              presence network-v4-uni ;
              list network {
                description 'Specify a network to announce via BGP.'
                            ;
                key 'ip-address ip-mask'
                    ;
                leaf ip-address {
                  description 'Network prefix.'
                              ;
                  type ncd:ipv4-address ;
                }
                leaf ip-mask {
                  description 'Network mask.'
                              ;
                  type ncd:ipv4-mask ;
                }
                leaf route-map {
                  description 'Route-map to modify the attributes.'
                              ;
                  type string {
                    length 1..200 ;
                  }
                }
                leaf route-policy {
                  description 'Route-policy to modify the attributes.'
                              ;
                  type string {
                    length 1..200 ;
                  }
                  ncd:revise-date 2020-10-10 ;
                }
              }
            }
            container track-v4-uni {
              description 'Event tracking.'
                          ;
              presence track-v4-uni ;
              container track-adjust-type-with-interface {
                description 'Configure adjust-priority of track object with int'
                          + 'erface.'
                            ;
                list track-adjust-with-interface {
                  description 'Configure adjust-priority of track object with i'
                            + 'nterface.'
                              ;
                  key 'track-name track-interface'
                      ;
                  leaf track-name {
                    description 'Name of track object (1-31 characters).'
                                ;
                    type string {
                      length 1..31 ;
                    }
                  }
                  leaf track-interface {
                    description 'Source of track object.'
                                ;
                    type ncd:ifname {
                      length 1..31 ;
                    }
                  }
                  leaf adjust-value {
                    description 'Value of adjust-priority.'
                                ;
                    type uint32 {
                      range 1..100 ;
                    }
                    mandatory true ;
                  }
                }
              }
              container track-adjust-type-without-interface {
                description 'Configure adjust-priority of track object without '
                          + 'interface.'
                            ;
                list track-adjust-without-interface {
                  description 'Configure adjust-priority of track object withou'
                            + 't interface.'
                              ;
                  max-elements 1 ;
                  key track-name ;
                  leaf track-name {
                    description 'Name of track object (1-31 characters).'
                                ;
                    type string {
                      length 1..31 ;
                    }
                  }
                  leaf adjust-value {
                    description 'Value of adjust-priority.'
                                ;
                    type uint32 {
                      range 1..100 ;
                    }
                    mandatory true ;
                  }
                }
              }
              container track-trigger-type {
                description 'Configure trigger of track object.'
                            ;
                list track-trigger {
                  description 'Configure trigger of track object.'
                              ;
                  key track-name ;
                  leaf track-name {
                    description 'Name of track object (1-31characters).'
                                ;
                    type string {
                      length 1..31 ;
                    }
                  }
                }
              }
            }
            container neighbor-ipv4-uni {
              description 'Specify a neighbor.'
                          ;
              presence neighbor-ipv4-uni ;
              container neighbor-uni-group {
                description 'Specify a neighbor peergroup.'
                            ;
                list neighbor-uni-peergroup {
                  description 'Specify a neighbor peergroup.'
                              ;
                  key neighbor-group ;
                  leaf neighbor-group {
                    description 'Peer group name (1-31 characters).'
                                ;
                    type string {
                      length 1..31 ;
                    }
                  }
                  leaf remote-as {
                    description 'Specify a BGP neighbor AS number.'
                                ;
                    type ncd:asn-dot ;
                  }
                  leaf activate {
                    description 'Enable the address family for this neighbor.'
                                ;
                    type enumeration {
                      enum disable {
                        value 0 ;
                      }
                      enum enable {
                        value 1 ;
                      }
                    }
                  }
                  leaf monitor {
                    description 'Config BMP monitor for the address family of t'
                              + 'his neighbor.'
                                ;
                    type enumeration {
                      enum disable {
                        value 2 ;
                      }
                      enum enable {
                        value 1 ;
                      }
                      enum inherit-global-config {
                        value 0 ;
                      }
                    }
                    ncd:revise-date 2019-07-29 ;
                  }
                  leaf advertisement-interval {
                    description 'Minimum interval between sending BGP routing w'
                              + 'hich is not locally originated updates.'
                                ;
                    type uint32 {
                      range 1..65535 ;
                    }
                    units s ;
                  }
                  leaf advertise-maximum-prefix {
                    description 'Maximum number of prefix send to this peer.'
                                ;
                    type uint32 {
                      range 1..4294967295 ;
                    }
                    ncd:revise-date 2016-01-06 ;
                  }
                  leaf allowas-in {
                    description 'Accept as-path with my AS present in it.'
                                ;
                    type uint32 {
                      range 1..10 {
                        description 'The number of my AS that presented in as-p'
                                  + 'ath.'
                                    ;
                      }
                    }
                  }
                  leaf default-originate {
                    description 'Originate default route to this neighbor.'
                                ;
                    type empty ;
                  }
                  leaf default-originate-routemap {
                    description 'Map external entry attributes into routing tab'
                              + 'le.'
                                ;
                    type string {
                      length 1..200 ;
                    }
                    ncd:revise-date 2020-07-28 ;
                  }
                  leaf default-originate-routepolicy {
                    description 'Set external entry attributes into routing tab'
                              + 'le.'
                                ;
                    type string {
                      length 1..200 ;
                    }
                    ncd:revise-date 2020-10-10 ;
                  }
                  leaf description {
                    description 'Neighbor specific description.'
                                ;
                    type ncd:string-with-blank {
                      length 1..80 ;
                    }
                  }
                  leaf next-hop-self {
                    description 'Disable the next hop calculation for this neig'
                              + 'hbor.'
                                ;
                    type enumeration {
                      enum enable {
                        value 1 ;
                        description 'Apply next-hop-self for EBGP route.'
                                    ;
                      }
                      enum all {
                        value 2 ;
                        description 'Apply next-hop-self for both EBGP and IBGP'
                                  + ' route.'
                                    ;
                      }
                    }
                  }
                  choice nh-unchanged {
                    case next-hop-unchanged {
                      description 'NEXT_HOP of the IBGP path propagated unchang'
                                + 'ed to this neighbor.'
                                  ;
                      leaf next-hop-unchanged {
                        description 'Propagate next hop unchanged for IBGP path'
                                  + 's to this neighbor.'
                                    ;
                        type empty ;
                      }
                      ncd:revise-date 2019-06-04 ;
                    }
                    case next-hop-unchanged-all {
                      description 'NEXT_HOP of either EBGP or IBGP path propaga'
                                + 'ted unchanged to this neighbor.'
                                  ;
                      leaf next-hop-unchanged-all {
                        description 'NEXT_HOP of either EBGP or IBGP path propa'
                                  + 'gated unchanged to this neighbor.'
                                    ;
                        type empty ;
                      }
                      ncd:revise-date 2020-04-07 ;
                    }
                  }
                  leaf originate-interval {
                    description 'Minimum interval between sending BGP routing w'
                              + 'hich is locally originated updates.'
                                ;
                    type uint32 {
                      range 1..65535 ;
                    }
                    units s ;
                  }
                  leaf passive {
                    description "Don't send open messages to this neighbor acti"
                              + "vely."
                                ;
                    type empty ;
                  }
                  leaf remove-private-as {
                    description 'EBGP use to remove private AS number.'
                                ;
                    type enumeration {
                      enum disable {
                        value 0 ;
                      }
                      enum enable {
                        value 1 ;
                      }
                    }
                  }
                  leaf route-reflector-client {
                    description 'Set this neighbor as a client peer.'
                                ;
                    type empty ;
                  }
                  leaf send-community {
                    description 'Send community to this neighbor.'
                                ;
                    type empty ;
                  }
                  leaf send-large-community {
                    description 'Send Large-community to this neighbor.'
                                ;
                    type empty ;
                    ncd:revise-date 2020-04-16 ;
                  }
                  leaf send-med {
                    description 'Send metric attribute to this neighbor.'
                                ;
                    type empty ;
                  }
                  leaf inherit-igp-metric {
                    description 'Med attribute inherited from IGP metric before'
                              + ' sending updates'
                                ;
                    type empty ;
                    ncd:revise-date 2017-07-25 ;
                  }
                  leaf shut-down {
                    status obsolete {
                      ncd:revise-date 2016-06-12 ;
                    }
                    description 'Administratively shut down this neighbor.'
                                ;
                    type empty ;
                  }
                  leaf update-source {
                    status obsolete {
                      ncd:revise-date 2018-11-27 ;
                    }
                    description 'Source of routing updates.'
                                ;
                    type ncd:ifname {
                      length 1..31 ;
                    }
                  }
                  leaf soft-reconfiguration {
                    status obsolete {
                      ncd:revise-date 2018-01-31 ;
                    }
                    description 'Neighbor soft reconfiguration.'
                                ;
                    type empty ;
                  }
                  leaf soft-reconfig {
                    description 'Neighbor soft reconfiguration.'
                                ;
                    type enumeration {
                      enum soft-reconfiguration {
                        value 1 ;
                        description Soft-reconfiguration. ;
                      }
                      enum enforce-soft-reconfiguration {
                        value 2 ;
                        description 'Enforce soft-reconfiguration instead of se'
                                  + 'nding route-refresh.'
                                    ;
                      }
                    }
                    ncd:revise-date 2018-01-31 ;
                  }
                  leaf maxas-in {
                    description 'Accept as-path not exceeded maxas-in.'
                                ;
                    type uint32 {
                      range 1..250 ;
                    }
                  }
                  leaf split-updgrp {
                    description 'Split neighbor from update group.'
                                ;
                    type empty ;
                  }
                  leaf weight {
                    description 'Set weight for routes from this neighbor.'
                                ;
                    type uint32 {
                      range 1..65535 ;
                    }
                  }
                  leaf connect-retry-interval {
                    description 'Set data of connect-retry timer for this neigh'
                              + 'bor.'
                                ;
                    type uint32 {
                      range 1..65535 ;
                    }
                    units s ;
                  }
                  leaf orf-prefix-filter {
                    description 'Advertise prefixlist ORF capability to this ne'
                              + 'ighbor.'
                                ;
                    type enumeration {
                      enum receive {
                        value 1 ;
                        description 'Capability to receive the ORF from this ne'
                                  + 'ighbor.'
                                    ;
                      }
                      enum send {
                        value 2 ;
                        description 'Capability to send the ORF to this neighbo'
                                  + 'r.'
                                    ;
                      }
                      enum both {
                        value 3 ;
                        description 'Capability to send and receive the ORF.'
                                    ;
                      }
                    }
                  }
                  leaf orf-prefix-filter-cisco {
                    description 'Compatible with CISCO.'
                                ;
                    type empty ;
                  }
                  leaf open-delay {
                    description 'Delay to send open message.'
                                ;
                    type uint32 {
                      range 1..240 ;
                    }
                    units s ;
                  }
                  leaf as-path-loopcheck {
                    description 'Check as-path sending BGP routing to EBGP neig'
                              + 'hbor.'
                                ;
                    type empty ;
                  }
                  leaf aigp {
                    description 'Enable AIGP for this neighbor.'
                                ;
                    type empty ;
                    ncd:revise-date 2017-11-01 ;
                  }
                  leaf send-label {
                    description 'Send NLRI with MPLS label to this neighbor.'
                                ;
                    type empty ;
                    ncd:revise-date 2018-11-06 ;
                  }
                  container advertise-map-uni {
                    description 'Specify route-map for conditional advertisemen'
                              + 't.'
                                ;
                    presence 'Specify route-map for conditional advertisement'
                             ;
                    leaf advertise-map-name {
                      description 'Advertise route-map name.'
                                  ;
                      type string {
                        length 1..200 ;
                      }
                      mandatory true ;
                    }
                    choice advertise-map {
                      description 'Specify route-map for conditional advertisem'
                                + 'ent.'
                                  ;
                      mandatory true ;
                      case exist-map {
                        description 'Advertise prefix only if prefix exists.'
                                    ;
                        leaf exist-map-name {
                          description 'Advertise prefix only if prefix exists.'
                                      ;
                          type string {
                            length 1..200 ;
                          }
                          mandatory true ;
                        }
                      }
                      case nonexist-map {
                        description 'Advertise prefix only if prefix does not e'
                                  + 'xist.'
                                    ;
                        leaf nonexist-map-name {
                          description 'Advertise prefix only if prefix does not'
                                    + ' exist.'
                                      ;
                          type string {
                            length 1..200 ;
                          }
                          mandatory true ;
                        }
                      }
                    }
                  }
                  container fall-over {
                    description 'Set BFD supporting for fallover.'
                                ;
                    presence 'Enable BFD support for fallover'
                             ;
                    leaf bfd {
                      description 'Enable BFD support for fallover.'
                                  ;
                      type empty ;
                      mandatory true ;
                    }
                    container bfd-parameters {
                      description 'The parameters of BFD.'
                                  ;
                      presence bfd-parameters ;
                      choice bfd-parameters {
                        description 'Config BFD parameters'
                                    ;
                        case template-name {
                          description 'Template name'
                                      ;
                          leaf template {
                            description 'BFD template name'
                                        ;
                            type string {
                              length 1..31 ;
                            }
                          }
                          ncd:revise-date 2020-03-31 ;
                        }
                        case parameters {
                          description Parameters ;
                          leaf bfd-interval {
                            description 'Minimum send interval.'
                                        ;
                            type uint32 {
                              range 10..990 ;
                            }
                            units ms ;
                            mandatory true ;
                          }
                          leaf min-rx {
                            description 'Minimum receive interval.'
                                        ;
                            type uint32 {
                              range 10..990 ;
                            }
                            units ms ;
                            mandatory true ;
                          }
                          leaf multiplier {
                            description Multiplier. ;
                            type uint8 {
                              range 3..50 ;
                            }
                            mandatory true ;
                          }
                        }
                      }
                    }
                    leaf bfd-hop {
                      description 'bfd optional hop'
                                  ;
                      type enumeration {
                        enum single-hop {
                          value 1 ;
                          description 'Set single-hop bfd'
                                      ;
                        }
                        enum multi-hop {
                          value 2 ;
                          description 'Set multi-hop bfd'
                                      ;
                        }
                      }
                      ncd:revise-date 2019-04-23 ;
                    }
                  }
                  container set-ttl {
                    description 'ebgp-multihop-ttl and ttl-security-hops are mu'
                              + 'tex.'
                                ;
                    choice set-ttl {
                      description 'ebgp-multihop-ttl and ttl-security-hops are '
                                + 'mutex.'
                                  ;
                      case ebgp-multihop-ttl {
                        description 'Allow EBGP neighbors not on directly conne'
                                  + 'cted net.'
                                    ;
                        leaf ebgp-multihop {
                          description 'Allow EBGP neighbors not on directly con'
                                    + 'nected net.'
                                      ;
                          type uint8 {
                            range 1..255 ;
                          }
                        }
                      }
                      case ttl-security-hops {
                        description 'Enable EBGP TTL security check.'
                                    ;
                        leaf ttl-security-hops {
                          description 'Enable EBGP TTL security check.'
                                      ;
                          type uint8 {
                            range 1..254 ;
                          }
                        }
                      }
                    }
                  }
                  container neighbor-extend {
                    description 'Specify a neighbor.'
                                ;
                    container maximum-prefix {
                      description 'The action that generated when threshold val'
                                + 'ue reached.'
                                  ;
                      presence 'The action that generated when threshold value '
                             + 'reached'
                               ;
                      leaf maximum-prefix-threshold {
                        description 'Threshold value(%) at which to generate a '
                                  + 'warning.'
                                    ;
                        type uint32 {
                          range 1..100 ;
                        }
                        mandatory true ;
                      }
                      leaf maximum-prefix-number {
                        description 'Maximum number of prefix limit.'
                                    ;
                        type uint32 {
                          range 1..4294967295 ;
                        }
                        mandatory true ;
                      }
                      choice maximum-prefix-action {
                        description 'The action that generated when threshold v'
                                  + 'alue reached.'
                                    ;
                        mandatory true ;
                        case peer-action {
                          description 'The action that generated when threshold'
                                    + ' value reached.'
                                      ;
                          leaf action {
                            description 'The action that generated when threshold value reached.'
                                        ;
                            type enumeration {
                              enum down {
                                value 0 ;
                                description 'Break down BGP connection after limit is exceeded.'
                                            ;
                              }
                              enum warning-only {
                                value 1 ;
                                description 'Only give warning message when limit is exceeded.'
                                            ;
                              }
                              enum drop-routes {
                                value 2 ;
                                description 'Drop routes that exceed the maximum-prefix.'
                                            ;
                              }
                            }
                            mandatory true ;
                          }
                        }
                        case restart {
                          description 'Restart BGP connection after limit is ex'
                                    + 'ceeded.'
                                      ;
                          leaf restart-time {
                            description 'Restart interval in minutes.'
                                        ;
                            type uint32 {
                              range 1..30000 ;
                            }
                            units min ;
                            mandatory true ;
                          }
                        }
                      }
                    }
                    container password {
                      description 'Set a password of the neighbor.'
                                  ;
                      choice password {
                        description 'Set a password of the neighbor.'
                                    ;
                        case clear-words {
                          description 'Specify the clear password (1-80 charact'
                                    + 'ers).'
                                      ;
                          leaf clear-words {
                            description 'The clear password (1-80 characters).'
                                        ;
                            type string {
                              length 1..80 ;
                            }
                          }
                        }
                        case encrypted-words {
                          description 'Specify the encrypted password.'
                                      ;
                          leaf encryped-words {
                            description 'Specify the encrypted password.'
                                        ;
                            type string {
                              length 64..172 ;
                            }
                          }
                        }
                      }
                    }
                    container timers {
                      description 'BGP per neighbor timers.'
                                  ;
                      presence timers ;
                      leaf keepalive-time {
                        description 'Adjust keepalive interval.'
                                    ;
                        type uint32 {
                          range 0..65535 ;
                        }
                        units s ;
                        mandatory true ;
                      }
                      leaf hold-time {
                        description 'Hold time interval.'
                                    ;
                        type uint32 {
                          range '0 | 3..65535'
                                ;
                        }
                        units s ;
                        mandatory true ;
                      }
                    }
                    container local-as {
                      description 'Specify a local-as number.'
                                  ;
                      presence local-as ;
                      leaf as-number {
                        description 'Autonomous system number (normal or 4 Octe'
                                  + 'ts).'
                                    ;
                        type ncd:asn-dot {
                          pattern '-?([1-9]+(\.(\d*)|0)?)|(0(\.\d+){1})'
                                  ;
                        }
                        mandatory true ;
                      }
                      leaf no-prepend {
                        description 'Do not prepend local-as to updates from EB'
                                  + 'GP peer.'
                                    ;
                        type empty ;
                      }
                      leaf replace-as {
                        description 'Replace real AS with local AS in the EBGP '
                                  + 'updates.'
                                    ;
                        type empty ;
                      }
                      leaf dual-as {
                        description 'Accept real AS or local AS from the EBGP p'
                                  + 'eer.'
                                    ;
                        type empty ;
                      }
                    }
                    leaf routemap-in-name {
                      description 'Apply map to incoming routes.'
                                  ;
                      type string {
                        length 1..200 ;
                      }
                    }
                    leaf routemap-out-name {
                      description 'Apply map to outbound routes.'
                                  ;
                      type string {
                        length 1..200 ;
                      }
                    }
                    leaf prefixlist-in-name {
                      description 'Apply  prefix list to incoming routes.'
                                  ;
                      type string {
                        length 1..169 ;
                      }
                    }
                    leaf prefixlist-out-name {
                      description 'Apply  prefix list to outbound routes.'
                                  ;
                      type string {
                        length 1..169 ;
                      }
                    }
                    container diverse-path {
                      description 'Advertise diverse path to this neighbor.'
                                  ;
                      presence diverse-path ;
                      choice diverse-path {
                        description 'Advertise diverse path to this neighbor.'
                                    ;
                        mandatory true ;
                        case backup {
                          description 'Advertisement of the backup path.'
                                      ;
                          leaf backup {
                            description 'Advertisement of the backup path.'
                                        ;
                            type empty ;
                            mandatory true ;
                          }
                        }
                        case multipath {
                          description 'Sequence number of multipath.'
                                      ;
                          leaf sequence-number {
                            description 'Sequence number of multipath.'
                                        ;
                            type uint32 {
                              range 2..32 ;
                            }
                            mandatory true ;
                          }
                        }
                      }
                      leaf route-map {
                        description 'Apply route-map to neighbor.'
                                    ;
                        type string {
                          length 1..200 ;
                        }
                        ncd:revise-date 2016-01-06 ;
                      }
                    }
                    leaf additional-paths-receive {
                      description 'Receive additional paths from this neighbor.'
                                  ;
                      type empty ;
                    }
                    container additional-paths-send {
                      description 'Send additional paths to this neighbor.'
                                  ;
                      choice additional-paths-send {
                        description 'Send additional paths to this neighbor.'
                                    ;
                        default send-one-path ;
                        case send-one-path {
                          description 'Send one additional path to this neighbo'
                                    + 'r.'
                                      ;
                          leaf send {
                            description 'Send additional paths to this neighbor.'
                                        ;
                            type empty ;
                          }
                        }
                        case send-multi-paths {
                          description 'Send additional multi-paths to this neig'
                                    + 'hbor.'
                                      ;
                          leaf paths-number {
                            description 'Number of paths for a prefix.'
                                        ;
                            type uint32 {
                              range 2..32 ;
                            }
                            mandatory true ;
                          }
                          leaf prefixlist {
                            description 'Prefixlist of filtering additional paths.'
                                        ;
                            type string {
                              length 1..169 ;
                            }
                          }
                        }
                      }
                    }
                    leaf routepolicy-in-name {
                      description 'Route policy name applied to the inbound rou'
                                + 'tes.'
                                  ;
                      type string {
                        length 1..200 ;
                      }
                      ncd:revise-date 2015-05-18 ;
                    }
                    leaf routepolicy-out-name {
                      description 'Route policy name applied to the outbound ro'
                                + 'utes.'
                                  ;
                      type string {
                        length 1..200 ;
                      }
                      ncd:revise-date 2015-05-18 ;
                    }
                    leaf keychain-name {
                      description 'Keychain name associated to peer for authent'
                                + 'ication.'
                                  ;
                      type string {
                        length 1..31 ;
                      }
                      ncd:revise-date 2015-12-21 ;
                    }
                    container transport {
                      description 'Specify TCP path MTU discovery or TCP MSS to'
                                + ' this neighbor.'
                                  ;
                      choice transport {
                        description 'Specify TCP path MTU discovery or TCP MSS '
                                  + 'to this neighbor.'
                                    ;
                        case path-mtu-discovery {
                          description 'Use transport path MTU discovery.'
                                      ;
                          leaf path-mtu-discovery {
                            description 'Use transport path MTU discovery.'
                                        ;
                            type empty ;
                          }
                        }
                        case mss {
                          description 'Set TCP initial maximum segment size.'
                                      ;
                          leaf mss {
                            description 'Set TCP initial maximum segment size.'
                                        ;
                            type uint32 {
                              range 68..10000 ;
                            }
                          }
                        }
                      }
                      ncd:revise-date 2016-01-06 ;
                    }
                    container withdraw {
                      description 'Withdraw routes when state of track-group is'
                                + ' down.'
                                  ;
                      presence withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                      ncd:revise-date 2016-02-06 ;
                    }
                    container second-withdraw {
                      description 'Withdraw routes when state of the second tra'
                                + 'ck-group is down.'
                                  ;
                      presence second-withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                      ncd:revise-date 2018-07-12 ;
                    }
                    container idle-hold-time {
                      description 'Specifiy the length of time the peer is held'
                                + ' in the idle state.'
                                  ;
                      presence idle-hold-time ;
                      leaf hold-time {
                        description 'Idle hold time.'
                                    ;
                        type uint32 {
                          range 1..3000 ;
                        }
                        units s ;
                        mandatory true ;
                      }
                      leaf increase {
                        description 'Increase idle hold time doubly to maximum '
                                  + '3000.'
                                    ;
                        type empty ;
                      }
                      ncd:revise-date 2016-03-23 ;
                    }
                    container cluster-id {
                      description 'Set Route-Reflector cluster-id type.'
                                  ;
                      choice cluster-id {
                        description 'Set Route-Reflector cluster-id type.'
                                    ;
                        case quantity-type {
                          description 'Route-Reflector Cluster-id as 32 bit qua'
                                    + 'ntity.'
                                      ;
                          leaf cluster-id-quantity {
                            description 'Route-Reflector Cluster-id as 32 bit quantity.'
                                        ;
                            type uint32 {
                              range 1..4294967295 ;
                            }
                          }
                        }
                        case address-type {
                          description 'Route-Reflector Cluster-id in IP address'
                                    + ' format.'
                                      ;
                          leaf cluster-id-address {
                            description 'Route-Reflector Cluster-id in IP address format.'
                                        ;
                            type ncd:ipv4-address {
                              pattern '([1-9][0-9]*\.[1-9][0-9]*\.[1-9][0-9]*\.'
                                    + '[1-9][0-9]*)|([1-9][0-9]*\.0\.0\.0)|(0\.'
                                    + '[1-9][0-9]*\.0\.0)|(0\.0\.[1-9][0-9]*\.0'
                                    + ')|(0\.0\.0\.[1-9][0-9]*)|([1-9][0-9]*\.['
                                    + '1-9][0-9]*\.0\.0)|(0\.[1-9][0-9]*\.[1-9]'
                                    + '[0-9]*\.0)|(0\.0\.[1-9][0-9]*\.[1-9][0-9'
                                    + ']*)|([1-9][0-9]*\.0\.0\.[1-9][0-9]*)|(0\.'
                                    + '[1-9][0-9]*\.0\.[1-9][0-9]*)|([1-9][0-9]'
                                    + '*\.0\.[1-9][0-9]*\.0)|([1-9][0-9]*\.[1-9'
                                    + '][0-9]*\.[1-9][0-9]*\.0)|([1-9][0-9]*\.['
                                    + '1-9][0-9]*\.0\.[1-9][0-9]*)|([1-9][0-9]*'
                                    + '\.0\.[1-9][0-9]*\.[1-9][0-9]*)|(0\.[1-9]'
                                    + '[0-9]*\.[1-9][0-9]*\.[1-9][0-9]*)'
                                      ;
                            }
                          }
                        }
                      }
                      ncd:revise-date 2017-10-23 ;
                    }
                    container tracking {
                      description 'Enable peer tracking.'
                                  ;
                      presence tracking ;
                      leaf tracking {
                        status obsolete {
                          ncd:revise-date 2019-01-15 ;
                        }
                        description 'Enable peer tracking.'
                                    ;
                        type empty ;
                        mandatory true ;
                      }
                      leaf tracking-ex {
                        description 'Peer tracking.'
                                    ;
                        type enumeration {
                          enum enable {
                            value 1 ;
                            description 'Enable peer tracking.'
                                        ;
                          }
                          enum disable {
                            value 0 ;
                            description 'Disable peer tracking.'
                                        ;
                          }
                        }
                        ncd:revise-date 2019-01-15 ;
                      }
                      leaf delay {
                        description 'Delay time to reset the session.'
                                    ;
                        type uint32 {
                          range 1..65535 ;
                        }
                        units s ;
                      }
                      ncd:revise-date 2018-08-29 ;
                    }
                    leaf redirect-ipv6-type {
                      description 'Redirect IPv6 type.'
                                  ;
                      type uint16 {
                        range '12 | 2048'
                              ;
                      }
                      ncd:revise-date 2020-10-15 ;
                    }
                    leaf neighbor-stalepath-time {
                      description "Set the max time to hold on to restarting pe"
                                + "er's stalepaths."
                                  ;
                      type uint32 {
                        range 1..604800 {
                          description 'Delay value.'
                                      ;
                        }
                      }
                      units s ;
                      ncd:revise-date 2021-02-01 ;
                    }
                    leaf neighbor-stalepath-time-permanent {
                      description 'Hold on stale paths permanently.'
                                  ;
                      type empty ;
                      ncd:revise-date 2021-02-01 ;
                    }
                  }
                  leaf dscp {
                    description 'Set DSCP value.'
                                ;
                    type uint8 {
                      range 0..63 ;
                    }
                    ncd:revise-date 2016-01-06 ;
                  }
                  container shutdown {
                    description 'Shut down this neighbor administratively or wh'
                              + 'en state of track-group is down.'
                                ;
                    presence shut-down ;
                    leaf shut-down {
                      description 'Administratively shut down this neighbor.'
                                  ;
                      type empty ;
                      mandatory true ;
                    }
                    leaf track-group {
                      description 'Shut down this neighbor when state of track-'
                                + 'group is down.'
                                  ;
                      type string {
                        length 1..31 ;
                      }
                    }
                    ncd:revise-date 2016-06-12 ;
                  }
                  container route-filter-group {
                    description 'Specify a neighbor to join a route-filter-grou'
                              + 'p.'
                                ;
                    presence route-filter-group ;
                    leaf filter-group {
                      description 'Route filter group name (1-31 characters).'
                                  ;
                      type string {
                        length 1..31 ;
                      }
                      mandatory true ;
                    }
                    leaf next-hop-self {
                      description 'Disable the next hop calculation for this ne'
                                + 'ighbor.'
                                  ;
                      type empty ;
                    }
                    ncd:revise-date 2017-06-12 ;
                  }
                  leaf enforce-first-as-disable {
                    description 'Not enforce the first AS for EBGP neighbor rou'
                              + 'tes'
                                ;
                    type empty ;
                    ncd:revise-date 2018-01-10 ;
                  }
                  leaf announce-sid {
                    description 'Enable Prefix-SID attribute for this neighbor.'
                                ;
                    type enumeration {
                      enum enable {
                        value 1 ;
                        description 'Enable Prefix-SID attribute for this neigh'
                                  + 'bor.'
                                    ;
                      }
                    }
                    ncd:revise-date 2018-05-14 ;
                  }
                  leaf enhanced-route-refresh-disable {
                    description 'Enhanced route refresh capability.'
                                ;
                    type empty ;
                    ncd:revise-date 2018-10-23 ;
                  }
                  container update-source-ex {
                    description 'Specify the update-source configuration of the'
                              + ' neighbor.'
                                ;
                    presence 'Specify the update-source configuration of the ne'
                           + 'ighbor.'
                             ;
                    choice update-source {
                      description 'Specify the update-source configuration of t'
                                + 'he neighbor.'
                                  ;
                      case update-source-if {
                        description 'Specify the update-source interface name o'
                                  + 'f the neighbor.'
                                    ;
                        leaf update-source-ifname {
                          description 'Specify the update-source interface name'
                                    + ' of the neighbor.'
                                      ;
                          type ncd:ifname ;
                        }
                      }
                      case update-source-ipv4 {
                        description 'Specify the update-source IPv4 address of '
                                  + 'the neighbor.'
                                    ;
                        leaf update-source-addrv4 {
                          description 'Specify the update-source IPv4 address o'
                                    + 'f the neighbor.'
                                      ;
                          type ncd:ipv4-address-none-zero ;
                        }
                      }
                      case update-source-ipv6 {
                        description 'Specify the update-source IPv6 address of '
                                  + 'the neighbor.'
                                    ;
                        leaf update-source-addrv6 {
                          description 'Specify the update-source IPv6 address o'
                                    + 'f the neighbor.'
                                      ;
                          type ncd:ipv6-address-none-zero ;
                        }
                        ncd:revise-date 2019-07-07 ;
                      }
                    }
                    ncd:revise-date 2018-11-27 ;
                  }
                  leaf four-byte-as-disable {
                    description 'Disable 4-byte AS capability.'
                                ;
                    type empty ;
                    ncd:revise-date 2019-01-15 ;
                  }
                  leaf sr-epe {
                    description 'Configure neighbor egress peer engineering'
                                ;
                    type link-state ;
                    default null ;
                    ncd:revise-date 2019-07-11 ;
                  }
                  leaf sr-epe-peer-set {
                    description 'Configure peer set for egress peer engineering.'
                                ;
                    type string {
                      length 1..31 ;
                    }
                    ncd:revise-date 2019-09-24 ;
                  }
                  choice backup-addr {
                    description 'Configure backup route'
                                ;
                    case backup-ipv4 {
                      description 'Configure backup route IPv4 address'
                                  ;
                      leaf backup {
                        description 'Configure backup route IPv4 address'
                                    ;
                        type ncd:ipv4-address-none-zero ;
                      }
                      ncd:revise-date 2019-07-11 ;
                    }
                    case backup-ipv6 {
                      description 'Configure backup route IPv6 address'
                                  ;
                      leaf backup-addrv6 {
                        description 'Configure backup route IPv6 address'
                                    ;
                        type ncd:ipv6-address-none-zero ;
                      }
                      ncd:revise-date 2019-09-24 ;
                    }
                    ncd:revise-date 2019-07-11 ;
                  }
                  leaf ope-type {
                    description 'Tunnel encapsulation attribute OPE type.'
                                ;
                    type uint16 {
                      range 1..65535 ;
                    }
                    ncd:revise-date 2019-08-26 ;
                  }
                  leaf send-link-bw {
                    description 'Send link bandwidth to this neighbor'
                                ;
                    type enumeration {
                      enum disable {
                        value 0 ;
                        description 'Disable peer send link bandwidth'
                                    ;
                      }
                      enum enable {
                        value 1 ;
                        description 'Enable peer send link bandwidth'
                                    ;
                      }
                    }
                    ncd:revise-date 2019-10-22 ;
                  }
                  leaf receive-single-label {
                    description 'Receive single label only for label unicast ro'
                              + 'ute.'
                                ;
                    type enumeration {
                      enum disable {
                        value 0 ;
                        description 'Disable receive single label only for labe'
                                  + 'l unicast route'
                                    ;
                      }
                      enum enable {
                        value 1 ;
                        description 'Enable receive single label only for label'
                                  + ' unicast route'
                                    ;
                      }
                    }
                    ncd:revise-date 2019-11-29 ;
                  }
                  leaf receive-single-label-compatible {
                    description 'Receive single label only for label unicast ro'
                              + 'ute.The function is the same as receive-single'
                              + '-label node.'
                                ;
                    type enumeration {
                      enum disable {
                        value 0 ;
                        description 'Disable receive single label only for labe'
                                  + 'l unicast route'
                                    ;
                      }
                      enum enable {
                        value 1 ;
                        description 'Enable receive single label only for label'
                                  + ' unicast route'
                                    ;
                      }
                    }
                    ncd:revise-date 2020-07-28 ;
                  }
                  leaf ignore-error-packet {
                    description 'Ignore error packet for this neighbor.'
                                ;
                    type enumeration {
                      enum disable {
                        value 0 ;
                        description 'Disable peer ignore error packet'
                                    ;
                      }
                      enum enable {
                        value 1 ;
                        description 'Enable peer ignore error packet'
                                    ;
                      }
                    }
                    default disable ;
                    ncd:revise-date 2020-01-13 ;
                  }
                  leaf srv6-l2-service-type {
                    description 'SRv6 L2 service type,cannot be the same as SRv'
                              + '6 L3 service.'
                                ;
                    type uint8 {
                      range 5..254 ;
                    }
                    ncd:revise-date 2020-03-02 ;
                  }
                  leaf srv6-l3-service-type {
                    description 'SRv6 L3 service type,cannot be the same as SRv'
                              + '6 L2 service.'
                                ;
                    type uint8 {
                      range 5..254 ;
                    }
                    ncd:revise-date 2020-03-02 ;
                  }
                  container route-server-client {
                    description 'Set route server client only valid for ebgp pe'
                              + 'er.'
                                ;
                    presence route-server-client ;
                    leaf route-svr-client {
                      description 'Set route server client only valid for ebgp '
                                + 'peer.'
                                  ;
                      type empty ;
                      mandatory true ;
                    }
                    ncd:revise-date 2020-04-07 ;
                  }
                  container srv6-epe {
                    status obsolete {
                      ncd:revise-date 2020-06-29 ;
                    }
                    description 'SRv6 BGP EPE peer node SID'
                                ;
                    container srv6-epe-auto-peernode {
                      status obsolete {
                        ncd:revise-date 2020-06-29 ;
                      }
                      description 'Automatic generation of SRv6 peer node SID'
                                  ;
                      leaf auto {
                        status obsolete {
                          ncd:revise-date 2020-06-29 ;
                        }
                        description 'Automatic generation of SRv6 peer node SID.'
                                    ;
                        type enumeration {
                          enum auto {
                            value 1 ;
                            description 'Automatic generation of SRv6 peer node SID.'
                                        ;
                          }
                        }
                      }
                    }
                    ncd:revise-date 2020-05-11 ;
                  }
                  container srv6-epe-peernode {
                    description 'Automatic generation of SRv6 peer node SID'
                                ;
                    leaf auto {
                      description 'Automatic generation of SRv6 peer node SID'
                                  ;
                      type enumeration {
                        enum auto {
                          value 1 ;
                          description 'Automatic generation of SRv6 peer node S'
                                    + 'ID'
                                      ;
                        }
                      }
                    }
                    ncd:revise-date 2020-11-11 ;
                  }
                }
              }
              container neighbor-uni-ipv4 {
                description 'Specify a IPv4 neighbor.'
                            ;
                list neighbor-uni {
                  description 'Specify a IPv4 neighbor.'
                              ;
                  key ipv4-addr ;
                  leaf ipv4-addr {
                    description 'Neighbor IPv4 address.'
                                ;
                    type ncd:ipv4-address ;
                  }
                  leaf remote-as {
                    description 'Specify a BGP neighbor AS number.'
                                ;
                    type ncd:asn-dot ;
                  }
                  leaf join-peergroup {
                    description 'Create/Join a peer group(1-31 characters).'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf monitor {
                    description 'Config BMP monitor for the address family of t'
                              + 'his neighbor.'
                                ;
                    type enumeration {
                      enum disable {
                        value 2 ;
                      }
                      enum enable {
                        value 1 ;
                      }
                      enum inherit-global-config {
                        value 0 ;
                      }
                    }
                    ncd:revise-date 2019-07-29 ;
                  }
                  leaf advertisement-interval {
                    description 'Minimum interval between sending BGP routing w'
                              + 'hich is not locally originated updates.'
                                ;
                    type uint32 {
                      range 1..65535 ;
                    }
                    units s ;
                  }
                  leaf advertise-maximum-prefix {
                    description 'Maximum number of prefix send to this peer.'
                                ;
                    type uint32 {
                      range 1..4294967295 ;
                    }
                    ncd:revise-date 2016-01-06 ;
                  }
                  leaf allowas-in {
                    description 'Accept as-path with my AS present in it.'
                                ;
                    type uint32 {
                      range 1..10 {
                        description 'The number of my AS that presented in as-p'
                                  + 'ath.'
                                    ;
                      }
                    }
                  }
                  leaf default-originate {
                    description 'Originate default route to this neighbor.'
                                ;
                    type empty ;
                  }
                  leaf default-originate-routemap {
                    description 'Map external entry attributes into routing tab'
                              + 'le.'
                                ;
                    type string {
                      length 1..200 ;
                    }
                    ncd:revise-date 2020-07-28 ;
                  }
                  leaf default-originate-routepolicy {
                    description 'Set external entry attributes into routing tab'
                              + 'le.'
                                ;
                    type string {
                      length 1..200 ;
                    }
                    ncd:revise-date 2020-10-10 ;
                  }
                  leaf description {
                    description 'Neighbor specific description.'
                                ;
                    type ncd:string-with-blank {
                      length 1..80 ;
                    }
                  }
                  leaf next-hop-self {
                    description 'Disable the next hop calculation for this neig'
                              + 'hbor.'
                                ;
                    type enumeration {
                      enum enable {
                        value 1 ;
                        description 'Apply next-hop-self for EBGP route.'
                                    ;
                      }
                      enum all {
                        value 2 ;
                        description 'Apply next-hop-self for both EBGP and IBGP'
                                  + ' route.'
                                    ;
                      }
                    }
                  }
                  choice nh-unchanged {
                    case next-hop-unchanged {
                      description 'NEXT_HOP of the IBGP path propagated unchang'
                                + 'ed to this neighbor.'
                                  ;
                      leaf next-hop-unchanged {
                        description 'Propagate next hop unchanged for IBGP path'
                                  + 's to this neighbor.'
                                    ;
                        type empty ;
                      }
                      ncd:revise-date 2019-06-04 ;
                    }
                    case next-hop-unchanged-all {
                      description 'NEXT_HOP of either EBGP or IBGP path propaga'
                                + 'ted unchanged to this neighbor.'
                                  ;
                      leaf next-hop-unchanged-all {
                        description 'NEXT_HOP of either EBGP or IBGP path propa'
                                  + 'gated unchanged to this neighbor.'
                                    ;
                        type empty ;
                      }
                      ncd:revise-date 2020-04-07 ;
                    }
                  }
                  leaf originate-interval {
                    description 'Minimum interval between sending BGP routing w'
                              + 'hich is locally originated updates.'
                                ;
                    type uint32 {
                      range 1..65535 ;
                    }
                    units s ;
                  }
                  leaf passive {
                    description "Don't send open messages to this neighbor acti"
                              + "vely."
                                ;
                    type empty ;
                  }
                  leaf remove-private-as {
                    description 'EBGP use to remove private AS number.'
                                ;
                    type enumeration {
                      enum disable {
                        value 0 ;
                      }
                      enum enable {
                        value 1 ;
                      }
                    }
                  }
                  leaf route-reflector-client {
                    description 'Set this neighbor as a client peer.'
                                ;
                    type empty ;
                  }
                  leaf send-community {
                    description 'Send community to this neighbor.'
                                ;
                    type empty ;
                  }
                  leaf send-large-community {
                    description 'Send Large-community to this neighbor.'
                                ;
                    type empty ;
                    ncd:revise-date 2020-04-16 ;
                  }
                  leaf send-med {
                    description 'Send metric attribute to this neighbor.'
                                ;
                    type empty ;
                  }
                  leaf inherit-igp-metric {
                    description 'Med attribute inherited from IGP metric before'
                              + ' sending updates'
                                ;
                    type empty ;
                    ncd:revise-date 2017-07-25 ;
                  }
                  leaf shut-down {
                    status obsolete {
                      ncd:revise-date 2016-06-12 ;
                    }
                    description 'Administratively shut down this neighbor.'
                                ;
                    type empty ;
                  }
                  leaf update-source {
                    status obsolete {
                      ncd:revise-date 2018-11-27 ;
                    }
                    description 'Source of routing updates.'
                                ;
                    type ncd:ifname {
                      length 1..31 ;
                    }
                  }
                  leaf send-label {
                    description 'Send NLRI with MPLS label to this neighbor.'
                                ;
                    type empty ;
                  }
                  leaf soft-reconfiguration {
                    status obsolete {
                      ncd:revise-date 2018-01-31 ;
                    }
                    description 'Neighbor soft reconfiguration.'
                                ;
                    type empty ;
                  }
                  leaf soft-reconfig {
                    description 'Neighbor soft reconfiguration.'
                                ;
                    type enumeration {
                      enum soft-reconfiguration {
                        value 1 ;
                        description Soft-reconfiguration. ;
                      }
                      enum enforce-soft-reconfiguration {
                        value 2 ;
                        description 'Enforce soft-reconfiguration instead of se'
                                  + 'nding route-refresh.'
                                    ;
                      }
                    }
                    ncd:revise-date 2018-01-31 ;
                  }
                  leaf maxas-in {
                    description 'Accept as-path not exceeded maxas-in.'
                                ;
                    type uint32 {
                      range 1..250 ;
                    }
                  }
                  leaf split-updgrp {
                    description 'Split neighbor from update group.'
                                ;
                    type empty ;
                  }
                  leaf weight {
                    description 'Set weight for routes from this neighbor.'
                                ;
                    type uint32 {
                      range 1..65535 ;
                    }
                  }
                  leaf connect-retry-interval {
                    description 'Set data of connect-retry timer for this neigh'
                              + 'bor.'
                                ;
                    type uint32 {
                      range 1..65535 ;
                    }
                    units s ;
                  }
                  leaf orf-prefix-filter {
                    description 'Advertise prefixlist ORF capability to this ne'
                              + 'ighbor.'
                                ;
                    type enumeration {
                      enum receive {
                        value 1 ;
                        description 'Capability to receive the ORF from this ne'
                                  + 'ighbor.'
                                    ;
                      }
                      enum send {
                        value 2 ;
                        description 'Capability to send the ORF to this neighbo'
                                  + 'r.'
                                    ;
                      }
                      enum both {
                        value 3 ;
                        description 'Capability to send and receive the ORF.'
                                    ;
                      }
                    }
                  }
                  leaf orf-prefix-filter-cisco {
                    description 'Compatible with CISCO.'
                                ;
                    type empty ;
                  }
                  leaf open-delay {
                    description 'Delay to send open message.'
                                ;
                    type uint32 {
                      range 1..240 ;
                    }
                    units s ;
                  }
                  leaf as-path-loopcheck {
                    description 'Check as-path sending BGP routing to EBGP neig'
                              + 'hbor.'
                                ;
                    type empty ;
                  }
                  leaf aigp {
                    description 'Enable AIGP for this neighbor.'
                                ;
                    type empty ;
                    ncd:revise-date 2017-11-01 ;
                  }
                  container advertise-map-uni {
                    description 'Specify route-map for conditional advertisemen'
                              + 't.'
                                ;
                    presence 'Specify route-map for conditional advertisement.'
                             ;
                    leaf advertise-map-name {
                      description 'Advertise route-map name.'
                                  ;
                      type string {
                        length 1..200 ;
                      }
                      mandatory true ;
                    }
                    choice advertise-map {
                      description 'Specify route-map for conditional advertisem'
                                + 'ent.'
                                  ;
                      mandatory true ;
                      case exist-map {
                        description 'Advertise prefix only if prefix exists.'
                                    ;
                        leaf exist-map-name {
                          description 'Advertise prefix only if prefix exists.'
                                      ;
                          type string {
                            length 1..200 ;
                          }
                          mandatory true ;
                        }
                      }
                      case nonexist-map {
                        description 'Advertise prefix only if prefix does not e'
                                  + 'xist.'
                                    ;
                        leaf nonexist-map-name {
                          description 'Advertise prefix only if prefix does not'
                                    + ' exist.'
                                      ;
                          type string {
                            length 1..200 ;
                          }
                          mandatory true ;
                        }
                      }
                    }
                  }
                  container fall-over {
                    description 'Set BFD supporting for fallover.'
                                ;
                    presence 'Enable BFD support for fallover'
                             ;
                    leaf bfd {
                      description 'Enable BFD support for fallover.'
                                  ;
                      type empty ;
                      mandatory true ;
                    }
                    container bfd-parameters {
                      description 'The parameters of BFD.'
                                  ;
                      presence bfd-parameters ;
                      choice bfd-parameters {
                        description 'Config bfd parameters'
                                    ;
                        case template-name {
                          description 'Template name'
                                      ;
                          leaf template {
                            description 'BFD template name'
                                        ;
                            type string {
                              length 1..31 ;
                            }
                          }
                          ncd:revise-date 2020-03-31 ;
                        }
                        case parameters {
                          description Parameters ;
                          leaf bfd-interval {
                            description 'Minimum send interval.'
                                        ;
                            type uint32 {
                              range 10..990 ;
                            }
                            units ms ;
                            mandatory true ;
                          }
                          leaf min-rx {
                            description 'Minimum receive interval.'
                                        ;
                            type uint32 {
                              range 10..990 ;
                            }
                            units ms ;
                            mandatory true ;
                          }
                          leaf multiplier {
                            description Multiplier. ;
                            type uint8 {
                              range 3..50 ;
                            }
                            mandatory true ;
                          }
                        }
                      }
                    }
                    leaf bfd-hop {
                      description 'bfd optional hop'
                                  ;
                      type enumeration {
                        enum single-hop {
                          value 1 ;
                          description 'Set single-hop bfd'
                                      ;
                        }
                        enum multi-hop {
                          value 2 ;
                          description 'Set multi-hop bfd'
                                      ;
                        }
                      }
                      ncd:revise-date 2019-04-23 ;
                    }
                  }
                  container set-ttl {
                    description 'ebgp-multihop-ttl and ttl-security-hops are mu'
                              + 'tex.'
                                ;
                    choice set-ttl {
                      description 'ebgp-multihop-ttl and ttl-security-hops are '
                                + 'mutex.'
                                  ;
                      case ebgp-multihop-ttl {
                        description 'Allow EBGP neighbors not on directly conne'
                                  + 'cted net.'
                                    ;
                        leaf ebgp-multihop {
                          description 'Allow EBGP neighbors not on directly con'
                                    + 'nected net.'
                                      ;
                          type uint8 {
                            range 1..255 ;
                          }
                        }
                      }
                      case ttl-security-hops {
                        description 'Enable EBGP TTL security check.'
                                    ;
                        leaf ttl-security-hops {
                          description 'Enable EBGP TTL security check.'
                                      ;
                          type uint8 {
                            range 1..254 ;
                          }
                        }
                      }
                    }
                  }
                  container neighbor-extend {
                    description 'Specify a neighbor.'
                                ;
                    container maximum-prefix {
                      description 'The action that generated when threshold val'
                                + 'ue reached.'
                                  ;
                      presence 'The action that generated when threshold value '
                             + 'reached'
                               ;
                      leaf maximum-prefix-threshold {
                        description 'Threshold value(%) at which to generate a '
                                  + 'warning.'
                                    ;
                        type uint32 {
                          range 1..100 ;
                        }
                        mandatory true ;
                      }
                      leaf maximum-prefix-number {
                        description 'Maximum number of prefix limit.'
                                    ;
                        type uint32 {
                          range 1..4294967295 ;
                        }
                        mandatory true ;
                      }
                      choice maximum-prefix-action {
                        description 'The action that generated when threshold v'
                                  + 'alue reached.'
                                    ;
                        mandatory true ;
                        case peer-action {
                          description 'The action that generated when threshold'
                                    + ' value reached.'
                                      ;
                          leaf action {
                            description 'The action that generated when threshold value reached.'
                                        ;
                            type enumeration {
                              enum down {
                                value 0 ;
                                description 'Break down BGP connection after limit is exceeded.'
                                            ;
                              }
                              enum warning-only {
                                value 1 ;
                                description 'Only give warning message when limit is exceeded.'
                                            ;
                                reference 'Only give warning message when limit is exceeded.'
                                          ;
                              }
                              enum drop-routes {
                                value 2 ;
                                description 'Drop routes that exceed the maximum-prefix.'
                                            ;
                              }
                            }
                            mandatory true ;
                          }
                        }
                        case restart {
                          description 'Restart BGP connection after limit is ex'
                                    + 'ceeded.'
                                      ;
                          leaf restart-time {
                            description 'Restart interval in minutes.'
                                        ;
                            type uint32 {
                              range 1..30000 ;
                            }
                            units min ;
                            mandatory true ;
                          }
                        }
                      }
                    }
                    container password {
                      description 'Set a password of the neighbor.'
                                  ;
                      choice password {
                        description 'Set a password of the neighbor.'
                                    ;
                        default encrypted-words ;
                        case clear-words {
                          description 'Specify the clear password (1-80 charact'
                                    + 'ers).'
                                      ;
                          leaf clear-words {
                            description 'The clear password (1-80 characters).'
                                        ;
                            type string {
                              length 1..80 ;
                            }
                          }
                        }
                        case encrypted-words {
                          description 'Specify the encrypted password.'
                                      ;
                          leaf encryped-words {
                            description 'Specify the encrypted password.'
                                        ;
                            type string {
                              length 64..172 ;
                            }
                          }
                        }
                      }
                    }
                    container timers {
                      description 'BGP per neighbor timers.'
                                  ;
                      presence timers ;
                      leaf keepalive-time {
                        description 'Adjust keepalive interval.'
                                    ;
                        type uint32 {
                          range 0..65535 ;
                        }
                        units s ;
                        mandatory true ;
                      }
                      leaf hold-time {
                        description 'Hold time interval.'
                                    ;
                        type uint32 {
                          range '0 | 3..65535'
                                ;
                        }
                        units s ;
                        mandatory true ;
                      }
                    }
                    container local-as {
                      description 'Specify a local-as number.'
                                  ;
                      presence local-as ;
                      leaf as-number {
                        description 'Autonomous system number (normal or 4 Octe'
                                  + 'ts).'
                                    ;
                        type ncd:asn-dot {
                          pattern '-?([1-9]+(\.(\d*)|0)?)|(0(\.\d+){1})'
                                  ;
                        }
                        mandatory true ;
                      }
                      leaf no-prepend {
                        description 'Do not prepend local-as to updates from EB'
                                  + 'GP peer.'
                                    ;
                        type empty ;
                      }
                      leaf replace-as {
                        description 'Replace real AS with local AS in the EBGP '
                                  + 'updates.'
                                    ;
                        type empty ;
                      }
                      leaf dual-as {
                        description 'Accept real AS or local AS from the EBGP p'
                                  + 'eer.'
                                    ;
                        type empty ;
                      }
                    }
                    leaf routemap-in-name {
                      description 'Apply map to incoming routes.'
                                  ;
                      type string {
                        length 1..200 ;
                      }
                    }
                    leaf routemap-out-name {
                      description 'Apply map to outbound routes.'
                                  ;
                      type string {
                        length 1..200 ;
                      }
                    }
                    leaf prefixlist-in-name {
                      description 'Apply  prefix list to incoming routes.'
                                  ;
                      type string {
                        length 1..169 ;
                      }
                    }
                    leaf prefixlist-out-name {
                      description 'Apply  prefix list to outbound routes.'
                                  ;
                      type string {
                        length 1..169 ;
                      }
                    }
                    container diverse-path {
                      description 'Advertise diverse path to this neighbor.'
                                  ;
                      presence diverse-path ;
                      choice diverse-path {
                        description 'Advertise diverse path to this neighbor.'
                                    ;
                        mandatory true ;
                        case backup {
                          description 'Advertisement of the backup path.'
                                      ;
                          leaf backup {
                            description 'Advertisement of the backup path.'
                                        ;
                            type empty ;
                            mandatory true ;
                          }
                        }
                        case multipath {
                          description 'Sequence number of multipath.'
                                      ;
                          leaf sequence-number {
                            description 'Sequence number of multipath.'
                                        ;
                            type uint32 {
                              range 2..32 ;
                            }
                            mandatory true ;
                          }
                        }
                      }
                      leaf route-map {
                        description 'Apply route-map to neighbor.'
                                    ;
                        type string {
                          length 1..200 ;
                        }
                        ncd:revise-date 2016-01-06 ;
                      }
                    }
                    leaf additional-paths-receive {
                      description 'Receive additional paths from this neighbor.'
                                  ;
                      type empty ;
                    }
                    container additional-paths-send {
                      description 'Send additional paths to this neighbor.'
                                  ;
                      choice additional-paths-send {
                        description 'Send additional paths to this neighbor.'
                                    ;
                        default send-one-path ;
                        case send-one-path {
                          description 'Send one additional path to this neighbo'
                                    + 'r.'
                                      ;
                          leaf send {
                            description 'Send additional paths to this neighbor.'
                                        ;
                            type empty ;
                          }
                        }
                        case send-multi-paths {
                          description 'Send additional multi-paths to this neig'
                                    + 'hbor.'
                                      ;
                          leaf paths-number {
                            description 'Number of paths for a prefix.'
                                        ;
                            type uint32 {
                              range 2..32 ;
                            }
                            mandatory true ;
                          }
                          leaf prefixlist {
                            description 'Prefixlist of filtering additional paths.'
                                        ;
                            type string {
                              length 1..169 ;
                            }
                          }
                        }
                      }
                    }
                    leaf routepolicy-in-name {
                      description 'Route policy name applied to the inbound rou'
                                + 'tes.'
                                  ;
                      type string {
                        length 1..200 ;
                      }
                      ncd:revise-date 2015-05-18 ;
                    }
                    leaf routepolicy-out-name {
                      description 'Route policy name applied to the outbound ro'
                                + 'utes.'
                                  ;
                      type string {
                        length 1..200 ;
                      }
                      ncd:revise-date 2015-05-18 ;
                    }
                    leaf keychain-name {
                      description 'Keychain name associated to peer for authent'
                                + 'ication.'
                                  ;
                      type string {
                        length 1..31 ;
                      }
                      ncd:revise-date 2015-12-21 ;
                    }
                    container transport {
                      description 'Specify TCP path MTU discovery or TCP MSS to'
                                + ' this neighbor.'
                                  ;
                      choice transport {
                        description 'Specify TCP path MTU discovery or TCP MSS '
                                  + 'to this neighbor.'
                                    ;
                        case path-mtu-discovery {
                          description 'Use transport path MTU discovery.'
                                      ;
                          leaf path-mtu-discovery {
                            description 'Use transport path MTU discovery.'
                                        ;
                            type empty ;
                          }
                        }
                        case mss {
                          description 'Set TCP initial maximum segment size.'
                                      ;
                          leaf mss {
                            description 'Set TCP initial maximum segment size.'
                                        ;
                            type uint32 {
                              range 68..10000 ;
                            }
                          }
                        }
                      }
                      ncd:revise-date 2016-01-06 ;
                    }
                    container withdraw {
                      description 'Withdraw routes when state of track-group is'
                                + ' down.'
                                  ;
                      presence withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                      ncd:revise-date 2016-02-06 ;
                    }
                    container second-withdraw {
                      description 'Withdraw routes when state of the second tra'
                                + 'ck-group is down.'
                                  ;
                      presence second-withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                      ncd:revise-date 2018-07-12 ;
                    }
                    container wait-ctrlr-arp {
                      description 'Route advertisement delay until the controll'
                                + 'er ARP synchronized event is received.'
                                  ;
                      presence wait-controller-arp ;
                      leaf wait-arp {
                        description 'Route advertisement delay until the contro'
                                  + 'ller ARP synchronized event is received.'
                                    ;
                        type empty ;
                        mandatory true ;
                      }
                      leaf route-map {
                        description 'Route-map name applied to waiting for cont'
                                  + 'roller ARP synchronized event.'
                                    ;
                        type string {
                          length 1..200 ;
                        }
                      }
                      ncd:revise-date 2016-03-07 ;
                    }
                    container idle-hold-time {
                      description 'Specifiy the length of time the peer is held'
                                + ' in the idle state.'
                                  ;
                      presence idle-hold-time ;
                      leaf hold-time {
                        description 'Idle hold time.'
                                    ;
                        type uint32 {
                          range 1..3000 ;
                        }
                        units s ;
                        mandatory true ;
                      }
                      leaf increase {
                        description 'Increase idle hold time doubly to maximum '
                                  + '3000.'
                                    ;
                        type empty ;
                      }
                      ncd:revise-date 2016-03-23 ;
                    }
                    container cluster-id {
                      description 'Set Route-Reflector cluster-id type.'
                                  ;
                      choice cluster-id {
                        description 'Set Route-Reflector cluster-id type.'
                                    ;
                        case quantity-type {
                          description 'Route-Reflector Cluster-id as 32 bit qua'
                                    + 'ntity.'
                                      ;
                          leaf cluster-id-quantity {
                            description 'Route-Reflector Cluster-id as 32 bit quantity.'
                                        ;
                            type uint32 {
                              range 1..4294967295 ;
                            }
                          }
                        }
                        case address-type {
                          description 'Route-Reflector Cluster-id in IP address'
                                    + ' format.'
                                      ;
                          leaf cluster-id-address {
                            description 'Route-Reflector Cluster-id in IP address format.'
                                        ;
                            type ncd:ipv4-address {
                              pattern '([1-9][0-9]*\.[1-9][0-9]*\.[1-9][0-9]*\.'
                                    + '[1-9][0-9]*)|([1-9][0-9]*\.0\.0\.0)|(0\.'
                                    + '[1-9][0-9]*\.0\.0)|(0\.0\.[1-9][0-9]*\.0'
                                    + ')|(0\.0\.0\.[1-9][0-9]*)|([1-9][0-9]*\.['
                                    + '1-9][0-9]*\.0\.0)|(0\.[1-9][0-9]*\.[1-9]'
                                    + '[0-9]*\.0)|(0\.0\.[1-9][0-9]*\.[1-9][0-9'
                                    + ']*)|([1-9][0-9]*\.0\.0\.[1-9][0-9]*)|(0\.'
                                    + '[1-9][0-9]*\.0\.[1-9][0-9]*)|([1-9][0-9]'
                                    + '*\.0\.[1-9][0-9]*\.0)|([1-9][0-9]*\.[1-9'
                                    + '][0-9]*\.[1-9][0-9]*\.0)|([1-9][0-9]*\.['
                                    + '1-9][0-9]*\.0\.[1-9][0-9]*)|([1-9][0-9]*'
                                    + '\.0\.[1-9][0-9]*\.[1-9][0-9]*)|(0\.[1-9]'
                                    + '[0-9]*\.[1-9][0-9]*\.[1-9][0-9]*)'
                                      ;
                            }
                          }
                        }
                      }
                      ncd:revise-date 2017-10-23 ;
                    }
                    container tracking {
                      description 'Enable peer tracking.'
                                  ;
                      presence tracking ;
                      leaf tracking {
                        status obsolete {
                          ncd:revise-date 2019-01-15 ;
                        }
                        description 'Enable peer tracking.'
                                    ;
                        type empty ;
                        mandatory true ;
                      }
                      leaf tracking-ex {
                        description 'Peer tracking.'
                                    ;
                        type enumeration {
                          enum enable {
                            value 1 ;
                            description 'Enable peer tracking.'
                                        ;
                          }
                          enum disable {
                            value 0 ;
                            description 'Disable peer tracking.'
                                        ;
                          }
                          enum inherit {
                            value 2 ;
                            description 'If the neighbor joined a group, the status of tracking inherited from group.'
                                        ;
                          }
                        }
                        ncd:revise-date 2019-01-15 ;
                      }
                      leaf delay {
                        description 'Delay time to reset the session.'
                                    ;
                        type uint32 {
                          range 1..65535 ;
                        }
                        units s ;
                      }
                      ncd:revise-date 2018-08-29 ;
                    }
                    leaf redirect-ipv6-type {
                      description 'Redirect IPv6 type.'
                                  ;
                      type uint16 {
                        range '12 | 2048'
                              ;
                      }
                      ncd:revise-date 2020-10-15 ;
                    }
                    leaf neighbor-stalepath-time {
                      description "Set the max time to hold on to restarting pe"
                                + "er's stalepaths."
                                  ;
                      type uint32 {
                        range 1..604800 {
                          description 'Delay value.'
                                      ;
                        }
                      }
                      units s ;
                      ncd:revise-date 2021-02-01 ;
                    }
                    leaf neighbor-stalepath-time-permanent {
                      description 'Hold on stale paths permanently.'
                                  ;
                      type empty ;
                      ncd:revise-date 2021-02-01 ;
                    }
                  }
                  leaf nouse-peergroup-config {
                    description 'Peer do not use group config set.Only for get '
                              + 'operation.'
                                ;
                    type empty ;
                  }
                  leaf dscp {
                    description 'Set DSCP value.'
                                ;
                    type uint8 {
                      range 0..63 ;
                    }
                    ncd:revise-date 2016-01-06 ;
                  }
                  container shutdown {
                    description 'Shut down this neighbor administratively or wh'
                              + 'en state of track-group is down.'
                                ;
                    presence shut-down ;
                    leaf shut-down {
                      description 'Administratively shut down this neighbor.'
                                  ;
                      type empty ;
                      mandatory true ;
                    }
                    leaf track-group {
                      description 'Shut down this neighbor when state of track-'
                                + 'group is down.'
                                  ;
                      type string {
                        length 1..31 ;
                      }
                    }
                    ncd:revise-date 2016-06-12 ;
                  }
                  container route-filter-group {
                    description 'Specify a neighbor to join a route-filter-grou'
                              + 'p.'
                                ;
                    presence route-filter-group ;
                    leaf filter-group {
                      description 'Route filter group name (1-31 characters).'
                                  ;
                      type string {
                        length 1..31 ;
                      }
                      mandatory true ;
                    }
                    leaf next-hop-self {
                      description 'Disable the next hop calculation for this ne'
                                + 'ighbor.'
                                  ;
                      type empty ;
                    }
                    ncd:revise-date 2017-06-12 ;
                  }
                  leaf enforce-first-as-disable {
                    description 'Not enforce the first AS for EBGP neighbor rou'
                              + 'tes'
                                ;
                    type empty ;
                    ncd:revise-date 2018-01-10 ;
                  }
                  leaf announce-sid {
                    description 'Enable Prefix-SID attribute for this neighbor.'
                                ;
                    type enumeration {
                      enum enable {
                        value 1 ;
                        description 'Enable Prefix-SID attribute for this neigh'
                                  + 'bor.'
                                    ;
                      }
                    }
                    ncd:revise-date 2018-05-14 ;
                  }
                  leaf enhanced-route-refresh-disable {
                    description 'Enhanced route refresh capability.'
                                ;
                    type empty ;
                    ncd:revise-date 2018-10-23 ;
                  }
                  container update-source-ex {
                    description 'Specify the update-source configuration of the'
                              + ' neighbor.'
                                ;
                    presence 'Specify the update-source configuration of the ne'
                           + 'ighbor.'
                             ;
                    choice update-source {
                      description 'Specify the update-source configuration of t'
                                + 'he neighbor.'
                                  ;
                      case update-source-if {
                        description 'Specify the update-source interface name o'
                                  + 'f the neighbor.'
                                    ;
                        leaf update-source-ifname {
                          description 'Specify the update-source interface name'
                                    + ' of the neighbor.'
                                      ;
                          type ncd:ifname ;
                        }
                      }
                      case update-source-ipv4 {
                        description 'Specify the update-source IPv4 address of '
                                  + 'the neighbor.'
                                    ;
                        leaf update-source-addrv4 {
                          description 'Specify the update-source IPv4 address o'
                                    + 'f the neighbor.'
                                      ;
                          type ncd:ipv4-address-none-zero ;
                        }
                      }
                      case update-source-ipv6 {
                        description 'Specify the update-source IPv6 address of '
                                  + 'the neighbor.'
                                    ;
                        leaf update-source-addrv6 {
                          description 'Specify the update-source IPv6 address o'
                                    + 'f the neighbor.'
                                      ;
                          type ncd:ipv6-address-none-zero ;
                        }
                        ncd:revise-date 2019-07-07 ;
                      }
                    }
                    ncd:revise-date 2018-11-27 ;
                  }
                  leaf four-byte-as-disable {
                    description 'Disable 4-byte AS capability.'
                                ;
                    type empty ;
                    ncd:revise-date 2019-01-15 ;
                  }
                  leaf sr-epe {
                    description 'Configure neighbor egress peer engineering'
                                ;
                    type link-state ;
                    default null ;
                    ncd:revise-date 2019-07-11 ;
                  }
                  leaf sr-epe-peer-set {
                    description 'Configure peer set for egress peer engineering.'
                                ;
                    type string {
                      length 1..31 ;
                    }
                    ncd:revise-date 2019-09-24 ;
                  }
                  container sr-epe-peer-adj {
                    status obsolete {
                      ncd:revise-date 2020-07-21 ;
                    }
                    description 'Configure peer-adj for egress peer engineering.'
                                ;
                    container ipv4-number {
                      status obsolete {
                        ncd:revise-date 2020-07-21 ;
                      }
                      description 'Configure IPv4 peer-adj for egress peer engi'
                                + 'neering.'
                                  ;
                      list peer-adj-ipv4 {
                        status obsolete {
                          ncd:revise-date 2020-07-21 ;
                        }
                        description 'Configure IPv4 peer-adj for egress peer en'
                                  + 'gineering.'
                                    ;
                        key 'local remote'
                            ;
                        leaf local {
                          status obsolete {
                            ncd:revise-date 2020-07-21 ;
                          }
                          description 'Configure local IP address.'
                                      ;
                          type ncd:ipv4-address-none-zero ;
                        }
                        leaf remote {
                          status obsolete {
                            ncd:revise-date 2020-07-21 ;
                          }
                          description 'Configure remote IP address.'
                                      ;
                          type ncd:ipv4-address-none-zero ;
                        }
                      }
                    }
                    container ipv6-number {
                      status obsolete {
                        ncd:revise-date 2020-07-21 ;
                      }
                      description 'Configure IPv6 peer-adj for egress peer engi'
                                + 'neering.'
                                  ;
                      list peer-adj-ipv6 {
                        status obsolete {
                          ncd:revise-date 2020-07-21 ;
                        }
                        description 'Configure IPv6 peer-adj for egress peer en'
                                  + 'gineering.'
                                    ;
                        key 'local remote'
                            ;
                        leaf local {
                          status obsolete {
                            ncd:revise-date 2020-07-21 ;
                          }
                          description 'Configure local IP address.'
                                      ;
                          type ncd:ipv6-address-none-zero ;
                        }
                        leaf remote {
                          status obsolete {
                            ncd:revise-date 2020-07-21 ;
                          }
                          description 'Configure remote IP address.'
                                      ;
                          type ncd:ipv6-address-none-zero ;
                        }
                      }
                    }
                    ncd:revise-date 2019-09-24 ;
                  }
                  choice backup-addr {
                    description 'Configure backup route'
                                ;
                    case backup-ipv4 {
                      description 'Configure backup route IPv4 address'
                                  ;
                      leaf backup {
                        description 'Configure backup route IPv4 address'
                                    ;
                        type ncd:ipv4-address-none-zero ;
                      }
                      ncd:revise-date 2019-07-11 ;
                    }
                    case backup-ipv6 {
                      description 'Configure backup route IPv6 address'
                                  ;
                      leaf backup-addrv6 {
                        description 'Configure backup route IPv6 address'
                                    ;
                        type ncd:ipv6-address-none-zero ;
                      }
                      ncd:revise-date 2019-09-24 ;
                    }
                    ncd:revise-date 2019-07-11 ;
                  }
                  leaf ope-type {
                    description 'Tunnel encapsulation attribute OPE type.'
                                ;
                    type uint16 {
                      range 1..65535 ;
                    }
                    ncd:revise-date 2019-08-26 ;
                  }
                  leaf send-link-bw {
                    description 'Send link bandwidth to this neighbor'
                                ;
                    type enumeration {
                      enum disable {
                        value 0 ;
                        description 'Disable peer send link bandwidth'
                                    ;
                      }
                      enum enable {
                        value 1 ;
                        description 'Enable peer send link bandwidth'
                                    ;
                      }
                      enum inherit {
                        value 2 ;
                        description 'If the neighbor joined a group, the status'
                                  + ' inherited from group.'
                                    ;
                      }
                    }
                    ncd:revise-date 2019-10-22 ;
                  }
                  leaf receive-single-label {
                    description 'Receive single label only for label unicast ro'
                              + 'ute.'
                                ;
                    type enumeration {
                      enum disable {
                        value 0 ;
                        description 'Disable receive single label only for labe'
                                  + 'l unicast route'
                                    ;
                      }
                      enum enable {
                        value 1 ;
                        description 'Enable receive single label only for label'
                                  + ' unicast route'
                                    ;
                      }
                      enum inherit {
                        value 2 ;
                        description 'If the neighbor joined a group, the status'
                                  + ' inherited from group'
                                    ;
                      }
                    }
                    ncd:revise-date 2019-11-29 ;
                  }
                  leaf receive-single-label-compatible {
                    description 'Receive single label only for label unicast ro'
                              + 'ute.The function is the same as receive-single'
                              + '-label node.'
                                ;
                    type enumeration {
                      enum disable {
                        value 0 ;
                        description 'Disable receive single label only for labe'
                                  + 'l unicast route'
                                    ;
                      }
                      enum enable {
                        value 1 ;
                        description 'Enable receive single label only for label'
                                  + ' unicast route'
                                    ;
                      }
                      enum inherit {
                        value 2 ;
                        description 'If the neighbor joined a group, the status'
                                  + ' inherited from group'
                                    ;
                      }
                    }
                    ncd:revise-date 2020-07-28 ;
                  }
                  leaf ignore-error-packet {
                    description 'Ignore error packet for this neighbor.'
                                ;
                    type enumeration {
                      enum disable {
                        value 0 ;
                        description 'Disable peer ignore error packet'
                                    ;
                      }
                      enum enable {
                        value 1 ;
                        description 'Enable peer ignore error packet'
                                    ;
                      }
                      enum inherit {
                        value 2 ;
                        description 'If the neighbor joined a group, the status'
                                  + ' inherited from group.'
                                    ;
                      }
                    }
                    ncd:revise-date 2020-01-13 ;
                  }
                  leaf srv6-l2-service-type {
                    description 'SRv6 L2 service type,,cannot be the same as SR'
                              + 'v6 L3 service.'
                                ;
                    type uint8 {
                      range 5..254 ;
                    }
                    ncd:revise-date 2020-03-02 ;
                  }
                  leaf srv6-l3-service-type {
                    description 'SRv6 L3 service type,cannot be the same as SRv'
                              + '6 L2 service.'
                                ;
                    type uint8 {
                      range 5..254 ;
                    }
                    ncd:revise-date 2020-03-02 ;
                  }
                  container route-server-client {
                    description 'Set route server client only valid for ebgp pe'
                              + 'er.'
                                ;
                    presence route-server-client ;
                    leaf route-svr-client {
                      description 'Set route server client only valid for ebgp '
                                + 'peer.'
                                  ;
                      type empty ;
                      mandatory true ;
                    }
                    ncd:revise-date 2020-04-07 ;
                  }
                  container epe-peer-adj {
                    description 'Configure peer-adj for egress peer engineering.'
                                ;
                    container ipv4-number {
                      description 'Configure IPv4 peer-adj for egress peer engi'
                                + 'neering.'
                                  ;
                      list peer-adj-ipv4 {
                        description 'Configure IPv4 peer-adj for egress peer en'
                                  + 'gineering.'
                                    ;
                        key 'local remote'
                            ;
                        leaf local {
                          description 'Configure local IP address.'
                                      ;
                          type ncd:ipv4-address-none-zero ;
                        }
                        leaf remote {
                          description 'Configure remote IP address.'
                                      ;
                          type ncd:ipv4-address-none-zero ;
                        }
                      }
                    }
                    container ipv6-number {
                      description 'Configure IPv6 peer-adj for egress peer engi'
                                + 'neering.'
                                  ;
                      list peer-adj-ipv6 {
                        description 'Configure IPv6 peer-adj for egress peer en'
                                  + 'gineering.'
                                    ;
                        key 'local remote'
                            ;
                        leaf local {
                          description 'Configure local IP address.'
                                      ;
                          type ncd:ipv6-address-none-zero ;
                        }
                        leaf remote {
                          description 'Configure remote IP address.'
                                      ;
                          type ncd:ipv6-address-none-zero ;
                        }
                      }
                    }
                    ncd:revise-date 2020-07-21 ;
                  }
                }
              }
              container neighbor-uni-ipv6 {
                description 'Specify a IPv6 neighbor.'
                            ;
                list neighbor-uni {
                  description 'Specify a IPv6 neighbor.'
                              ;
                  key ipv6-addr ;
                  leaf ipv6-addr {
                    description 'Neighbor IP address.'
                                ;
                    type ncd:ipv6-address ;
                  }
                  leaf remote-as {
                    description 'Specify a BGP neighbor AS number.'
                                ;
                    type ncd:asn-dot ;
                  }
                  leaf monitor {
                    description 'Config BMP monitor for the address family of t'
                              + 'his neighbor.'
                                ;
                    type enumeration {
                      enum disable {
                        value 2 ;
                      }
                      enum enable {
                        value 1 ;
                      }
                      enum inherit-global-config {
                        value 0 ;
                      }
                    }
                    ncd:revise-date 2019-07-29 ;
                  }
                  leaf join-peergroup {
                    description 'Create/Join a peer group(1-31 characters).'
                                ;
                    type string {
                      length 1..31 ;
                    }
                  }
                  leaf advertisement-interval {
                    description 'Minimum interval between sending BGP routing w'
                              + 'hich is not locally originated updates.'
                                ;
                    type uint32 {
                      range 1..65535 ;
                    }
                    units s ;
                  }
                  leaf description {
                    description 'Neighbor specific description.'
                                ;
                    type ncd:string-with-blank {
                      length 1..80 ;
                    }
                  }
                  leaf originate-interval {
                    description 'Minimum interval between sending BGP routing w'
                              + 'hich is locally originated updates.'
                                ;
                    type uint32 {
                      range 1..65535 ;
                    }
                    units s ;
                  }
                  leaf passive {
                    description "Don't send open messages to this neighbor acti"
                              + "vely."
                                ;
                    type empty ;
                  }
                  leaf shut-down {
                    status obsolete {
                      ncd:revise-date 2016-06-12 ;
                    }
                    description 'Administratively shut down this neighbor.'
                                ;
                    type empty ;
                  }
                  leaf update-source {
                    status obsolete {
                      ncd:revise-date 2018-11-27 ;
                    }
                    description 'Source of routing updates.'
                                ;
                    type ncd:ifname {
                      length 1..31 ;
                    }
                  }
                  leaf connect-retry-interval {
                    description 'Set data of connect-retry timer for this neigh'
                              + 'bor.'
                                ;
                    type uint32 {
                      range 1..65535 ;
                    }
                    units s ;
                  }
                  leaf open-delay {
                    description 'Delay to send open message.'
                                ;
                    type uint32 {
                      range 1..240 ;
                    }
                    units s ;
                  }
                  container fall-over {
                    description 'Set BFD supporting for fallover.'
                                ;
                    presence 'Enable BFD support for fallover'
                             ;
                    leaf bfd {
                      description 'Enable BFD support for fallover.'
                                  ;
                      type empty ;
                      mandatory true ;
                    }
                    container bfd-parameters {
                      description 'The parameters of BFD.'
                                  ;
                      presence bfd-parameters ;
                      choice bfd-parameters {
                        description 'Config bfd parameters'
                                    ;
                        case template-name {
                          description 'Template name'
                                      ;
                          leaf template {
                            description 'BFD template name'
                                        ;
                            type string {
                              length 1..31 ;
                            }
                          }
                          ncd:revise-date 2020-03-31 ;
                        }
                        case parameters {
                          description Parameters ;
                          leaf bfd-interval {
                            description 'Minimum send interval.'
                                        ;
                            type uint32 {
                              range 10..990 ;
                            }
                            units ms ;
                            mandatory true ;
                          }
                          leaf min-rx {
                            description 'Minimum receive interval.'
                                        ;
                            type uint32 {
                              range 10..990 ;
                            }
                            units ms ;
                            mandatory true ;
                          }
                          leaf multiplier {
                            description Multiplier. ;
                            type uint8 {
                              range 3..50 ;
                            }
                            mandatory true ;
                          }
                        }
                      }
                    }
                    leaf bfd-hop {
                      description 'bfd optional hop'
                                  ;
                      type enumeration {
                        enum single-hop {
                          value 1 ;
                          description 'Set single-hop bfd'
                                      ;
                        }
                        enum multi-hop {
                          value 2 ;
                          description 'Set multi-hop bfd'
                                      ;
                        }
                      }
                      ncd:revise-date 2019-04-23 ;
                    }
                  }
                  container set-ttl {
                    description 'ebgp-multihop-ttl and ttl-security-hops are mu'
                              + 'tex.'
                                ;
                    choice set-ttl {
                      description 'ebgp-multihop-ttl and ttl-security-hops are '
                                + 'mutex.'
                                  ;
                      case ebgp-multihop-ttl {
                        description 'Allow EBGP neighbors not on directly conne'
                                  + 'cted net.'
                                    ;
                        leaf ebgp-multihop {
                          description 'Allow EBGP neighbors not on directly con'
                                    + 'nected net.'
                                      ;
                          type uint8 {
                            range 1..255 ;
                          }
                        }
                      }
                      case ttl-security-hops {
                        description 'Enable EBGP TTL security check.'
                                    ;
                        leaf ttl-security-hops {
                          description 'Enable EBGP TTL security check.'
                                      ;
                          type uint8 {
                            range 1..254 ;
                          }
                        }
                      }
                    }
                  }
                  leaf activate {
                    description 'Enable the address family for this neighbor.'
                                ;
                    type enumeration {
                      enum disable {
                        value 0 ;
                      }
                      enum enable {
                        value 1 ;
                      }
                    }
                    ncd:revise-date 2020-07-10 ;
                  }
                  leaf allowas-in {
                    description 'Accept as-path with my AS present in it.'
                                ;
                    type uint32 {
                      range 1..10 {
                        description 'The number of my AS that presented in as-p'
                                  + 'ath.'
                                    ;
                      }
                    }
                    ncd:revise-date 2020-07-10 ;
                  }
                  leaf default-originate {
                    description 'Originate default route to this neighbor.'
                                ;
                    type empty ;
                    ncd:revise-date 2020-07-10 ;
                  }
                  leaf default-originate-routemap {
                    description 'Map external entry attributes into routing tab'
                              + 'le.'
                                ;
                    type string {
                      length 1..200 ;
                    }
                    ncd:revise-date 2020-07-28 ;
                  }
                  leaf default-originate-routepolicy {
                    description 'Set external entry attributes into routing tab'
                              + 'le.'
                                ;
                    type string {
                      length 1..200 ;
                    }
                    ncd:revise-date 2020-10-10 ;
                  }
                  leaf next-hop-self {
                    description 'Disable the next hop calculation for this neig'
                              + 'hbor.'
                                ;
                    type enumeration {
                      enum enable {
                        value 1 ;
                        description 'Apply next-hop-self for EBGP route.'
                                    ;
                      }
                      enum all {
                        value 2 ;
                        description 'Apply next-hop-self for both EBGP and IBGP'
                                  + ' route.'
                                    ;
                      }
                    }
                    ncd:revise-date 2020-07-10 ;
                  }
                  choice nh-unchanged {
                    case next-hop-unchanged {
                      description 'NEXT_HOP of the IBGP path propagated unchang'
                                + 'ed to this neighbor.'
                                  ;
                      leaf next-hop-unchanged {
                        description 'Propagate next hop unchanged for IBGP path'
                                  + 's to this neighbor.'
                                    ;
                        type empty ;
                      }
                    }
                    case next-hop-unchanged-all {
                      description 'NEXT_HOP of either EBGP or IBGP path propaga'
                                + 'ted unchanged to this neighbor.'
                                  ;
                      leaf next-hop-unchanged-all {
                        description 'NEXT_HOP of either EBGP or IBGP path propa'
                                  + 'gated unchanged to this neighbor.'
                                    ;
                        type empty ;
                      }
                    }
                    ncd:revise-date 2020-07-10 ;
                  }
                  leaf advertise-maximum-prefix {
                    description 'Maximum number of prefix send to this peer.'
                                ;
                    type uint32 {
                      range 1..4294967295 ;
                    }
                    ncd:revise-date 2020-07-10 ;
                  }
                  leaf remove-private-as {
                    description 'EBGP use to remove private AS number.'
                                ;
                    type enumeration {
                      enum disable {
                        value 0 ;
                      }
                      enum enable {
                        value 1 ;
                      }
                    }
                    ncd:revise-date 2020-07-10 ;
                  }
                  leaf route-reflector-client {
                    description 'Set this neighbor as a client peer.'
                                ;
                    type empty ;
                    ncd:revise-date 2020-07-10 ;
                  }
                  leaf send-community {
                    description 'Send community to this neighbor.'
                                ;
                    type empty ;
                    ncd:revise-date 2020-07-10 ;
                  }
                  leaf send-large-community {
                    description 'Send Large-community to this neighbor.'
                                ;
                    type empty ;
                    ncd:revise-date 2020-07-10 ;
                  }
                  leaf send-label {
                    description 'Send NLRI with MPLS label to this neighbor.'
                                ;
                    type empty ;
                    ncd:revise-date 2020-07-10 ;
                  }
                  leaf send-med {
                    description 'Send metric attribute to this neighbor.'
                                ;
                    type empty ;
                    ncd:revise-date 2020-07-10 ;
                  }
                  leaf inherit-igp-metric {
                    description 'Med attribute inherited from IGP metric before'
                              + ' sending updates'
                                ;
                    type empty ;
                    ncd:revise-date 2020-07-10 ;
                  }
                  leaf soft-reconfig {
                    description 'Neighbor soft reconfiguration.'
                                ;
                    type enumeration {
                      enum soft-reconfiguration {
                        value 1 ;
                        description Soft-reconfiguration. ;
                      }
                      enum enforce-soft-reconfiguration {
                        value 2 ;
                        description 'Enforce soft-reconfiguration instead of se'
                                  + 'nding route-refresh.'
                                    ;
                      }
                    }
                    ncd:revise-date 2020-07-10 ;
                  }
                  leaf soft-reconfiguration {
                    status obsolete {
                      ncd:revise-date 2020-07-10 ;
                    }
                    description 'Neighbor soft reconfiguration.'
                                ;
                    type empty ;
                    ncd:revise-date 2020-07-10 ;
                  }
                  leaf maxas-in {
                    description 'Accept as-path not exceeded maxas-in.'
                                ;
                    type uint32 {
                      range 1..250 ;
                    }
                    ncd:revise-date 2020-07-10 ;
                  }
                  leaf split-updgrp {
                    description 'Split neighbor from update group.'
                                ;
                    type empty ;
                    ncd:revise-date 2020-07-10 ;
                  }
                  leaf weight {
                    description 'Set weight for routes from this neighbor.'
                                ;
                    type uint32 {
                      range 1..65535 ;
                    }
                    ncd:revise-date 2020-07-10 ;
                  }
                  leaf orf-prefix-filter {
                    description 'Advertise prefixlist ORF capability to this ne'
                              + 'ighbor.'
                                ;
                    type enumeration {
                      enum receive {
                        value 1 ;
                        description 'Capability to receive the ORF from this ne'
                                  + 'ighbor.'
                                    ;
                      }
                      enum send {
                        value 2 ;
                        description 'Capability to send the ORF to this neighbo'
                                  + 'r.'
                                    ;
                      }
                      enum both {
                        value 3 ;
                        description 'Capability to send and receive the ORF.'
                                    ;
                      }
                    }
                    ncd:revise-date 2020-07-10 ;
                  }
                  leaf orf-prefix-filter-cisco {
                    description 'Compatible with CISCO.'
                                ;
                    type empty ;
                    ncd:revise-date 2020-07-10 ;
                  }
                  leaf as-path-loopcheck {
                    description 'Check as-path sending BGP routing to EBGP neig'
                              + 'hbor.'
                                ;
                    type empty ;
                    ncd:revise-date 2020-07-10 ;
                  }
                  leaf aigp {
                    description 'Enable AIGP for this neighbor.'
                                ;
                    type empty ;
                    ncd:revise-date 2020-07-10 ;
                  }
                  container route-server-client {
                    description 'Set route server client only valid for ebgp pe'
                              + 'er.'
                                ;
                    presence route-server-client ;
                    leaf route-svr-client {
                      description 'Set route server client only valid for ebgp '
                                + 'peer.'
                                  ;
                      type empty ;
                      mandatory true ;
                    }
                    ncd:revise-date 2020-07-10 ;
                  }
                  container advertise-map-uni {
                    description 'Specify route-map for conditional advertisemen'
                              + 't.'
                                ;
                    presence 'Specify route-map for conditional advertisement.'
                             ;
                    leaf advertise-map-name {
                      description 'Advertise route-map name.'
                                  ;
                      type string {
                        length 1..200 ;
                      }
                      mandatory true ;
                    }
                    choice advertise-map {
                      description 'Specify route-map for conditional advertisem'
                                + 'ent.'
                                  ;
                      mandatory true ;
                      case exist-map {
                        description 'Advertise prefix only if prefix exists.'
                                    ;
                        leaf exist-map-name {
                          description 'Advertise prefix only if prefix exists.'
                                      ;
                          type string {
                            length 1..200 ;
                          }
                          mandatory true ;
                        }
                      }
                      case nonexist-map {
                        description 'Advertise prefix only if prefix does not e'
                                  + 'xist.'
                                    ;
                        leaf nonexist-map-name {
                          description 'Advertise prefix only if prefix does not'
                                    + ' exist.'
                                      ;
                          type string {
                            length 1..200 ;
                          }
                          mandatory true ;
                        }
                      }
                    }
                    ncd:revise-date 2020-07-10 ;
                  }
                  container route-filter-group {
                    description 'Specify a neighbor to join a route-filter-grou'
                              + 'p.'
                                ;
                    presence route-filter-group ;
                    leaf filter-group {
                      description 'Route filter group name (1-31 characters).'
                                  ;
                      type string {
                        length 1..31 ;
                      }
                      mandatory true ;
                    }
                    leaf next-hop-self {
                      description 'Disable the next hop calculation for this ne'
                                + 'ighbor.'
                                  ;
                      type empty ;
                    }
                    ncd:revise-date 2020-07-10 ;
                  }
                  leaf announce-sid {
                    description 'Enable Prefix-SID attribute for this neighbor.'
                                ;
                    type enumeration {
                      enum enable {
                        value 1 ;
                        description 'Enable Prefix-SID attribute for this neigh'
                                  + 'bor.'
                                    ;
                      }
                    }
                    ncd:revise-date 2020-07-10 ;
                  }
                  leaf send-link-bw {
                    description 'Send link bandwidth to this neighbor'
                                ;
                    type enumeration {
                      enum disable {
                        value 0 ;
                        description 'Disable peer send link bandwidth'
                                    ;
                      }
                      enum enable {
                        value 1 ;
                        description 'Enable peer send link bandwidth'
                                    ;
                      }
                      enum inherit {
                        value 2 ;
                        description 'If the neighbor joined a group, the status'
                                  + ' inherited from group.'
                                    ;
                      }
                    }
                    ncd:revise-date 2020-07-10 ;
                  }
                  container neighbor-extend {
                    description 'Specify a neighbor.'
                                ;
                    container maximum-prefix {
                      description 'The action that generated when threshold val'
                                + 'ue reached.'
                                  ;
                      presence 'The action that generated when threshold value '
                             + 'reached'
                               ;
                      leaf maximum-prefix-threshold {
                        description 'Threshold value(%) at which to generate a '
                                  + 'warning.'
                                    ;
                        type uint32 {
                          range 1..100 ;
                        }
                        mandatory true ;
                      }
                      leaf maximum-prefix-number {
                        description 'Maximum number of prefix limit.'
                                    ;
                        type uint32 {
                          range 1..4294967295 ;
                        }
                        mandatory true ;
                      }
                      choice maximum-prefix-action {
                        description 'The action that generated when threshold v'
                                  + 'alue reached.'
                                    ;
                        mandatory true ;
                        case peer-action {
                          description 'The action that generated when threshold'
                                    + ' value reached.'
                                      ;
                          leaf action {
                            description 'The action that generated when threshold value reached.'
                                        ;
                            type enumeration {
                              enum down {
                                value 0 ;
                                description 'Break down BGP connection after limit is exceeded.'
                                            ;
                              }
                              enum warning-only {
                                value 1 ;
                                description 'Only give warning message when limit is exceeded.'
                                            ;
                                reference 'Only give warning message when limit is exceeded.'
                                          ;
                              }
                              enum drop-routes {
                                value 2 ;
                                description 'Drop routes that exceed the maximum-prefix.'
                                            ;
                              }
                            }
                            mandatory true ;
                          }
                        }
                        case restart {
                          description 'Restart BGP connection after limit is ex'
                                    + 'ceeded.'
                                      ;
                          leaf restart-time {
                            description 'Restart interval in minutes.'
                                        ;
                            type uint32 {
                              range 1..30000 ;
                            }
                            units min ;
                            mandatory true ;
                          }
                        }
                      }
                      ncd:revise-date 2020-07-10 ;
                    }
                    container password {
                      description 'Set a password of the neighbor.'
                                  ;
                      choice password {
                        description 'Set a password of the neighbor.'
                                    ;
                        default encrypted-words ;
                        case clear-words {
                          description 'Specify the clear password (1-80 charact'
                                    + 'ers).'
                                      ;
                          leaf clear-words {
                            description 'The clear password (1-80 characters).'
                                        ;
                            type string {
                              length 1..80 ;
                            }
                          }
                        }
                        case encrypted-words {
                          description 'Specify the encrypted password.'
                                      ;
                          leaf encryped-words {
                            description 'Specify the encrypted password.'
                                        ;
                            type string {
                              length 64..172 ;
                            }
                          }
                        }
                      }
                    }
                    container timers {
                      description 'BGP per neighbor timers.'
                                  ;
                      presence timers ;
                      leaf keepalive-time {
                        description 'Adjust keepalive interval.'
                                    ;
                        type uint32 {
                          range 0..65535 ;
                        }
                        units s ;
                        mandatory true ;
                      }
                      leaf hold-time {
                        description 'Hold time interval.'
                                    ;
                        type uint32 {
                          range '0 | 3..65535'
                                ;
                        }
                        units s ;
                        mandatory true ;
                      }
                    }
                    container local-as {
                      description 'Specify a local-as number.'
                                  ;
                      presence local-as ;
                      leaf as-number {
                        description 'Autonomous system number (normal or 4 Octe'
                                  + 'ts).'
                                    ;
                        type ncd:asn-dot {
                          pattern '-?([1-9]+(\.(\d*)|0)?)|(0(\.\d+){1})'
                                  ;
                        }
                        mandatory true ;
                      }
                      leaf no-prepend {
                        description 'Do not prepend local-as to updates from EB'
                                  + 'GP peer.'
                                    ;
                        type empty ;
                      }
                      leaf replace-as {
                        description 'Replace real AS with local AS in the EBGP '
                                  + 'updates.'
                                    ;
                        type empty ;
                      }
                      leaf dual-as {
                        description 'Accept real AS or local AS from the EBGP p'
                                  + 'eer.'
                                    ;
                        type empty ;
                      }
                    }
                    leaf keychain-name {
                      description 'Keychain name associated to peer for authent'
                                + 'ication.'
                                  ;
                      type string {
                        length 1..31 ;
                      }
                    }
                    container idle-hold-time {
                      description 'Specifiy the length of time the peer is held'
                                + ' in the idle state.'
                                  ;
                      presence idle-hold-time ;
                      leaf hold-time {
                        description 'Idle hold time.'
                                    ;
                        type uint32 {
                          range 1..3000 ;
                        }
                        units s ;
                        mandatory true ;
                      }
                      leaf increase {
                        description 'Increase idle hold time doubly to maximum '
                                  + '3000.'
                                    ;
                        type empty ;
                      }
                      ncd:revise-date 2016-03-23 ;
                    }
                    container cluster-id {
                      description 'Set Route-Reflector cluster-id type.'
                                  ;
                      choice cluster-id {
                        description 'Set Route-Reflector cluster-id type.'
                                    ;
                        case quantity-type {
                          description 'Route-Reflector Cluster-id as 32 bit qua'
                                    + 'ntity.'
                                      ;
                          leaf cluster-id-quantity {
                            description 'Route-Reflector Cluster-id as 32 bit quantity.'
                                        ;
                            type uint32 {
                              range 1..4294967295 ;
                            }
                          }
                        }
                        case address-type {
                          description 'Route-Reflector Cluster-id in IP address'
                                    + ' format.'
                                      ;
                          leaf cluster-id-address {
                            description 'Route-Reflector Cluster-id in IP address format.'
                                        ;
                            type ncd:ipv4-address {
                              pattern '([1-9][0-9]*\.[1-9][0-9]*\.[1-9][0-9]*\.'
                                    + '[1-9][0-9]*)|([1-9][0-9]*\.0\.0\.0)|(0\.'
                                    + '[1-9][0-9]*\.0\.0)|(0\.0\.[1-9][0-9]*\.0'
                                    + ')|(0\.0\.0\.[1-9][0-9]*)|([1-9][0-9]*\.['
                                    + '1-9][0-9]*\.0\.0)|(0\.[1-9][0-9]*\.[1-9]'
                                    + '[0-9]*\.0)|(0\.0\.[1-9][0-9]*\.[1-9][0-9'
                                    + ']*)|([1-9][0-9]*\.0\.0\.[1-9][0-9]*)|(0\.'
                                    + '[1-9][0-9]*\.0\.[1-9][0-9]*)|([1-9][0-9]'
                                    + '*\.0\.[1-9][0-9]*\.0)|([1-9][0-9]*\.[1-9'
                                    + '][0-9]*\.[1-9][0-9]*\.0)|([1-9][0-9]*\.['
                                    + '1-9][0-9]*\.0\.[1-9][0-9]*)|([1-9][0-9]*'
                                    + '\.0\.[1-9][0-9]*\.[1-9][0-9]*)|(0\.[1-9]'
                                    + '[0-9]*\.[1-9][0-9]*\.[1-9][0-9]*)'
                                      ;
                            }
                          }
                        }
                      }
                      ncd:revise-date 2017-10-23 ;
                    }
                    container tracking {
                      description 'Enable peer tracking.'
                                  ;
                      presence tracking ;
                      leaf tracking {
                        status obsolete {
                          ncd:revise-date 2019-01-15 ;
                        }
                        description 'Enable peer tracking.'
                                    ;
                        type empty ;
                        mandatory true ;
                      }
                      leaf tracking-ex {
                        description 'Peer tracking.'
                                    ;
                        type enumeration {
                          enum enable {
                            value 1 ;
                            description 'Enable peer tracking.'
                                        ;
                          }
                          enum disable {
                            value 0 ;
                            description 'Disable peer tracking.'
                                        ;
                          }
                          enum inherit {
                            value 2 ;
                            description 'If the neighbor joined a group, the status of tracking inherited from group.'
                                        ;
                          }
                        }
                        ncd:revise-date 2019-01-15 ;
                      }
                      leaf delay {
                        description 'Delay time to reset the session.'
                                    ;
                        type uint32 {
                          range 1..65535 ;
                        }
                        units s ;
                      }
                      ncd:revise-date 2018-08-29 ;
                    }
                    leaf routemap-in-name {
                      description 'Apply map to incoming routes.'
                                  ;
                      type string {
                        length 1..200 ;
                      }
                      ncd:revise-date 2020-07-10 ;
                    }
                    leaf routemap-out-name {
                      description 'Apply map to outbound routes.'
                                  ;
                      type string {
                        length 1..200 ;
                      }
                      ncd:revise-date 2020-07-10 ;
                    }
                    leaf prefixlist-in-name {
                      description 'Apply  prefix list to incoming routes.'
                                  ;
                      type string {
                        length 1..169 ;
                      }
                      ncd:revise-date 2020-07-10 ;
                    }
                    leaf prefixlist-out-name {
                      description 'Apply  prefix list to outbound routes.'
                                  ;
                      type string {
                        length 1..169 ;
                      }
                      ncd:revise-date 2020-07-10 ;
                    }
                    container diverse-path {
                      description 'Advertise diverse path to this neighbor.'
                                  ;
                      presence diverse-path ;
                      choice diverse-path {
                        description 'Advertise diverse path to this neighbor.'
                                    ;
                        mandatory true ;
                        case backup {
                          description 'Advertisement of the backup path.'
                                      ;
                          leaf backup {
                            description 'Advertisement of the backup path.'
                                        ;
                            type empty ;
                            mandatory true ;
                          }
                        }
                        case multipath {
                          description 'Sequence number of multipath.'
                                      ;
                          leaf sequence-number {
                            description 'Sequence number of multipath.'
                                        ;
                            type uint32 {
                              range 2..32 ;
                            }
                            mandatory true ;
                          }
                        }
                      }
                      leaf route-map {
                        description 'Apply route-map to neighbor.'
                                    ;
                        type string {
                          length 1..200 ;
                        }
                      }
                      ncd:revise-date 2020-07-10 ;
                    }
                    leaf additional-paths-receive {
                      description 'Receive additional paths from this neighbor.'
                                  ;
                      type empty ;
                      ncd:revise-date 2020-07-10 ;
                    }
                    container additional-paths-send {
                      description 'Send additional paths to this neighbor.'
                                  ;
                      choice additional-paths-send {
                        description 'Send additional paths to this neighbor.'
                                    ;
                        default send-one-path ;
                        case send-one-path {
                          description 'Send one additional path to this neighbo'
                                    + 'r.'
                                      ;
                          leaf send {
                            description 'Send additional paths to this neighbor.'
                                        ;
                            type empty ;
                          }
                        }
                        case send-multi-paths {
                          description 'Send additional multi-paths to this neig'
                                    + 'hbor.'
                                      ;
                          leaf paths-number {
                            description 'Number of paths for a prefix.'
                                        ;
                            type uint32 {
                              range 2..32 ;
                            }
                            mandatory true ;
                          }
                          leaf prefixlist {
                            description 'Prefixlist of filtering additional paths.'
                                        ;
                            type string {
                              length 1..169 ;
                            }
                          }
                        }
                      }
                      ncd:revise-date 2020-07-10 ;
                    }
                    leaf routepolicy-in-name {
                      description 'Route policy name applied to the inbound rou'
                                + 'tes.'
                                  ;
                      type string {
                        length 1..200 ;
                      }
                      ncd:revise-date 2020-07-10 ;
                    }
                    leaf routepolicy-out-name {
                      description 'Route policy name applied to the outbound ro'
                                + 'utes.'
                                  ;
                      type string {
                        length 1..200 ;
                      }
                      ncd:revise-date 2020-07-10 ;
                    }
                    container transport {
                      description 'Specify TCP path MTU discovery or TCP MSS to'
                                + ' this neighbor.'
                                  ;
                      choice transport {
                        description 'Specify TCP path MTU discovery or TCP MSS '
                                  + 'to this neighbor.'
                                    ;
                        case path-mtu-discovery {
                          description 'Use transport path MTU discovery.'
                                      ;
                          leaf path-mtu-discovery {
                            description 'Use transport path MTU discovery.'
                                        ;
                            type empty ;
                          }
                        }
                        case mss {
                          description 'Set TCP initial maximum segment size.'
                                      ;
                          leaf mss {
                            description 'Set TCP initial maximum segment size.'
                                        ;
                            type uint32 {
                              range 68..10000 ;
                            }
                          }
                        }
                      }
                      ncd:revise-date 2020-07-10 ;
                    }
                    container withdraw {
                      description 'Withdraw routes when state of track-group is'
                                + ' down.'
                                  ;
                      presence withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                      ncd:revise-date 2020-07-10 ;
                    }
                    container second-withdraw {
                      description 'Withdraw routes when state of the second tra'
                                + 'ck-group is down.'
                                  ;
                      presence second-withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                      ncd:revise-date 2020-07-10 ;
                    }
                    container wait-ctrlr-arp {
                      description 'Route advertisement delay until the controll'
                                + 'er ARP synchronized event is received.'
                                  ;
                      presence wait-controller-arp ;
                      leaf wait-arp {
                        description 'Route advertisement delay until the contro'
                                  + 'ller ARP synchronized event is received.'
                                    ;
                        type empty ;
                        mandatory true ;
                      }
                      leaf route-map {
                        description 'Route-map name applied to waiting for cont'
                                  + 'roller ARP synchronized event.'
                                    ;
                        type string {
                          length 1..200 ;
                        }
                      }
                      ncd:revise-date 2020-07-10 ;
                    }
                    leaf redirect-ipv6-type {
                      description 'Redirect IPv6 type.'
                                  ;
                      type uint16 {
                        range '12 | 2048'
                              ;
                      }
                      ncd:revise-date 2020-10-15 ;
                    }
                    leaf neighbor-stalepath-time {
                      description "Set the max time to hold on to restarting pe"
                                + "er's stalepaths."
                                  ;
                      type uint32 {
                        range 1..604800 {
                          description 'Delay value.'
                                      ;
                        }
                      }
                      units s ;
                      ncd:revise-date 2021-02-01 ;
                    }
                    leaf neighbor-stalepath-time-permanent {
                      description 'Hold on stale paths permanently.'
                                  ;
                      type empty ;
                      ncd:revise-date 2021-02-01 ;
                    }
                  }
                  leaf nouse-peergroup-config {
                    description 'Peer do not use group config set.Only for get '
                              + 'operation.'
                                ;
                    type empty ;
                  }
                  leaf dscp {
                    description 'Set DSCP value.'
                                ;
                    type uint8 {
                      range 0..63 ;
                    }
                  }
                  container shutdown {
                    description 'Shut down this neighbor administratively or wh'
                              + 'en state of track-group is down.'
                                ;
                    presence shut-down ;
                    leaf shut-down {
                      description 'Administratively shut down this neighbor.'
                                  ;
                      type empty ;
                      mandatory true ;
                    }
                    leaf track-group {
                      description 'Shut down this neighbor when state of track-'
                                + 'group is down.'
                                  ;
                      type string {
                        length 1..31 ;
                      }
                    }
                    ncd:revise-date 2016-06-12 ;
                  }
                  leaf enforce-first-as-disable {
                    description 'Not enforce the first AS for EBGP neighbor rou'
                              + 'tes'
                                ;
                    type empty ;
                    ncd:revise-date 2018-01-10 ;
                  }
                  leaf enhanced-route-refresh-disable {
                    description 'Enhanced route refresh capability.'
                                ;
                    type empty ;
                    ncd:revise-date 2018-10-23 ;
                  }
                  container update-source-ex {
                    description 'Specify the update-source configuration of the'
                              + ' neighbor.'
                                ;
                    presence 'Specify the update-source configuration of the ne'
                           + 'ighbor.'
                             ;
                    choice update-source {
                      description 'Specify the update-source configuration of t'
                                + 'he neighbor.'
                                  ;
                      case update-source-if {
                        description 'Specify the update-source interface name o'
                                  + 'f the neighbor.'
                                    ;
                        leaf update-source-ifname {
                          description 'Specify the update-source interface name'
                                    + ' of the neighbor.'
                                      ;
                          type ncd:ifname ;
                        }
                      }
                      case update-source-ipv4 {
                        description 'Specify the update-source IPv4 address of '
                                  + 'the neighbor.'
                                    ;
                        leaf update-source-addrv4 {
                          description 'Specify the update-source IPv4 address o'
                                    + 'f the neighbor.'
                                      ;
                          type ncd:ipv4-address-none-zero ;
                        }
                      }
                      case update-source-ipv6 {
                        description 'Specify the update-source IPv6 address of '
                                  + 'the neighbor.'
                                    ;
                        leaf update-source-addrv6 {
                          description 'Specify the update-source IPv6 address o'
                                    + 'f the neighbor.'
                                      ;
                          type ncd:ipv6-address-none-zero ;
                        }
                        ncd:revise-date 2019-07-07 ;
                      }
                    }
                    ncd:revise-date 2018-11-27 ;
                  }
                  leaf four-byte-as-disable {
                    description 'Disable 4-byte AS capability.'
                                ;
                    type empty ;
                    ncd:revise-date 2019-01-15 ;
                  }
                  leaf sr-epe {
                    description 'Configure neighbor egress peer engineering'
                                ;
                    type link-state ;
                    default null ;
                    ncd:revise-date 2019-07-11 ;
                  }
                  leaf sr-epe-peer-set {
                    description 'Configure peer set for egress peer engineering.'
                                ;
                    type string {
                      length 1..31 ;
                    }
                    ncd:revise-date 2019-09-24 ;
                  }
                  container sr-epe-peer-adj {
                    status obsolete {
                      ncd:revise-date 2020-07-21 ;
                    }
                    description 'Configure peer-adj for egress peer engineering.'
                                ;
                    container ipv4-number {
                      status obsolete {
                        ncd:revise-date 2020-07-21 ;
                      }
                      description 'Configure IPv4 peer-adj for egress peer engi'
                                + 'neering.'
                                  ;
                      list peer-adj-ipv4 {
                        status obsolete {
                          ncd:revise-date 2020-07-21 ;
                        }
                        description 'Configure IPv4 peer-adj for egress peer en'
                                  + 'gineering.'
                                    ;
                        key 'local remote'
                            ;
                        leaf local {
                          status obsolete {
                            ncd:revise-date 2020-07-21 ;
                          }
                          description 'Configure local IP address.'
                                      ;
                          type ncd:ipv4-address-none-zero ;
                        }
                        leaf remote {
                          status obsolete {
                            ncd:revise-date 2020-07-21 ;
                          }
                          description 'Configure remote IP address.'
                                      ;
                          type ncd:ipv4-address-none-zero ;
                        }
                      }
                    }
                    container ipv6-number {
                      status obsolete {
                        ncd:revise-date 2020-07-21 ;
                      }
                      description 'Configure IPv6 peer-adj for egress peer engi'
                                + 'neering.'
                                  ;
                      list peer-adj-ipv6 {
                        status obsolete {
                          ncd:revise-date 2020-07-21 ;
                        }
                        description 'Configure IPv6 peer-adj for egress peer en'
                                  + 'gineering.'
                                    ;
                        key 'local remote'
                            ;
                        leaf local {
                          status obsolete {
                            ncd:revise-date 2020-07-21 ;
                          }
                          description 'Configure local IP address.'
                                      ;
                          type ncd:ipv6-address-none-zero ;
                        }
                        leaf remote {
                          status obsolete {
                            ncd:revise-date 2020-07-21 ;
                          }
                          description 'Configure remote IP address.'
                                      ;
                          type ncd:ipv6-address-none-zero ;
                        }
                      }
                    }
                    ncd:revise-date 2019-09-24 ;
                  }
                  choice backup-addr {
                    description 'Configure backup route'
                                ;
                    case backup-ipv4 {
                      description 'Configure backup route IPv4 address'
                                  ;
                      leaf backup {
                        description 'Configure backup route IPv4 address'
                                    ;
                        type ncd:ipv4-address-none-zero ;
                      }
                      ncd:revise-date 2019-07-11 ;
                    }
                    case backup-ipv6 {
                      description 'Configure backup route IPv6 address'
                                  ;
                      leaf backup-addrv6 {
                        description 'Configure backup route IPv6 address'
                                    ;
                        type ncd:ipv6-address-none-zero ;
                      }
                      ncd:revise-date 2019-09-24 ;
                    }
                    ncd:revise-date 2019-07-11 ;
                  }
                  leaf ope-type {
                    description 'Tunnel encapsulation attribute OPE type.'
                                ;
                    type uint16 {
                      range 1..65535 ;
                    }
                    ncd:revise-date 2019-08-26 ;
                  }
                  leaf receive-single-label {
                    description 'Receive single label only for label unicast ro'
                              + 'ute.'
                                ;
                    type enumeration {
                      enum disable {
                        value 0 ;
                        description 'Disable receive single label only for labe'
                                  + 'l unicast route'
                                    ;
                      }
                      enum enable {
                        value 1 ;
                        description 'Enable receive single label only for label'
                                  + ' unicast route'
                                    ;
                      }
                      enum inherit {
                        value 2 ;
                        description 'If the neighbor joined a group, the status'
                                  + ' inherited from group'
                                    ;
                      }
                    }
                    ncd:revise-date 2019-11-29 ;
                  }
                  leaf receive-single-label-compatible {
                    description 'Receive single label only for label unicast ro'
                              + 'ute.The function is the same as receive-single'
                              + '-label node.'
                                ;
                    type enumeration {
                      enum disable {
                        value 0 ;
                        description 'Disable receive single label only for labe'
                                  + 'l unicast route'
                                    ;
                      }
                      enum enable {
                        value 1 ;
                        description 'Enable receive single label only for label'
                                  + ' unicast route'
                                    ;
                      }
                      enum inherit {
                        value 2 ;
                        description 'If the neighbor joined a group, the status'
                                  + ' inherited from group'
                                    ;
                      }
                    }
                    ncd:revise-date 2020-07-28 ;
                  }
                  leaf ignore-error-packet {
                    description 'Ignore error packet for this neighbor.'
                                ;
                    type enumeration {
                      enum disable {
                        value 0 ;
                        description 'Disable peer ignore error packet'
                                    ;
                      }
                      enum enable {
                        value 1 ;
                        description 'Enable peer ignore error packet'
                                    ;
                      }
                      enum inherit {
                        value 2 ;
                        description 'If the neighbor joined a group, the status'
                                  + ' inherited from group.'
                                    ;
                      }
                    }
                    ncd:revise-date 2020-01-13 ;
                  }
                  leaf srv6-l2-service-type {
                    description 'SRv6 L2 service type,,cannot be the same as SR'
                              + 'v6 L3 service.'
                                ;
                    type uint8 {
                      range 5..254 ;
                    }
                    ncd:revise-date 2020-03-02 ;
                  }
                  leaf srv6-l3-service-type {
                    description 'SRv6 L3 service type,,cannot be the same as SR'
                              + 'v6 L2 service.'
                                ;
                    type uint8 {
                      range 5..254 ;
                    }
                    ncd:revise-date 2020-03-02 ;
                  }
                  container srv6-epe {
                    description 'SRv6 BGP EPE peer node SID'
                                ;
                    choice srv6-epe-peer-node {
                      description 'SRv6 BGP EPE peer node SID'
                                  ;
                      case srv6-epe-auto {
                        status obsolete {
                          ncd:revise-date 2020-06-29 ;
                        }
                        description 'Automatic generation of SRv6 peer node SID.'
                                    ;
                        container srv6-epe-auto-peernode {
                          status obsolete {
                            ncd:revise-date 2020-06-29 ;
                          }
                          description 'Automatic generation of SRv6 peer node S'
                                    + 'ID'
                                      ;
                          leaf auto {
                            status obsolete {
                              ncd:revise-date 2020-06-29 ;
                            }
                            description 'Automatic generation of SRv6 peer node SID.'
                                        ;
                            type enumeration {
                              enum auto {
                                value 1 ;
                                description 'Automatic generation of SRv6 peer node SID'
                                            ;
                              }
                            }
                          }
                        }
                      }
                      case srv6-epe-static {
                        description 'Specify a SRv6 peer node SID.'
                                    ;
                        container srv6-epe-static-peernode {
                          description 'Specify a SRv6 peer node SID.'
                                      ;
                          leaf sid {
                            description 'SRv6 peer node SID.'
                                        ;
                            type ncd:ipv6-address ;
                          }
                        }
                      }
                      case srv6-epe-dyn {
                        description 'Automatic generation of SRv6 peer node SID.'
                                    ;
                        container srv6-epe-dyn-peernode {
                          description 'Automatic generation of SRv6 peer node S'
                                    + 'ID.'
                                      ;
                          leaf auto {
                            description 'Automatic generation of SRv6 peer node SID.'
                                        ;
                            type enumeration {
                              enum auto {
                                value 1 ;
                                description 'Automatic generation of SRv6 peer node SID.'
                                            ;
                              }
                            }
                          }
                        }
                        ncd:revise-date 2020-11-11 ;
                      }
                    }
                    ncd:revise-date 2020-05-11 ;
                  }
                  container srv6-epe-peer-adj {
                    description 'Configure peer-adj for SRv6 egress peer engine'
                              + 'ering.'
                                ;
                    container ipv6-number {
                      description 'Configure IPv6 peer-adj for SRv6 egress peer'
                                + ' engineering.'
                                  ;
                      list peer-adj-ipv6 {
                        description 'Configure IPv6 peer-adj for egress peer en'
                                  + 'gineering.'
                                    ;
                        key 'local remote'
                            ;
                        leaf local {
                          description 'Configure local IP address.'
                                      ;
                          type ncd:ipv6-address-none-zero ;
                        }
                        leaf remote {
                          description 'Configure remote IP address.'
                                      ;
                          type ncd:ipv6-address-none-zero ;
                        }
                        container srv6-sid {
                          description 'Configure SRv6 EPE peer adjacency SID.'
                                      ;
                          choice srv6-epe-peeradj-sid {
                            description 'SRv6 BGP EPE peer adjacency SID'
                                        ;
                            case srv6-epe-auto {
                              status obsolete {
                                ncd:revise-date 2020-06-29 ;
                              }
                              description 'Automatic generation of SRv6 peer node SID.'
                                          ;
                              container srv6-epe-auto-peeradj {
                                status obsolete {
                                  ncd:revise-date 2020-06-29 ;
                                }
                                description 'Automatic generation of SRv6 peer adjacency SID'
                                            ;
                                leaf auto {
                                  status obsolete {
                                    ncd:revise-date 2020-06-29 ;
                                  }
                                  description 'Automatic generation of SRv6 peer adjacency SID.'
                                              ;
                                  type enumeration {
                                    enum auto {
                                      value 1 ;
                                      description 'Automatic generation of SRv6 peer node SID'
                                                  ;
                                    }
                                  }
                                }
                              }
                            }
                            case srv6-epe-static {
                              description 'Specify a SRv6 peer adjacency SID.'
                                          ;
                              container srv6-epe-static-peeradj {
                                description 'Specify a SRv6 peer adjacency SID.'
                                            ;
                                leaf sid {
                                  description 'SRv6 peer adjacency SID.'
                                              ;
                                  type ncd:ipv6-address ;
                                }
                              }
                            }
                            case srv6-epe-dyn {
                              description 'Automatic generation of SRv6 peer adjacency SID'
                                          ;
                              container srv6-epe-dyn-peeradj {
                                description 'Automatic generation of SRv6 peer adjacency SID'
                                            ;
                                leaf auto {
                                  description 'Automatic generation of SRv6 peer adjacency SID'
                                              ;
                                  type enumeration {
                                    enum auto {
                                      value 1 ;
                                      description 'Automatic generation of SRv6 peer adjacency SID'
                                                  ;
                                    }
                                  }
                                }
                              }
                              ncd:revise-date 2020-11-11 ;
                            }
                          }
                        }
                      }
                    }
                    ncd:revise-date 2020-05-11 ;
                  }
                  container epe-peer-adj {
                    description 'Configure peer-adj for egress peer engineering.'
                                ;
                    container ipv4-number {
                      description 'Configure IPv4 peer-adj for egress peer engi'
                                + 'neering.'
                                  ;
                      list peer-adj-ipv4 {
                        description 'Configure IPv4 peer-adj for egress peer en'
                                  + 'gineering.'
                                    ;
                        key 'local remote'
                            ;
                        leaf local {
                          description 'Configure local IP address.'
                                      ;
                          type ncd:ipv4-address-none-zero ;
                        }
                        leaf remote {
                          description 'Configure remote IP address.'
                                      ;
                          type ncd:ipv4-address-none-zero ;
                        }
                      }
                    }
                    container ipv6-number {
                      description 'Configure IPv6 peer-adj for egress peer engi'
                                + 'neering.'
                                  ;
                      list peer-adj-ipv6 {
                        description 'Configure IPv6 peer-adj for egress peer en'
                                  + 'gineering.'
                                    ;
                        key 'local remote'
                            ;
                        leaf local {
                          description 'Configure local IP address.'
                                      ;
                          type ncd:ipv6-address-none-zero ;
                        }
                        leaf remote {
                          description 'Configure remote IP address.'
                                      ;
                          type ncd:ipv6-address-none-zero ;
                        }
                      }
                    }
                    ncd:revise-date 2020-07-21 ;
                  }
                }
                ncd:revise-date 2016-01-06 ;
              }
            }
            leaf table-policy {
              description 'Set external entry attributes into routing table.'
                          ;
              type string {
                length 1..200 ;
              }
              ncd:revise-date 2015-05-18 ;
            }
            container route-scan-time {
              description 'Adjust BGP route scan.'
                          ;
              presence 'The ability of BGP route scan.'
                       ;
              leaf interval-wait {
                description 'The interval of scan waiting. Default value is 500.'
                            ;
                type uint32 {
                  range 1..65535 ;
                }
                units ms ;
                mandatory true ;
              }
              leaf Initial {
                description 'The initialization time of scan. Default value is '
                          + '50.'
                            ;
                type uint32 {
                  range 1..65535 ;
                }
                units ms ;
                mandatory true ;
              }
              leaf max-wait {
                description 'The max waiting time of scan. Default value is 500'
                          + '0.'
                            ;
                type uint32 {
                  range 1..65535 ;
                }
                units ms ;
                mandatory true ;
              }
              ncd:revise-date 2015-11-20 ;
            }
            container additional-paths {
              description 'Additional paths in the BGP table.'
                          ;
              leaf selection-route-map {
                description 'Selection criteria to pick the additional paths.'
                            ;
                type string {
                  length 1..200 ;
                }
              }
              ncd:revise-date 2016-01-06 ;
            }
            leaf urpf-id-download {
              if-feature urpf ;
              description 'Download URPF-ID information to RTM.'
                          ;
              type empty ;
              ncd:revise-date 2017-11-16 ;
            }
            container group-to-group {
              description 'Configure filter group to filter group route reflect'
                        + 'ion.'
                          ;
              presence group-to-group ;
              leaf reflection {
                description 'Reflection of routes is allowed.'
                            ;
                type empty ;
                mandatory true ;
              }
              leaf next-hop-self {
                description 'Disable the next hop calculation.'
                            ;
                type empty ;
              }
              ncd:revise-date 2018-08-04 ;
            }
            leaf default-set-mpls-label {
              description 'Set MPLS label for local route.'
                          ;
              type empty ;
              ncd:revise-date 2018-09-03 ;
            }
            leaf ebgp-interface-sensitive {
              description 'Enable or disable interface sensitive for EBGP neigh'
                        + 'bor.'
                          ;
              type enumeration {
                enum disable {
                  value 0 ;
                }
                enum enable {
                  value 1 ;
                }
              }
              default enable ;
              ncd:revise-date 2018-12-11 ;
            }
            leaf entropy-label {
              description 'entropy-label enable or disable'
                          ;
              type enumeration {
                enum disable {
                  value 0 ;
                }
                enum enable {
                  value 1 ;
                }
              }
              ncd:revise-date 2019-02-21 ;
            }
            leaf additional-paths-send-igp-path {
              description 'Send neighbor NLRI with igp-path of additional-paths.'
                          ;
              type empty ;
              ncd:revise-date 2019-07-01 ;
            }
            leaf additional-paths-different-color {
              description 'Set different colors of additional-paths.'
                          ;
              type empty ;
              ncd:revise-date 2019-07-01 ;
            }
            leaf link-bandwidth-download {
              description 'Download link-bandwidth information to RTM.'
                          ;
              type empty ;
              ncd:revise-date 2019-10-22 ;
            }
            leaf sr-lsr {
              description 'Enable or disable BGP segment routing lable switch r'
                        + 'outer'
                          ;
              type enumeration {
                enum disable {
                  value 0 ;
                }
                enum enable {
                  value 1 ;
                }
              }
              default disable ;
              ncd:revise-date 2020-02-13 ;
            }
            leaf slow-peer-detection {
              description 'Set slow peer detection.'
                          ;
              type enumeration {
                enum disable {
                  value 0 ;
                  description 'Disable slow peer detection'
                              ;
                }
                enum enable {
                  value 1 ;
                  description 'Enable slow peer detection'
                              ;
                }
              }
              default disable ;
              ncd:revise-date 2020-09-08 ;
            }
            leaf slow-peer-detection-threshold {
              description 'Set threshold time for slow peer.Default value is 30'
                        + '0.'
                          ;
              type uint32 {
                range 120..3600 {
                  description 'Threshold time range.'
                              ;
                }
              }
              units s ;
              default 300 ;
              ncd:revise-date 2020-09-08 ;
            }
            leaf slow-peer-detection-recover {
              description 'Set recover time for slow peer.Default value is 300.'
                          ;
              type uint32 {
                range 120..3600 {
                  description 'Recover time range.'
                              ;
                }
              }
              units s ;
              default 300 ;
              ncd:revise-date 2020-09-08 ;
            }
            leaf download-community {
              description 'The maximum number of communities for one route.'
                          ;
              type uint8 {
                range 1..255 ;
              }
              ncd:revise-date 2020-10-10 ;
            }
            leaf nexthop-recursive-lookup-srv6-sid {
              description 'Enable or disable bgp nexthop recursive-lookup srv6-'
                        + 'sid'
                          ;
              type enumeration {
                enum disable {
                  value 0 ;
                }
                enum enable {
                  value 1 ;
                }
              }
              default disable ;
              ncd:revise-date 2020-10-28 ;
            }
            leaf bestpath-rpki-validation {
              description 'Compare RPKI state in bestpath selection.'
                          ;
              type empty ;
              ncd:revise-date 2020-12-20 ;
            }
          }
          container address-family-vpls {
            description 'Configuration in address family L2VPN VPLS mode.'
                        ;
            presence 'L2VPN VPLS address family.'
                     ;
            container neighbor-group {
              description 'Specify a peergroup neighbor.'
                          ;
              list neighbor-vpls-peergroup {
                description 'Specify a peergroup neighbor.'
                            ;
                key neighbor-group ;
                leaf neighbor-group {
                  description 'Peer group name (1-31 characters).'
                              ;
                  type string {
                    length 1..31 ;
                  }
                }
                leaf activate {
                  description 'Enable the address family for this neighbor.'
                              ;
                  type enumeration {
                    enum disable {
                      value 0 ;
                    }
                    enum enable {
                      value 1 ;
                    }
                  }
                }
                leaf allowas-in {
                  description 'Accept as-path with my AS present in it.'
                              ;
                  type uint32 {
                    range 1..10 ;
                  }
                }
                leaf as-path-loopcheck {
                  description 'Check as-path sending BGP routing to EBGP neighb'
                            + 'or.'
                              ;
                  type empty ;
                }
                leaf next-hop-self {
                  description 'Disable the next hop calculation for this neighb'
                            + 'or.'
                              ;
                  type enumeration {
                    enum enable {
                      value 1 ;
                      description 'Apply next-hop-self for EBGP route.'
                                  ;
                    }
                    enum all {
                      value 2 ;
                      description 'Apply next-hop-self for both EBGP and IBGP r'
                                + 'oute.'
                                  ;
                    }
                  }
                }
                choice nh-unchanged {
                  case next-hop-unchanged {
                    description 'NEXT_HOP of the IBGP path propagated unchanged'
                              + ' to this neighbor.'
                                ;
                    leaf next-hop-unchanged {
                      description 'Propagate next hop unchanged for IBGP paths '
                                + 'to this neighbor.'
                                  ;
                      type empty ;
                    }
                  }
                  case next-hop-unchanged-all {
                    description 'NEXT_HOP of either EBGP or IBGP path propagate'
                              + 'd unchanged to this neighbor.'
                                ;
                    leaf next-hop-unchanged-all {
                      description 'NEXT_HOP of either EBGP or IBGP path propaga'
                                + 'ted unchanged to this neighbor.'
                                  ;
                      type empty ;
                    }
                    ncd:revise-date 2020-04-07 ;
                  }
                }
                leaf nlri-type {
                  description 'Set NLRI type of routes for this neighbor.'
                              ;
                  type enumeration {
                    enum martini-only {
                      value 1 ;
                    }
                    enum kompella-only {
                      value 2 ;
                    }
                  }
                }
                leaf remove-private-as {
                  description 'EBGP use to remove private AS number.'
                              ;
                  type enumeration {
                    enum disable {
                      value 0 ;
                    }
                    enum enable {
                      value 1 ;
                    }
                  }
                }
                leaf route-reflector-client {
                  description 'Set this neighbor as a client peer.'
                              ;
                  type empty ;
                }
                leaf send-community {
                  description 'Send community to this neighbor.'
                              ;
                  type empty ;
                }
                leaf send-large-community {
                  description 'Send Large-community to this neighbor.'
                              ;
                  type empty ;
                  ncd:revise-date 2020-04-16 ;
                }
                leaf send-med {
                  description 'Send metric attribute to this neighbor.'
                              ;
                  type empty ;
                }
                leaf weight {
                  description 'Set weight for routes from this neighbor.'
                              ;
                  type uint32 {
                    range 1..65535 ;
                  }
                }
                container neighbor-extend {
                  description 'Specify a neighbor.'
                              ;
                  leaf route-map-in-name {
                    description 'Apply route-map to incoming routes.'
                                ;
                    type string {
                      length 1..200 ;
                    }
                  }
                  leaf route-map-out-name {
                    description 'Apply route-map to outbound routes.'
                                ;
                    type string {
                      length 1..200 ;
                    }
                  }
                  container maximum-prefix {
                    description 'The action that generated when threshold value'
                              + ' reached.'
                                ;
                    presence 'The action that generated when threshold value re'
                           + 'ached'
                             ;
                    leaf maximum-prefix-number {
                      description 'Maximum number of prefix limit.'
                                  ;
                      type uint32 {
                        range 1..4294967295 ;
                      }
                      mandatory true ;
                    }
                    leaf maximum-prefix-threshold {
                      description 'Threshold value(%) at which to generate a wa'
                                + 'rning.'
                                  ;
                      type uint32 {
                        range 1..100 ;
                      }
                      mandatory true ;
                    }
                    choice maximum-prefix-action {
                      description 'The action that generated when threshold val'
                                + 'ue reached.'
                                  ;
                      mandatory true ;
                      case peer-action {
                        description 'The action that generated when threshold v'
                                  + 'alue reached.'
                                    ;
                        leaf action {
                          description 'The action that generated when threshold'
                                    + ' value reached.'
                                      ;
                          type enumeration {
                            enum down {
                              value 0 ;
                              description 'Break down BGP connection after limit is exceeded.'
                                          ;
                            }
                            enum warning-only {
                              value 1 ;
                              description 'Only give warning message when limit is exceeded.'
                                          ;
                            }
                            enum drop-route {
                              value 2 ;
                              description 'Drop routes that exceed the maximum-prefix.'
                                          ;
                            }
                          }
                          mandatory true ;
                        }
                      }
                      case restart {
                        description 'Restart BGP connection after limit is exce'
                                  + 'eded.'
                                    ;
                        leaf restart-time {
                          description 'Restart interval in minutes.'
                                      ;
                          type uint32 {
                            range 1..30000 ;
                          }
                          mandatory true ;
                        }
                      }
                    }
                  }
                  leaf routepolicy-in-name {
                    description 'Route policy name applied to the inbound route'
                              + 's.'
                                ;
                    type string {
                      length 1..200 ;
                    }
                    ncd:revise-date 2015-05-18 ;
                  }
                  leaf routepolicy-out-name {
                    description 'Route policy name applied to the outbound rout'
                              + 'es.'
                                ;
                    type string {
                      length 1..200 ;
                    }
                    ncd:revise-date 2015-05-18 ;
                  }
                }
              }
            }
            container neighbor-ipv4 {
              description 'Specify a IPv4 neighbor.'
                          ;
              list neighbor-vpls {
                description 'Specify a IPv4 neighbor.'
                            ;
                key ipv4-address ;
                leaf ipv4-address {
                  description 'Neighbor IPv4 address.'
                              ;
                  type ncd:ipv4-address ;
                }
                leaf joined-group {
                  description 'Only for read operation. The joined group name.'
                              ;
                  type string {
                    length 1..31 ;
                  }
                  ncd:revise-date 2016-05-16 ;
                }
                leaf activate {
                  description 'Enable the address family for this neighbor.'
                              ;
                  type enumeration {
                    enum disable {
                      value 0 ;
                    }
                    enum enable {
                      value 1 ;
                    }
                  }
                }
                leaf allowas-in {
                  description 'Accept as-path with my AS present in it.'
                              ;
                  type uint32 {
                    range 1..10 ;
                  }
                }
                leaf as-path-loopcheck {
                  description 'Check as-path sending BGP routing to EBGP neighb'
                            + 'or.'
                              ;
                  type empty ;
                }
                leaf next-hop-self {
                  description 'Disable the next hop calculation for this neighb'
                            + 'or.'
                              ;
                  type enumeration {
                    enum enable {
                      value 1 ;
                      description 'Apply next-hop-self for EBGP route.'
                                  ;
                    }
                    enum all {
                      value 2 ;
                      description 'Apply next-hop-self for both EBGP and IBGP r'
                                + 'oute.'
                                  ;
                    }
                  }
                }
                choice nh-unchanged {
                  case next-hop-unchanged {
                    description 'NEXT_HOP of the IBGP path propagated unchanged'
                              + ' to this neighbor.'
                                ;
                    leaf next-hop-unchanged {
                      description 'Propagate next hop unchanged for IBGP paths '
                                + 'to this neighbor.'
                                  ;
                      type empty ;
                    }
                  }
                  case next-hop-unchanged-all {
                    description 'NEXT_HOP of either EBGP or IBGP path propagate'
                              + 'd unchanged to this neighbor.'
                                ;
                    leaf next-hop-unchanged-all {
                      description 'NEXT_HOP of either EBGP or IBGP path propaga'
                                + 'ted unchanged to this neighbor.'
                                  ;
                      type empty ;
                    }
                    ncd:revise-date 2020-04-07 ;
                  }
                }
                leaf nlri-type {
                  description 'Set NLRI type of routes for this neighbor.'
                              ;
                  type enumeration {
                    enum martini-only {
                      value 1 ;
                    }
                    enum kompella-only {
                      value 2 ;
                    }
                  }
                }
                leaf remove-private-as {
                  description 'EBGP use to remove private AS number.'
                              ;
                  type enumeration {
                    enum disable {
                      value 0 ;
                    }
                    enum enable {
                      value 1 ;
                    }
                  }
                }
                leaf route-reflector-client {
                  description 'Set this neighbor as a client peer.'
                              ;
                  type empty ;
                }
                leaf send-community {
                  description 'Send community to this neighbor.'
                              ;
                  type empty ;
                }
                leaf send-large-community {
                  description 'Send Large-community to this neighbor.'
                              ;
                  type empty ;
                  ncd:revise-date 2020-04-16 ;
                }
                leaf send-med {
                  description 'Send metric attribute to this neighbor.'
                              ;
                  type empty ;
                }
                leaf weight {
                  description 'Set weight for routes from this neighbor.'
                              ;
                  type uint32 {
                    range 1..65535 ;
                  }
                }
                container neighbor-extend {
                  description 'Specify a neighbor.'
                              ;
                  leaf route-map-in-name {
                    description 'Apply route-map to incoming routes.'
                                ;
                    type string {
                      length 1..200 ;
                    }
                  }
                  leaf route-map-out-name {
                    description 'Apply route-map to outbound routes.'
                                ;
                    type string {
                      length 1..200 ;
                    }
                  }
                  container maximum-prefix {
                    description 'The action that generated when threshold value'
                              + ' reached.'
                                ;
                    presence 'The action that generated when threshold value re'
                           + 'ached'
                             ;
                    leaf maximum-prefix-number {
                      description 'Maximum number of prefix limit.'
                                  ;
                      type uint32 {
                        range 1..4294967295 ;
                      }
                      mandatory true ;
                    }
                    leaf maximum-prefix-threshold {
                      description 'Threshold value(%) at which to generate a wa'
                                + 'rning.'
                                  ;
                      type uint32 {
                        range 1..100 ;
                      }
                      mandatory true ;
                    }
                    choice maximum-prefix-action {
                      description 'The action that generated when threshold val'
                                + 'ue reached.'
                                  ;
                      mandatory true ;
                      case peer-action {
                        description 'The action that generated when threshold v'
                                  + 'alue reached.'
                                    ;
                        leaf action {
                          description 'The action that generated when threshold'
                                    + ' value reached.'
                                      ;
                          type enumeration {
                            enum down {
                              value 0 ;
                              description 'Break down BGP connection after limit is exceeded.'
                                          ;
                            }
                            enum warning-only {
                              value 1 ;
                              description 'Only give warning message when limit is exceeded.'
                                          ;
                            }
                            enum drop-route {
                              value 2 ;
                              description 'Drop routes that exceed the maximum-prefix.'
                                          ;
                            }
                          }
                          mandatory true ;
                        }
                      }
                      case restart {
                        description 'Restart BGP connection after limit is exce'
                                  + 'eded.'
                                    ;
                        leaf restart-time {
                          description 'Restart interval in minutes.'
                                      ;
                          type uint32 {
                            range 1..30000 ;
                          }
                          mandatory true ;
                        }
                      }
                    }
                  }
                  leaf routepolicy-in-name {
                    description 'Route policy name applied to the inbound route'
                              + 's.'
                                ;
                    type string {
                      length 1..200 ;
                    }
                    ncd:revise-date 2015-05-18 ;
                  }
                  leaf routepolicy-out-name {
                    description 'Route policy name applied to the outbound rout'
                              + 'es.'
                                ;
                    type string {
                      length 1..200 ;
                    }
                    ncd:revise-date 2015-05-18 ;
                  }
                }
                leaf nouse-peergroup-config {
                  status obsolete {
                    ncd:revise-date 2015-05-18 ;
                  }
                  description 'Peer do not use group config set.Only for get op'
                            + 'eration.'
                              ;
                  type empty ;
                }
              }
            }
            container neighbor-ipv6 {
              description 'Specify a IPv6 neighbor.'
                          ;
              list neighbor-ipv6-vpls {
                description 'Specify a IPv6 neighbor.'
                            ;
                key ipv6-addr ;
                leaf ipv6-addr {
                  description 'Neighbor IPv6 address.'
                              ;
                  type ncd:ipv6-address ;
                }
                leaf joined-group {
                  description 'Only for read operation. The joined group name.'
                              ;
                  type string {
                    length 1..31 ;
                  }
                }
                leaf activate {
                  description 'Enable the address family for this neighbor.'
                              ;
                  type enumeration {
                    enum disable {
                      value 0 ;
                    }
                    enum enable {
                      value 1 ;
                    }
                  }
                }
                leaf allowas-in {
                  description 'Accept as-path with my AS present in it.'
                              ;
                  type uint32 {
                    range 1..10 ;
                  }
                }
                leaf as-path-loopcheck {
                  description 'Check as-path sending BGP routing to EBGP neighb'
                            + 'or.'
                              ;
                  type empty ;
                }
                leaf next-hop-self {
                  description 'Disable the next hop calculation for this neighb'
                            + 'or.'
                              ;
                  type enumeration {
                    enum enable {
                      value 1 ;
                      description 'Apply next-hop-self for EBGP route.'
                                  ;
                    }
                    enum all {
                      value 2 ;
                      description 'Apply next-hop-self for both EBGP and IBGP r'
                                + 'oute.'
                                  ;
                    }
                  }
                }
                choice nh-unchanged {
                  case next-hop-unchanged {
                    description 'NEXT_HOP of the IBGP path propagated unchanged'
                              + ' to this neighbor.'
                                ;
                    leaf next-hop-unchanged {
                      description 'Propagate next hop unchanged for IBGP paths '
                                + 'to this neighbor.'
                                  ;
                      type empty ;
                    }
                  }
                  case next-hop-unchanged-all {
                    description 'NEXT_HOP of either EBGP or IBGP path propagate'
                              + 'd unchanged to this neighbor.'
                                ;
                    leaf next-hop-unchanged-all {
                      description 'NEXT_HOP of either EBGP or IBGP path propaga'
                                + 'ted unchanged to this neighbor.'
                                  ;
                      type empty ;
                    }
                    ncd:revise-date 2020-04-07 ;
                  }
                }
                leaf nlri-type {
                  description 'Set NLRI type of routes for this neighbor.'
                              ;
                  type enumeration {
                    enum martini-only {
                      value 1 ;
                    }
                    enum kompella-only {
                      value 2 ;
                    }
                  }
                }
                leaf remove-private-as {
                  description 'EBGP use to remove private AS number.'
                              ;
                  type enumeration {
                    enum disable {
                      value 0 ;
                    }
                    enum enable {
                      value 1 ;
                    }
                  }
                }
                leaf route-reflector-client {
                  description 'Set this neighbor as a client peer.'
                              ;
                  type empty ;
                }
                leaf send-community {
                  description 'Send community to this neighbor.'
                              ;
                  type empty ;
                }
                leaf send-large-community {
                  description 'Send Large-community to this neighbor.'
                              ;
                  type empty ;
                  ncd:revise-date 2020-04-16 ;
                }
                leaf send-med {
                  description 'Send metric attribute to this neighbor.'
                              ;
                  type empty ;
                }
                leaf weight {
                  description 'Set weight for routes from this neighbor.'
                              ;
                  type uint32 {
                    range 1..65535 ;
                  }
                }
                container neighbor-extend {
                  description 'Specify a neighbor.'
                              ;
                  leaf route-map-in-name {
                    description 'Apply route-map to incoming routes.'
                                ;
                    type string {
                      length 1..200 ;
                    }
                  }
                  leaf route-map-out-name {
                    description 'Apply route-map to outbound routes.'
                                ;
                    type string {
                      length 1..200 ;
                    }
                  }
                  container maximum-prefix {
                    description 'The action that generated when threshold value'
                              + ' reached.'
                                ;
                    presence 'The action that generated when threshold value re'
                           + 'ached'
                             ;
                    leaf maximum-prefix-number {
                      description 'Maximum number of prefix limit.'
                                  ;
                      type uint32 {
                        range 1..4294967295 ;
                      }
                      mandatory true ;
                    }
                    leaf maximum-prefix-threshold {
                      description 'Threshold value(%) at which to generate a wa'
                                + 'rning.'
                                  ;
                      type uint32 {
                        range 1..100 ;
                      }
                      mandatory true ;
                    }
                    choice maximum-prefix-action {
                      description 'The action that generated when threshold val'
                                + 'ue reached.'
                                  ;
                      mandatory true ;
                      case peer-action {
                        description 'The action that generated when threshold v'
                                  + 'alue reached.'
                                    ;
                        leaf action {
                          description 'The action that generated when threshold'
                                    + ' value reached.'
                                      ;
                          type enumeration {
                            enum down {
                              value 0 ;
                              description 'Break down BGP connection after limit is exceeded.'
                                          ;
                            }
                            enum warning-only {
                              value 1 ;
                              description 'Only give warning message when limit is exceeded.'
                                          ;
                            }
                            enum drop-route {
                              value 2 ;
                              description 'Drop routes that exceed the maximum-prefix.'
                                          ;
                            }
                          }
                          mandatory true ;
                        }
                      }
                      case restart {
                        description 'Restart BGP connection after limit is exce'
                                  + 'eded.'
                                    ;
                        leaf restart-time {
                          description 'Restart interval in minutes.'
                                      ;
                          type uint32 {
                            range 1..30000 ;
                          }
                          mandatory true ;
                        }
                      }
                    }
                  }
                  leaf routepolicy-in-name {
                    description 'Route policy name applied to the inbound route'
                              + 's.'
                                ;
                    type string {
                      length 1..200 ;
                    }
                  }
                  leaf routepolicy-out-name {
                    description 'Route policy name applied to the outbound rout'
                              + 'es.'
                                ;
                    type string {
                      length 1..200 ;
                    }
                  }
                }
              }
              ncd:revise-date 2019-05-20 ;
            }
            leaf default-metric {
              description 'Set metric of BGP routes without MED.'
                          ;
              type uint32 {
                range 0..4294967295 ;
              }
              default 0 ;
              ncd:revise-date 2019-04-10 ;
            }
          }
          container address-family-mdt {
            description 'Configuration in address family Multicast distribution'
                      + ' tree mode.'
                        ;
            presence 'Multicast distribution tree address family.'
                     ;
            container neighbor-group {
              status obsolete {
                ncd:revise-date 2015-05-18 ;
              }
              description 'Specify a peergroup neighbor.'
                          ;
              list neighbor-mdt-peergroup {
                description 'Specify a neighbor.'
                            ;
                key neighbor-group ;
                leaf neighbor-group {
                  description 'Peer group name (1-31 characters).'
                              ;
                  type string {
                    length 1..31 ;
                  }
                }
                leaf activate {
                  description 'Enable the address family for this neighbor.'
                              ;
                  type enumeration {
                    enum disable {
                      value 0 ;
                    }
                    enum enable {
                      value 1 ;
                    }
                  }
                }
                leaf allowas-in {
                  description 'Accept as-path with my AS present in it.'
                              ;
                  type uint32 {
                    range 1..10 ;
                  }
                }
                leaf as-path-loopcheck {
                  description 'Check as-path sending BGP routing to EBGP neighb'
                            + 'or.'
                              ;
                  type empty ;
                }
                leaf maxas-in {
                  description 'Accept as-path not exceeded maxas-in.'
                              ;
                  type uint32 {
                    range 1..250 ;
                  }
                }
                leaf next-hop-self {
                  description 'Disable the next hop calculation for this neighb'
                            + 'or.'
                              ;
                  type enumeration {
                    enum enable {
                      value 1 ;
                      description 'Apply next-hop-self for EBGP route.'
                                  ;
                    }
                    enum all {
                      value 2 ;
                      description 'Apply next-hop-self for both EBGP and IBGP r'
                                + 'oute.'
                                  ;
                    }
                  }
                }
                choice nh-unchanged {
                  case next-hop-unchanged {
                    description 'NEXT_HOP of the IBGP path propagated unchanged'
                              + ' to this neighbor.'
                                ;
                    leaf next-hop-unchanged {
                      description 'Propagate next hop unchanged for IBGP paths '
                                + 'to this neighbor.'
                                  ;
                      type empty ;
                    }
                    ncd:revise-date 2019-06-04 ;
                  }
                  case next-hop-unchanged-all {
                    description 'NEXT_HOP of either EBGP or IBGP path propagate'
                              + 'd unchanged to this neighbor.'
                                ;
                    leaf next-hop-unchanged-all {
                      description 'NEXT_HOP of either EBGP or IBGP path propaga'
                                + 'ted unchanged to this neighbor.'
                                  ;
                      type empty ;
                    }
                    ncd:revise-date 2020-04-07 ;
                  }
                }
                leaf remove-private-as {
                  description 'EBGP use to remove private AS number.'
                              ;
                  type enumeration {
                    enum disable {
                      value 0 ;
                    }
                    enum enable {
                      value 1 ;
                    }
                  }
                }
                leaf route-reflector-client {
                  description 'Set this neighbor as a client peer.'
                              ;
                  type empty ;
                }
                leaf send-community {
                  description 'Send community to this neighbor.'
                              ;
                  type empty ;
                }
                leaf send-med {
                  description 'Send metric attribute to this neighbor.'
                              ;
                  type empty ;
                }
                leaf split-update-group {
                  description 'Split neighbor from update group.'
                              ;
                  type empty ;
                }
                leaf weight {
                  description 'Set weight for routes from this neighbor.'
                              ;
                  type uint32 {
                    range 1..65535 ;
                  }
                }
                container neighbor-extend {
                  description 'Specify a neighbor.'
                              ;
                  leaf route-map-in-name {
                    description 'Apply route-map to incoming routes.'
                                ;
                    type string {
                      length 1..200 ;
                    }
                  }
                  leaf route-map-out-name {
                    description 'Apply route-map to outbound routes.'
                                ;
                    type string {
                      length 1..200 ;
                    }
                  }
                  container maximum-prefix {
                    description 'The action that generated when threshold value'
                              + ' reached.'
                                ;
                    presence 'The action that generated when threshold value re'
                           + 'ached'
                             ;
                    leaf maximum-prefix-number {
                      description 'Maximum number of prefix limit.'
                                  ;
                      type uint32 {
                        range 1..4294967295 ;
                      }
                      mandatory true ;
                    }
                    leaf maximum-prefix-threshold {
                      description 'Threshold value(%) at which to generate a wa'
                                + 'rning.'
                                  ;
                      type uint32 {
                        range 1..100 ;
                      }
                      mandatory true ;
                    }
                    choice maximum-prefix-action {
                      description 'The Action that generated when threshold val'
                                + 'ue reached.'
                                  ;
                      mandatory true ;
                      case peer-action {
                        description 'The action that generated when threshold v'
                                  + 'alue reached.'
                                    ;
                        leaf action {
                          description 'The action that generated when threshold'
                                    + ' value reached.'
                                      ;
                          type enumeration {
                            enum down {
                              value 0 ;
                              description 'Break down BGP connection after limit is exceeded.'
                                          ;
                            }
                            enum warning-only {
                              value 1 ;
                              description 'Only give warning message when limit is exceeded.'
                                          ;
                            }
                            enum drop-routes {
                              value 2 ;
                              description 'Drop routes that exceed the maximum-prefix.'
                                          ;
                            }
                          }
                          mandatory true ;
                        }
                      }
                      case restart {
                        description 'Restart BGP connection after limit is exce'
                                  + 'eded.'
                                    ;
                        leaf restart-time {
                          description 'Restart interval in minutes.'
                                      ;
                          type uint32 {
                            range 1..30000 ;
                          }
                          units min ;
                          mandatory true ;
                        }
                      }
                    }
                  }
                }
              }
            }
            container neighbor-ipv4 {
              description 'Specify a IPv4 neighbor.'
                          ;
              list neighbor-mdt {
                description 'Specify a neighbor.'
                            ;
                key ipv4-address ;
                leaf ipv4-address {
                  description 'Neighbor IPv4 address.'
                              ;
                  type ncd:ipv4-address ;
                }
                leaf joined-group {
                  description 'Only for read operation. The joined group name.'
                              ;
                  type string {
                    length 1..31 ;
                  }
                  ncd:revise-date 2016-05-16 ;
                }
                leaf activate {
                  description 'Enable the address family for this neighbor.'
                              ;
                  type enumeration {
                    enum disable {
                      value 0 ;
                    }
                    enum enable {
                      value 1 ;
                    }
                  }
                }
                leaf allowas-in {
                  description 'Accept as-path with my AS present in it.'
                              ;
                  type uint32 {
                    range 1..10 ;
                  }
                }
                leaf as-path-loopcheck {
                  description 'Check as-path sending BGP routing to EBGP neighb'
                            + 'or.'
                              ;
                  type empty ;
                }
                leaf maxas-in {
                  description 'Accept as-path not exceeded maxas-in.'
                              ;
                  type uint32 {
                    range 1..250 ;
                  }
                }
                leaf next-hop-self {
                  description 'Disable the next hop calculation for this neighb'
                            + 'or.'
                              ;
                  type enumeration {
                    enum enable {
                      value 1 ;
                      description 'Apply next-hop-self for EBGP route.'
                                  ;
                    }
                    enum all {
                      value 2 ;
                      description 'Apply next-hop-self for both EBGP and IBGP r'
                                + 'oute.'
                                  ;
                    }
                  }
                }
                choice nh-unchanged {
                  case next-hop-unchanged {
                    description 'NEXT_HOP of the IBGP path propagated unchanged'
                              + ' to this neighbor.'
                                ;
                    leaf next-hop-unchanged {
                      description 'Propagate next hop unchanged for IBGP paths '
                                + 'to this neighbor.'
                                  ;
                      type empty ;
                    }
                    ncd:revise-date 2019-06-04 ;
                  }
                  case next-hop-unchanged-all {
                    description 'NEXT_HOP of either EBGP or IBGP path propagate'
                              + 'd unchanged to this neighbor.'
                                ;
                    leaf next-hop-unchanged-all {
                      description 'NEXT_HOP of either EBGP or IBGP path propaga'
                                + 'ted unchanged to this neighbor.'
                                  ;
                      type empty ;
                    }
                    ncd:revise-date 2020-04-07 ;
                  }
                }
                leaf remove-private-as {
                  description 'EBGP use to remove private AS number.'
                              ;
                  type enumeration {
                    enum disable {
                      value 0 ;
                    }
                    enum enable {
                      value 1 ;
                    }
                  }
                }
                leaf route-reflector-client {
                  description 'Set this neighbor as a client peer.'
                              ;
                  type empty ;
                }
                leaf send-community {
                  description 'Send community to this neighbor.'
                              ;
                  type empty ;
                }
                leaf send-large-community {
                  description 'Send Large-community to this neighbor.'
                              ;
                  type empty ;
                  ncd:revise-date 2020-04-16 ;
                }
                leaf send-med {
                  description 'Send metric attribute to this neighbor.'
                              ;
                  type empty ;
                }
                leaf split-update-group {
                  description 'Split neighbor from update group.'
                              ;
                  type empty ;
                }
                leaf weight {
                  description 'Set weight for routes from this neighbor.'
                              ;
                  type uint32 {
                    range 1..65535 ;
                  }
                }
                container neighbor-extend {
                  description 'Specify a neighbor.'
                              ;
                  leaf route-map-in-name {
                    description 'Apply route-map to incoming routes.'
                                ;
                    type string {
                      length 1..200 ;
                    }
                  }
                  leaf route-map-out-name {
                    description 'Apply route-map to outbound routes.'
                                ;
                    type string {
                      length 1..200 ;
                    }
                  }
                  container maximum-prefix {
                    description 'The action that generated when threshold value'
                              + ' reached.'
                                ;
                    presence 'The action that generated when threshold value re'
                           + 'ached'
                             ;
                    leaf maximum-prefix-number {
                      description 'Maximum number of prefix limit.'
                                  ;
                      type uint32 {
                        range 1..4294967295 ;
                      }
                      mandatory true ;
                    }
                    leaf maximum-prefix-threshold {
                      description 'Threshold value(%) at which to generate a wa'
                                + 'rning.'
                                  ;
                      type uint32 {
                        range 1..100 ;
                      }
                      mandatory true ;
                    }
                    choice maximum-prefix-action {
                      description 'The action that generated when threshold val'
                                + 'ue reached.'
                                  ;
                      mandatory true ;
                      case peer-action {
                        description 'The action that generated when threshold v'
                                  + 'alue reached.'
                                    ;
                        leaf action {
                          description 'The action that generated when threshold'
                                    + ' value reached.'
                                      ;
                          type enumeration {
                            enum down {
                              value 0 ;
                              description 'Break down BGP connection after limit is exceeded.'
                                          ;
                            }
                            enum warning-only {
                              value 1 ;
                              description 'Only give warning message when limit is exceeded.'
                                          ;
                            }
                            enum drop-routes {
                              value 2 ;
                              description 'Drop routes that exceed the maximum-prefix.'
                                          ;
                            }
                          }
                          mandatory true ;
                        }
                      }
                      case restart {
                        description 'Restart BGP connection after limit is exce'
                                  + 'eded.'
                                    ;
                        leaf restart-time {
                          description 'Restart interval in minutes.'
                                      ;
                          type uint32 {
                            range 1..30000 ;
                          }
                          units min ;
                          mandatory true ;
                        }
                      }
                    }
                  }
                  leaf routepolicy-in-name {
                    description 'Route policy name applied to the inbound route'
                              + 's.'
                                ;
                    type string {
                      length 1..200 ;
                    }
                    ncd:revise-date 2015-05-18 ;
                  }
                  leaf routepolicy-out-name {
                    description 'Route policy name applied to the outbound rout'
                              + 'es.'
                                ;
                    type string {
                      length 1..200 ;
                    }
                    ncd:revise-date 2015-05-18 ;
                  }
                }
                leaf nouse-peergroup-config {
                  status obsolete {
                    ncd:revise-date 2015-05-18 ;
                  }
                  description 'Peer do not use group config set.Only for get op'
                            + 'eration.'
                              ;
                  type empty ;
                }
              }
            }
            leaf default-metric {
              description 'Set metric of BGP routes without MED.'
                          ;
              type uint32 {
                range 0..4294967295 ;
              }
              default 0 ;
              ncd:revise-date 2019-04-10 ;
            }
          }
          container address-family-ipv4-vpn-mcast {
            description 'Configuration in address family VPNv4 mcast mode.'
                        ;
            presence 'VPNv4 mcast address family.'
                     ;
            container neighbor-ipv4 {
              description 'Specify a IPv4 neighbor.'
                          ;
              list neighbor {
                description 'Specify a neighbor.'
                            ;
                key ipv4-address ;
                leaf ipv4-address {
                  description 'Neighbor IPv4 address.'
                              ;
                  type ncd:ipv4-address ;
                }
                leaf activate {
                  description 'Enable the address family for this neighbor.'
                              ;
                  type enumeration {
                    enum enable {
                      value 1 ;
                    }
                  }
                }
                leaf split-update-group {
                  description 'Split neighbor from update group.'
                              ;
                  type empty ;
                }
                leaf route-reflector-client {
                  description 'Set this neighbor as a client peer.'
                              ;
                  type empty ;
                }
                choice nh-unchanged {
                  case next-hop-unchanged {
                    description 'NEXT_HOP of the IBGP path propagated unchanged'
                              + ' to this neighbor.'
                                ;
                    leaf next-hop-unchanged {
                      description 'Propagate next hop unchanged for IBGP paths '
                                + 'to this neighbor.'
                                  ;
                      type empty ;
                    }
                    ncd:revise-date 2019-06-04 ;
                  }
                  case next-hop-unchanged-all {
                    description 'NEXT_HOP of either EBGP or IBGP path propagate'
                              + 'd unchanged to this neighbor.'
                                ;
                    leaf next-hop-unchanged-all {
                      description 'NEXT_HOP of either EBGP or IBGP path propaga'
                                + 'ted unchanged to this neighbor.'
                                  ;
                      type empty ;
                    }
                    ncd:revise-date 2020-04-07 ;
                  }
                }
                container neighbor-extend {
                  description 'Specify a neighbor.'
                              ;
                  leaf route-map-in-name {
                    description 'Apply route-map to incoming routes.'
                                ;
                    type string {
                      length 1..200 ;
                    }
                  }
                  leaf route-map-out-name {
                    description 'Apply route-map to outbound routes.'
                                ;
                    type string {
                      length 1..200 ;
                    }
                  }
                  leaf announce-msid {
                    description 'Enable multicast service identifier attribute '
                              + 'for this neighbor.'
                                ;
                    type empty ;
                    ncd:revise-date 2021-04-21 ;
                  }
                  leaf non-segmented {
                    description 'Non-segmented inter-AS/intra-AS tunnels.'
                                ;
                    type empty ;
                    ncd:revise-date 2021-04-21 ;
                  }
                  ncd:revise-date 2020-03-02 ;
                }
                leaf weight {
                  description 'Set weight for routes from this neighbor.'
                              ;
                  type uint32 {
                    range 1..65535 ;
                  }
                  ncd:revise-date 2020-03-02 ;
                }
              }
            }
            leaf default-metric {
              description 'Set metric of BGP routes without MED.'
                          ;
              type uint32 {
                range 0..4294967295 ;
              }
              default 0 ;
              ncd:revise-date 2019-04-10 ;
            }
          }
          container address-family-ipv4-vpn-multi {
            description 'Configuration in address family VPNv4 multicast mode.'
                        ;
            presence 'VPNv4 multicast address family.'
                     ;
            container neighbor-ipv4 {
              description 'Specify a IPv4 neighbor.'
                          ;
              list neighbor {
                description 'Specify a neighbor.'
                            ;
                key ipv4-address ;
                leaf ipv4-address {
                  description 'Neighbor IPv4 address.'
                              ;
                  type ncd:ipv4-address ;
                }
                leaf activate {
                  description 'Enable the address family for this neighbor.'
                              ;
                  type enumeration {
                    enum enable {
                      value 1 ;
                    }
                  }
                }
                leaf split-update-group {
                  description 'Split neighbor from update group.'
                              ;
                  type empty ;
                }
                leaf route-reflector-client {
                  description 'Set this neighbor as a client peer.'
                              ;
                  type empty ;
                }
                choice nh-unchanged {
                  case next-hop-unchanged {
                    description 'NEXT_HOP of the IBGP path propagated unchanged'
                              + ' to this neighbor.'
                                ;
                    leaf next-hop-unchanged {
                      description 'Propagate next hop unchanged for IBGP paths '
                                + 'to this neighbor.'
                                  ;
                      type empty ;
                    }
                    ncd:revise-date 2019-06-04 ;
                  }
                  case next-hop-unchanged-all {
                    description 'NEXT_HOP of either EBGP or IBGP path propagate'
                              + 'd unchanged to this neighbor.'
                                ;
                    leaf next-hop-unchanged-all {
                      description 'NEXT_HOP of either EBGP or IBGP path propaga'
                                + 'ted unchanged to this neighbor.'
                                  ;
                      type empty ;
                    }
                    ncd:revise-date 2020-04-07 ;
                  }
                }
                container neighbor-extend {
                  description 'Specify a neighbor.'
                              ;
                  leaf route-map-in-name {
                    description 'Apply route-map to incoming routes.'
                                ;
                    type string {
                      length 1..200 ;
                    }
                  }
                  leaf route-map-out-name {
                    description 'Apply route-map to outbound routes.'
                                ;
                    type string {
                      length 1..200 ;
                    }
                  }
                  ncd:revise-date 2020-03-02 ;
                }
                leaf weight {
                  description 'Set weight for routes from this neighbor.'
                              ;
                  type uint32 {
                    range 1..65535 ;
                  }
                  ncd:revise-date 2020-03-02 ;
                }
                container route-server-client {
                  description 'Set route server client only valid for ebgp peer.'
                              ;
                  presence route-server-client ;
                  leaf route-svr-client {
                    description 'Set route server client only valid for ebgp pe'
                              + 'er.'
                                ;
                    type empty ;
                    mandatory true ;
                  }
                  ncd:revise-date 2020-04-07 ;
                }
              }
            }
            leaf default-metric {
              description 'Set metric of BGP routes without MED.'
                          ;
              type uint32 {
                range 0..4294967295 ;
              }
              default 0 ;
              ncd:revise-date 2019-04-10 ;
            }
          }
          container address-family-rt {
            description 'Configuration in address family ROUTER-TARGET mode.'
                        ;
            presence 'ROUTER-TARGET address family'
                     ;
            leaf defaults-set-flag {
              status obsolete {
                ncd:revise-date 2020-07-28 ;
              }
              description 'Flag of defaults.Only for get operation.When this va'
                        + 'lue expressed as a binary,The lowest bit indicate di'
                        + 'stance-ibgp,the next bit distance-ebgp,then maxpaths'
                        + '-ebgp,then default-metric,then wait-for-end-of-rib,t'
                        + 'hen constrain-rt-filter.'
                          ;
              type uint32 {
                range 0..4294967295 ;
              }
              default 0 ;
              ncd:revise-date 2015-06-02 ;
            }
            leaf constrain-rt-filter {
              description 'Constraining VPN Route Distribution with Route-Targe'
                        + 't Filtering.'
                          ;
              type enumeration {
                enum disable {
                  value 0 ;
                }
                enum enable {
                  value 1 ;
                }
              }
              default enable ;
            }
            leaf default-metric {
              description 'Set metric of BGP routes without MED.'
                          ;
              type uint32 {
                range 0..4294967295 ;
              }
              default 0 ;
            }
            leaf maximum-paths {
              description 'Maximum number of parallel routes BGP can support.'
                          ;
              type uint32 {
                range 1..32 ;
              }
              default 1 ;
            }
            leaf wait-for-end-of-rib {
              description 'Configure how long BGP waits to receive End-of-RIB m'
                        + 'arkers from route-target address family peers.'
                          ;
              type uint32 {
                range 3..3000 ;
              }
              units s ;
              default 60 ;
            }
            leaf nexthop-recursive-default-route {
              description 'Nexthop recursive lookup default-route.'
                          ;
              type enumeration {
                enum enable {
                  value 1 ;
                }
                enum disable {
                  value 0 ;
                }
              }
              default enable ;
              ncd:revise-date 2020-07-28 ;
            }
            container neighbor-rt {
              description 'Specify a neighbor.'
                          ;
              presence neighbor-rt ;
              container neighbor-group {
                description 'Specify a peergroup neighbor.'
                            ;
                list neighbor-peergroup {
                  description 'Specify a neighbor.'
                              ;
                  key neighbor-group ;
                  leaf neighbor-group {
                    description 'Peer group name (1-31 characters).'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf allowas-in {
                    description 'Accept as-path with my AS present in it.'
                                ;
                    type uint32 {
                      range 1..10 ;
                    }
                  }
                  leaf as-path-loopcheck {
                    description 'Check as-path sending BGP routing to EBGP neig'
                              + 'hbor.'
                                ;
                    type empty ;
                  }
                  leaf default-originate {
                    description 'Originate default route to this neighbor.'
                                ;
                    type empty ;
                  }
                  leaf default-originate-routemap {
                    description 'Map external entry attributes into routing tab'
                              + 'le.'
                                ;
                    type string {
                      length 1..200 ;
                    }
                    ncd:revise-date 2020-07-28 ;
                  }
                  leaf default-originate-routepolicy {
                    description 'Set external entry attributes into routing tab'
                              + 'le.'
                                ;
                    type string {
                      length 1..200 ;
                    }
                    ncd:revise-date 2020-10-10 ;
                  }
                  leaf maxas-in {
                    description 'Accept as-path not exceeded maxas-in.'
                                ;
                    type uint32 {
                      range 1..250 ;
                    }
                  }
                  leaf next-hop-self {
                    description 'Disable the next hop calculation for this neig'
                              + 'hbor.'
                                ;
                    type enumeration {
                      enum enable {
                        value 1 ;
                        description 'Apply next-hop-self for EBGP route.'
                                    ;
                      }
                      enum all {
                        value 2 ;
                        description 'Apply next-hop-self for both EBGP and IBGP'
                                  + ' route.'
                                    ;
                      }
                    }
                  }
                  leaf remove-private-as {
                    description 'EBGP use to remove private AS number.'
                                ;
                    type enumeration {
                      enum disable {
                        value 0 ;
                      }
                      enum enable {
                        value 1 ;
                      }
                    }
                  }
                  leaf route-reflector-client {
                    description 'Set this neighbor as a client peer.'
                                ;
                    type empty ;
                  }
                  leaf send-community {
                    description 'Send community to this neighbor.'
                                ;
                    type empty ;
                  }
                  leaf send-large-community {
                    description 'Send Large-community to this neighbor.'
                                ;
                    type empty ;
                    ncd:revise-date 2020-04-16 ;
                  }
                  leaf send-med {
                    description 'Send metric attribute to this neighbor.'
                                ;
                    type empty ;
                  }
                  leaf split-update-group {
                    description 'Split neighbor from update group.'
                                ;
                    type empty ;
                  }
                  leaf weight {
                    description 'Set weight for routes from this neighbor.'
                                ;
                    type uint32 {
                      range 1..65535 ;
                    }
                  }
                  container neighbor-extend {
                    description 'Specify a neighbor.'
                                ;
                    leaf route-map-in-name {
                      description 'Apply route-map to incoming routes.'
                                  ;
                      type string {
                        length 1..200 ;
                      }
                    }
                    leaf route-map-out-name {
                      description 'Apply route-map to outbound routes.'
                                  ;
                      type string {
                        length 1..200 ;
                      }
                    }
                    leaf routepolicy-in-name {
                      description 'Route policy name applied to the inbound rou'
                                + 'tes.'
                                  ;
                      type string {
                        length 1..200 ;
                      }
                      ncd:revise-date 2015-05-18 ;
                    }
                    leaf routepolicy-out-name {
                      description 'Route policy name applied to the outbound ro'
                                + 'utes.'
                                  ;
                      type string {
                        length 1..200 ;
                      }
                      ncd:revise-date 2015-05-18 ;
                    }
                  }
                }
              }
              container neighbor-ipv4 {
                description 'Specify a IPv4 neighbor.'
                            ;
                list neighbor {
                  description 'Specify a neighbor.'
                              ;
                  key ipv4-address ;
                  leaf ipv4-address {
                    description 'Neighbor IPv4 address.'
                                ;
                    type ncd:ipv4-address ;
                  }
                  leaf joined-group {
                    description 'Only for read operation. The joined group name.'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf allowas-in {
                    description 'Accept as-path with my AS present in it.'
                                ;
                    type uint32 {
                      range 1..10 ;
                    }
                  }
                  leaf as-path-loopcheck {
                    description 'Check as-path sending BGP routing to EBGP neig'
                              + 'hbor.'
                                ;
                    type empty ;
                  }
                  leaf default-originate {
                    description 'Originate default route to this neighbor.'
                                ;
                    type empty ;
                  }
                  leaf default-originate-routemap {
                    description 'Map external entry attributes into routing tab'
                              + 'le.'
                                ;
                    type string {
                      length 1..200 ;
                    }
                    ncd:revise-date 2020-07-28 ;
                  }
                  leaf default-originate-routepolicy {
                    description 'Set external entry attributes into routing tab'
                              + 'le.'
                                ;
                    type string {
                      length 1..200 ;
                    }
                    ncd:revise-date 2020-10-10 ;
                  }
                  leaf maxas-in {
                    description 'Accept as-path not exceeded maxas-in.'
                                ;
                    type uint32 {
                      range 1..250 ;
                    }
                  }
                  leaf next-hop-self {
                    description 'Disable the next hop calculation for this neig'
                              + 'hbor.'
                                ;
                    type enumeration {
                      enum enable {
                        value 1 ;
                        description 'Apply next-hop-self for EBGP route.'
                                    ;
                      }
                      enum all {
                        value 2 ;
                        description 'Apply next-hop-self for both EBGP and IBGP'
                                  + ' route.'
                                    ;
                      }
                    }
                  }
                  leaf remove-private-as {
                    description 'EBGP use to remove private AS number.'
                                ;
                    type enumeration {
                      enum disable {
                        value 0 ;
                      }
                      enum enable {
                        value 1 ;
                      }
                    }
                  }
                  leaf route-reflector-client {
                    description 'Set this neighbor as a client peer.'
                                ;
                    type empty ;
                  }
                  leaf send-community {
                    description 'Send community to this neighbor.'
                                ;
                    type empty ;
                  }
                  leaf send-large-community {
                    description 'Send Large-community to this neighbor.'
                                ;
                    type empty ;
                    ncd:revise-date 2020-04-16 ;
                  }
                  leaf send-med {
                    description 'Send metric attribute to this neighbor.'
                                ;
                    type empty ;
                  }
                  leaf split-update-group {
                    description 'Split neighbor from update group.'
                                ;
                    type empty ;
                  }
                  leaf weight {
                    description 'Set weight for routes from this neighbor.'
                                ;
                    type uint32 {
                      range 1..65535 ;
                    }
                  }
                  container neighbor-extend {
                    description 'Specify a neighbor.'
                                ;
                    leaf route-map-in-name {
                      description 'Apply route-map to incoming routes.'
                                  ;
                      type string {
                        length 1..200 ;
                      }
                    }
                    leaf route-map-out-name {
                      description 'Apply route-map to outbound routes.'
                                  ;
                      type string {
                        length 1..200 ;
                      }
                    }
                    leaf routepolicy-in-name {
                      description 'Route policy name applied to the inbound rou'
                                + 'tes.'
                                  ;
                      type string {
                        length 1..200 ;
                      }
                      ncd:revise-date 2015-05-18 ;
                    }
                    leaf routepolicy-out-name {
                      description 'Route policy name applied to the outbound ro'
                                + 'utes.'
                                  ;
                      type string {
                        length 1..200 ;
                      }
                      ncd:revise-date 2015-05-18 ;
                    }
                  }
                  leaf nouse-peergroup-config {
                    status obsolete {
                      ncd:revise-date 2015-05-18 ;
                    }
                    description 'Peer do not use group config set.Only for get '
                              + 'operation.'
                                ;
                    type empty ;
                  }
                }
              }
              container neighbor-ipv6 {
                description 'Specify a IPv6 neighbor.'
                            ;
                list neighbor {
                  description 'Specify a neighbor.'
                              ;
                  key ipv6-address ;
                  leaf ipv6-address {
                    description 'Neighbor IPv6 address.'
                                ;
                    type ncd:ipv6-address ;
                  }
                  leaf joined-group {
                    description 'Only for read operation. The joined group name.'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf allowas-in {
                    description 'Accept as-path with my AS present in it.'
                                ;
                    type uint32 {
                      range 1..10 ;
                    }
                  }
                  leaf as-path-loopcheck {
                    description 'Check as-path sending BGP routing to EBGP neig'
                              + 'hbor.'
                                ;
                    type empty ;
                  }
                  leaf default-originate {
                    description 'Originate default route to this neighbor.'
                                ;
                    type empty ;
                  }
                  leaf default-originate-routemap {
                    description 'Map external entry attributes into routing tab'
                              + 'le.'
                                ;
                    type string {
                      length 1..200 ;
                    }
                    ncd:revise-date 2020-07-28 ;
                  }
                  leaf default-originate-routepolicy {
                    description 'Set external entry attributes into routing tab'
                              + 'le.'
                                ;
                    type string {
                      length 1..200 ;
                    }
                    ncd:revise-date 2020-10-10 ;
                  }
                  leaf maxas-in {
                    description 'Accept as-path not exceeded maxas-in.'
                                ;
                    type uint32 {
                      range 1..250 ;
                    }
                  }
                  leaf next-hop-self {
                    description 'Disable the next hop calculation for this neig'
                              + 'hbor.'
                                ;
                    type enumeration {
                      enum enable {
                        value 1 ;
                        description 'Apply next-hop-self for EBGP route.'
                                    ;
                      }
                      enum all {
                        value 2 ;
                        description 'Apply next-hop-self for both EBGP and IBGP'
                                  + ' route.'
                                    ;
                      }
                    }
                  }
                  leaf remove-private-as {
                    description 'EBGP use to remove private AS number.'
                                ;
                    type enumeration {
                      enum disable {
                        value 0 ;
                      }
                      enum enable {
                        value 1 ;
                      }
                    }
                  }
                  leaf route-reflector-client {
                    description 'Set this neighbor as a client peer.'
                                ;
                    type empty ;
                  }
                  leaf send-community {
                    description 'Send community to this neighbor.'
                                ;
                    type empty ;
                  }
                  leaf send-large-community {
                    description 'Send Large-community to this neighbor.'
                                ;
                    type empty ;
                    ncd:revise-date 2020-04-16 ;
                  }
                  leaf send-med {
                    description 'Send metric attribute to this neighbor.'
                                ;
                    type empty ;
                  }
                  leaf split-update-group {
                    description 'Split neighbor from update group.'
                                ;
                    type empty ;
                  }
                  leaf weight {
                    description 'Set weight for routes from this neighbor.'
                                ;
                    type uint32 {
                      range 1..65535 ;
                    }
                  }
                  container neighbor-extend {
                    description 'Specify a neighbor.'
                                ;
                    leaf route-map-in-name {
                      description 'Apply route-map to incoming routes.'
                                  ;
                      type string {
                        length 1..200 ;
                      }
                    }
                    leaf route-map-out-name {
                      description 'Apply route-map to outbound routes.'
                                  ;
                      type string {
                        length 1..200 ;
                      }
                    }
                    leaf routepolicy-in-name {
                      description 'Route policy name applied to the inbound rou'
                                + 'tes.'
                                  ;
                      type string {
                        length 1..200 ;
                      }
                    }
                    leaf routepolicy-out-name {
                      description 'Route policy name applied to the outbound ro'
                                + 'utes.'
                                  ;
                      type string {
                        length 1..200 ;
                      }
                    }
                  }
                }
                ncd:revise-date 2020-02-08 ;
              }
            }
            leaf nexthop-recursive-null1 {
              description 'Nexthop recursive lookup null1.'
                          ;
              type enumeration {
                enum enable {
                  value 1 ;
                }
                enum disable {
                  value 0 ;
                }
              }
              default enable ;
              ncd:revise-date 2020-12-09 ;
            }
          }
          container address-family-ipv4-multi {
            description 'Configuration in address family IPv4 multicast mode.'
                        ;
            presence 'IPv4 multicast address family.'
                     ;
            leaf defaults-set-flag {
              status obsolete {
                ncd:revise-date 2020-07-28 ;
              }
              description 'Flag of defaults.Only for get operation.When this va'
                        + 'lue expressed as a binary,The lowest bit indicate di'
                        + 'stance-ibgp,the next bit distance-ebgp,then maxpaths'
                        + '-ebgp,then default-metric,then wait-for-end-of-rib,t'
                        + 'hen constrain-rt-filter.'
                          ;
              type uint32 {
                range 0..4294967295 ;
              }
              default 0 ;
              ncd:revise-date 2015-06-02 ;
            }
            leaf default-information-originate {
              description 'Notify default route.'
                          ;
              type empty ;
            }
            leaf default-metric {
              description 'Set metric of BGP routes without MED.'
                          ;
              type uint32 {
                range 0..4294967295 ;
              }
              default 0 ;
            }
            leaf distance-bgp-external {
              description 'Distance for routes external to the AS.'
                          ;
              type uint32 {
                range 1..255 ;
              }
              default 20 ;
            }
            leaf distance-bgp-internal {
              description 'Distance for routes internal to the AS.'
                          ;
              type uint32 {
                range 1..255 ;
              }
              default 200 ;
            }
            leaf distance-route-map {
              description 'Define distance by route-map.This node has higher pr'
                        + 'iority than distance-bgp-internal and distance-bgp-e'
                        + 'xternal.'
                          ;
              type string {
                length 1..200 ;
              }
              ncd:revise-date 2020-09-08 ;
            }
            leaf distance-route-policy {
              description 'Define distance by route-policy.This node has higher'
                        + ' priority than distance-bgp-internal and distance-bg'
                        + 'p-external.'
                          ;
              type string {
                length 1..200 ;
              }
              ncd:revise-date 2020-10-10 ;
            }
            container redistribute-ipv4-multi {
              description 'Redistribute information from another routing protoc'
                        + 'ol.'
                          ;
              presence redistribute-ipv4-multi ;
              container redistribute-multi {
                description 'Redistribute information from another routing prot'
                          + 'ocol.'
                            ;
                list redistribute {
                  description 'Redistribute information from another routing pr'
                            + 'otocol.'
                              ;
                  key protocol ;
                  leaf protocol {
                    description 'Routing protocol type.'
                                ;
                    type enumeration {
                      enum connected {
                        value 1 ;
                        description 'Connected routes.'
                                    ;
                      }
                      enum static {
                        value 2 ;
                        description 'Static routes.'
                                    ;
                      }
                      enum rip {
                        value 3 ;
                        description 'Routing information protocol(RIP).'
                                    ;
                      }
                      enum ps-busi-addr {
                        value 10 ;
                        description 'Ps-busi-addr routes.'
                                    ;
                      }
                      enum ps-user-addr {
                        value 11 ;
                        description 'Ps-user-addr routes.'
                                    ;
                      }
                      enum bras-pool {
                        value 24 ;
                        description 'Broadband Remote Access Server pool routes.'
                                    ;
                      }
                      enum ipsec {
                        value 25 ;
                        description 'IPsec routes'
                                    ;
                      }
                      enum hagp {
                        value 26 ;
                        description 'Hybrid access gateway protocol routes.'
                                    ;
                      }
                      enum dyn-leasedline {
                        value 29 ;
                        description 'Dynamic-leased-line routes assigned by AAA.'
                                    ;
                      }
                      enum address {
                        value 9 ;
                        description 'Address routes.'
                                    ;
                      }
                    }
                  }
                  leaf route-map {
                    description 'Apply route-map to redistribute.'
                                ;
                    type string {
                      length 1..200 ;
                    }
                  }
                  leaf route-policy {
                    description 'Apply route-policy to redistribute.'
                                ;
                    type string {
                      length 1..200 ;
                    }
                    ncd:revise-date 2020-10-10 ;
                  }
                  container set-metric {
                    description 'Set route metric.'
                                ;
                    leaf metric {
                      description 'Set route metric.'
                                  ;
                      type uint32 {
                        range 0..4294967295 ;
                      }
                    }
                  }
                }
              }
              container redistribute-isis-multi {
                description 'Redistribute information from ISIS protocol.'
                            ;
                list redistribute-isis {
                  description 'Redistribute information from ISIS protocol.'
                              ;
                  key 'protocol process-id'
                      ;
                  leaf protocol {
                    description 'Routing protocol type(ISIS-1,ISIS-2 or ISIS-1-'
                              + '2).'
                                ;
                    type enumeration {
                      enum isis-1 {
                        value 4 ;
                        description 'IS-IS level-1 routes only.'
                                    ;
                      }
                      enum isis-2 {
                        value 5 ;
                        description 'IS-IS level-2 routes only.'
                                    ;
                      }
                    }
                  }
                  leaf process-id {
                    description 'ISIS process ID.'
                                ;
                    type uint32 {
                      range 0..65535 ;
                    }
                  }
                  leaf route-map {
                    description 'Apply route-map to redistribute.'
                                ;
                    type string {
                      length 1..200 ;
                    }
                  }
                  leaf route-policy {
                    description 'Apply route-policy to redistribute.'
                                ;
                    type string {
                      length 1..200 ;
                    }
                    ncd:revise-date 2020-10-10 ;
                  }
                  container set-metric {
                    description 'Set route metric.'
                                ;
                    leaf metric {
                      description 'Set route metric.'
                                  ;
                      type uint32 {
                        range 0..4294967295 ;
                      }
                    }
                  }
                }
              }
              container redistribute-ospf-multi {
                description 'Redistribute information from OSPF protocol.'
                            ;
                list redistribute-ospf {
                  description 'Redistribute information from OSPF protocol.'
                              ;
                  key 'protocol process-id'
                      ;
                  leaf protocol {
                    description 'Routing protocol type(OSPF-EXT or OSPF-INT).'
                                ;
                    type enumeration {
                      enum ospf-ext {
                        value 7 ;
                        description 'Open shortest path first(OSPF) external ro'
                                  + 'utes.'
                                    ;
                      }
                      enum ospf-int {
                        value 8 ;
                        description 'Open shortest path first(OSPF) internal ro'
                                  + 'utes.'
                                    ;
                      }
                    }
                  }
                  leaf process-id {
                    description 'OSPF process ID.'
                                ;
                    type uint32 {
                      range 1..65535 ;
                    }
                  }
                  leaf route-map {
                    description 'Apply route-map to redistribute.'
                                ;
                    type string {
                      length 1..200 ;
                    }
                  }
                  leaf route-policy {
                    description 'Apply route-policy to redistribute.'
                                ;
                    type string {
                      length 1..200 ;
                    }
                    ncd:revise-date 2020-10-10 ;
                  }
                  container set-metric {
                    description 'Set route metric.'
                                ;
                    leaf metric {
                      description 'Set route metric.'
                                  ;
                      type uint32 {
                        range 0..4294967295 ;
                      }
                    }
                  }
                }
              }
            }
            container network-ipv4-multi {
              description 'Specify a network to announce via BGP.'
                          ;
              presence network-ipv4-multi ;
              list network {
                description 'Specify a network to announce via BGP.'
                            ;
                key 'ip-address ip-mask'
                    ;
                leaf ip-address {
                  description 'Network prefix.'
                              ;
                  type ncd:ipv4-address ;
                }
                leaf ip-mask {
                  description 'Network mask.'
                              ;
                  type ncd:ipv4-mask ;
                }
                leaf route-map {
                  description 'Route-map to modify the attributes.'
                              ;
                  type string {
                    length 1..200 ;
                  }
                }
                leaf route-policy {
                  description 'Route-policy to modify the attributes.'
                              ;
                  type string {
                    length 1..200 ;
                  }
                  ncd:revise-date 2020-10-10 ;
                }
              }
            }
            container neighbor-v4-multi {
              description 'Specify a neighbor.'
                          ;
              presence neighbor-v4-multi ;
              container neighbor-group {
                description 'Specify a peergroup neighbor.'
                            ;
                list neighbor-peergroup {
                  description 'Specify a neighbor.'
                              ;
                  key neighbor-group ;
                  leaf neighbor-group {
                    description 'Peer group name (1-31 characters).'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf allowas-in {
                    description 'Accept as-path with my AS present in it.'
                                ;
                    type uint32 {
                      range 1..10 ;
                    }
                  }
                  leaf as-path-loopcheck {
                    description 'Check as-path sending BGP routing to EBGP neig'
                              + 'hbor.'
                                ;
                    type empty ;
                  }
                  leaf default-originate {
                    description 'Originate default route to this neighbor.'
                                ;
                    type empty ;
                  }
                  leaf default-originate-routemap {
                    description 'Map external entry attributes into routing tab'
                              + 'le.'
                                ;
                    type string {
                      length 1..200 ;
                    }
                    ncd:revise-date 2020-07-28 ;
                  }
                  leaf default-originate-routepolicy {
                    description 'Set external entry attributes into routing tab'
                              + 'le.'
                                ;
                    type string {
                      length 1..200 ;
                    }
                    ncd:revise-date 2020-10-10 ;
                  }
                  leaf maxas-in {
                    description 'Accept as-path not exceeded maxas-in.'
                                ;
                    type uint32 {
                      range 1..250 ;
                    }
                  }
                  leaf next-hop-self {
                    description 'Disable the next hop calculation for this neig'
                              + 'hbor.'
                                ;
                    type enumeration {
                      enum enable {
                        value 1 ;
                        description 'Apply next-hop-self for EBGP route.'
                                    ;
                      }
                      enum all {
                        value 2 ;
                        description 'Apply next-hop-self for both EBGP and IBGP'
                                  + ' route.'
                                    ;
                      }
                    }
                  }
                  leaf remove-private-as {
                    description 'EBGP use to remove private AS number.'
                                ;
                    type enumeration {
                      enum disable {
                        value 0 ;
                      }
                      enum enable {
                        value 1 ;
                      }
                    }
                  }
                  leaf route-reflector-client {
                    description 'Set this neighbor as a client peer.'
                                ;
                    type empty ;
                  }
                  leaf send-community {
                    description 'Send community to this neighbor.'
                                ;
                    type empty ;
                  }
                  leaf send-large-community {
                    description 'Send Large-community to this neighbor.'
                                ;
                    type empty ;
                    ncd:revise-date 2020-04-16 ;
                  }
                  leaf send-med {
                    description 'Send metric attribute to this neighbor.'
                                ;
                    type empty ;
                  }
                  leaf split-update-group {
                    description 'Split neighbor from update group.'
                                ;
                    type empty ;
                  }
                  container advertise-map {
                    description 'Specify route-map for conditional advertisemen'
                              + 't.'
                                ;
                    presence 'Specify route-map for conditional advertisement'
                             ;
                    leaf advertise-map-name {
                      description 'Advertise route-map name.'
                                  ;
                      type string {
                        length 1..200 ;
                      }
                      mandatory true ;
                    }
                    choice advertise-map {
                      description 'Specify route-map for conditional advertisem'
                                + 'ent.'
                                  ;
                      mandatory true ;
                      case exist-map {
                        description 'Advertise prefix only if prefix exists.'
                                    ;
                        leaf exist-map-name {
                          description 'Advertise prefix only if prefix exists.'
                                      ;
                          type string {
                            length 1..200 ;
                          }
                          mandatory true ;
                        }
                      }
                      case nonexist-map {
                        description 'Advertise prefix only if prefix does not e'
                                  + 'xist.'
                                    ;
                        leaf nonexist-map-name {
                          description 'Advertise prefix only if prefix does not'
                                    + ' exist.'
                                      ;
                          type string {
                            length 1..200 ;
                          }
                          mandatory true ;
                        }
                      }
                    }
                  }
                  leaf weight {
                    description 'Set weight for routes from this neighbor.'
                                ;
                    type uint32 {
                      range 1..65535 ;
                    }
                  }
                  container neighbor-extend {
                    description 'Specify a neighbor.'
                                ;
                    leaf prefix-list-in-name {
                      description 'Apply prefix list to incoming routes.'
                                  ;
                      type string {
                        length 1..169 ;
                      }
                    }
                    leaf prefix-list-out-name {
                      description 'Apply prefix list to outbound routes.'
                                  ;
                      type string {
                        length 1..169 ;
                      }
                    }
                    leaf route-map-in-name {
                      description 'Apply route-map to incoming routes.'
                                  ;
                      type string {
                        length 1..200 ;
                      }
                    }
                    leaf route-map-out-name {
                      description 'Apply route-map to outbound routes.'
                                  ;
                      type string {
                        length 1..200 ;
                      }
                    }
                    container maximum-prefix {
                      description 'The action that generated when threshold val'
                                + 'ue reached.'
                                  ;
                      presence 'The Action that generated when threshold value '
                             + 'reached'
                               ;
                      leaf maximum-prefix-number {
                        description 'Maximum number of prefix limit.'
                                    ;
                        type uint32 {
                          range 1..4294967295 ;
                        }
                        mandatory true ;
                      }
                      leaf maximum-prefix-threshold {
                        description 'Threshold value(%) at which to generate a '
                                  + 'warning.'
                                    ;
                        type uint32 {
                          range 1..100 ;
                        }
                        mandatory true ;
                      }
                      choice maximum-prefix-action {
                        description 'The action that generated when threshold v'
                                  + 'alue reached.'
                                    ;
                        mandatory true ;
                        case peer-action {
                          description 'The action that generated when threshold'
                                    + ' value reached.'
                                      ;
                          leaf action {
                            description 'The action that generated when threshold value reached.'
                                        ;
                            type enumeration {
                              enum down {
                                value 0 ;
                                description 'Break down BGP connection after limit is exceeded.'
                                            ;
                              }
                              enum warning-only {
                                value 1 ;
                                description 'Only give warning message when limit is exceeded.'
                                            ;
                              }
                              enum drop-routes {
                                value 2 ;
                                description 'Drop routes that exceed the maximum-prefix.'
                                            ;
                              }
                            }
                            mandatory true ;
                          }
                        }
                        case restart {
                          description 'Restart BGP connection after limit is ex'
                                    + 'ceeded.'
                                      ;
                          leaf restart-time {
                            description 'Restart interval in minutes.'
                                        ;
                            type uint32 {
                              range 1..30000 ;
                            }
                            units min ;
                            mandatory true ;
                          }
                        }
                      }
                    }
                    leaf routepolicy-in-name {
                      description 'Route policy name applied to the inbound rou'
                                + 'tes.'
                                  ;
                      type string {
                        length 1..200 ;
                      }
                      ncd:revise-date 2015-05-18 ;
                    }
                    leaf routepolicy-out-name {
                      description 'Route policy name applied to the outbound ro'
                                + 'utes.'
                                  ;
                      type string {
                        length 1..200 ;
                      }
                      ncd:revise-date 2015-05-18 ;
                    }
                  }
                  container route-server-client {
                    description 'Set route server client only valid for ebgp pe'
                              + 'er.'
                                ;
                    presence route-server-client ;
                    leaf route-svr-client {
                      description 'Set route server client only valid for ebgp '
                                + 'peer.'
                                  ;
                      type empty ;
                      mandatory true ;
                    }
                    ncd:revise-date 2020-04-07 ;
                  }
                }
              }
              container neighbor-ipv4 {
                description 'Specify a IPv4 neighbor.'
                            ;
                list neighbor {
                  description 'Specify a neighbor.'
                              ;
                  key ipv4-address ;
                  leaf ipv4-address {
                    description 'Neighbor IPv4 address.'
                                ;
                    type ncd:ipv4-address ;
                  }
                  leaf joined-group {
                    description 'Only for read operation. The joined group name.'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf allowas-in {
                    description 'Accept as-path with my AS present in it.'
                                ;
                    type uint32 {
                      range 1..10 ;
                    }
                  }
                  leaf as-path-loopcheck {
                    description 'Check as-path sending BGP routing to EBGP neig'
                              + 'hbor.'
                                ;
                    type empty ;
                  }
                  leaf default-originate {
                    description 'Originate default route to this neighbor.'
                                ;
                    type empty ;
                  }
                  leaf default-originate-routemap {
                    description 'Map external entry attributes into routing tab'
                              + 'le.'
                                ;
                    type string {
                      length 1..200 ;
                    }
                    ncd:revise-date 2020-07-28 ;
                  }
                  leaf default-originate-routepolicy {
                    description 'Set external entry attributes into routing tab'
                              + 'le.'
                                ;
                    type string {
                      length 1..200 ;
                    }
                    ncd:revise-date 2020-10-10 ;
                  }
                  leaf maxas-in {
                    description 'Accept as-path not exceeded maxas-in.'
                                ;
                    type uint32 {
                      range 1..250 ;
                    }
                  }
                  leaf next-hop-self {
                    description 'Disable the next hop calculation for this neig'
                              + 'hbor.'
                                ;
                    type enumeration {
                      enum enable {
                        value 1 ;
                        description 'Apply next-hop-self for EBGP route.'
                                    ;
                      }
                      enum all {
                        value 2 ;
                        description 'Apply next-hop-self for both EBGP and IBGP'
                                  + ' route.'
                                    ;
                      }
                    }
                  }
                  leaf remove-private-as {
                    description 'EBGP use to remove private AS number.'
                                ;
                    type enumeration {
                      enum disable {
                        value 0 ;
                      }
                      enum enable {
                        value 1 ;
                      }
                    }
                  }
                  leaf route-reflector-client {
                    description 'Set this neighbor as a client peer.'
                                ;
                    type empty ;
                  }
                  leaf send-community {
                    description 'Send community to this neighbor.'
                                ;
                    type empty ;
                  }
                  leaf send-large-community {
                    description 'Send Large-community to this neighbor.'
                                ;
                    type empty ;
                    ncd:revise-date 2020-04-16 ;
                  }
                  leaf send-med {
                    description 'Send metric attribute to this neighbor.'
                                ;
                    type empty ;
                  }
                  leaf split-update-group {
                    description 'Split neighbor from update group.'
                                ;
                    type empty ;
                  }
                  container advertise-map {
                    presence 'Specify route-map for conditional advertisement'
                             ;
                    leaf advertise-map-name {
                      description 'Advertise route-map name.'
                                  ;
                      type string {
                        length 1..200 ;
                      }
                      mandatory true ;
                    }
                    choice advertise-map {
                      description 'Specify route-map for conditional advertisem'
                                + 'ent.'
                                  ;
                      mandatory true ;
                      case exist-map {
                        description 'Advertise prefix only if prefix exists.'
                                    ;
                        leaf exist-map-name {
                          description 'Advertise prefix only if prefix exists.'
                                      ;
                          type string {
                            length 1..200 ;
                          }
                          mandatory true ;
                        }
                      }
                      case nonexist-map {
                        description 'Advertise prefix only if prefix does not e'
                                  + 'xist.'
                                    ;
                        leaf nonexist-map-name {
                          description 'Advertise prefix only if prefix does not'
                                    + ' exist.'
                                      ;
                          type string {
                            length 1..200 ;
                          }
                          mandatory true ;
                        }
                      }
                    }
                  }
                  leaf weight {
                    description 'Set weight for routes from this neighbor.'
                                ;
                    type uint32 {
                      range 1..65535 ;
                    }
                  }
                  container neighbor-extend {
                    description 'Specify a neighbor.'
                                ;
                    leaf prefix-list-in-name {
                      description 'Apply prefix list to incoming routes.'
                                  ;
                      type string {
                        length 1..169 ;
                      }
                    }
                    leaf prefix-list-out-name {
                      description 'Apply prefix list to outbound routes.'
                                  ;
                      type string {
                        length 1..169 ;
                      }
                    }
                    leaf route-map-in-name {
                      description 'Apply route-map to incoming routes.'
                                  ;
                      type string {
                        length 1..200 ;
                      }
                    }
                    leaf route-map-out-name {
                      description 'Apply route-map to outbound routes.'
                                  ;
                      type string {
                        length 1..200 ;
                      }
                    }
                    container maximum-prefix {
                      description 'The action that generated when threshold val'
                                + 'ue reached.'
                                  ;
                      presence 'The action that generated when threshold value '
                             + 'reached'
                               ;
                      leaf maximum-prefix-number {
                        description 'Maximum number of prefix limit.'
                                    ;
                        type uint32 {
                          range 1..4294967295 ;
                        }
                        mandatory true ;
                      }
                      leaf maximum-prefix-threshold {
                        description 'Threshold value(%) at which to generate a '
                                  + 'warning.'
                                    ;
                        type uint32 {
                          range 1..100 ;
                        }
                        mandatory true ;
                      }
                      choice maximum-prefix-action {
                        description 'Maximum number of prefix accept from this '
                                  + 'peer.'
                                    ;
                        mandatory true ;
                        case peer-action {
                          description 'The action that generated when threshold'
                                    + ' value reached.'
                                      ;
                          leaf action {
                            description 'The action that generated when threshold value reached.'
                                        ;
                            type enumeration {
                              enum down {
                                value 0 ;
                                description 'Break down BGP connection after limit is exceeded.'
                                            ;
                              }
                              enum warning-only {
                                value 1 ;
                                description 'Only give warning message when limit is exceeded.'
                                            ;
                              }
                              enum drop-routes {
                                value 2 ;
                                description 'Drop routes that exceed the maximum-prefix.'
                                            ;
                              }
                            }
                            mandatory true ;
                          }
                        }
                        case restart {
                          description 'Restart BGP connection after limit is ex'
                                    + 'ceeded.'
                                      ;
                          leaf restart-time {
                            description 'Restart interval in minutes.'
                                        ;
                            type uint32 {
                              range 1..30000 ;
                            }
                            units min ;
                            mandatory true ;
                          }
                        }
                      }
                    }
                    leaf routepolicy-in-name {
                      description 'Route policy name applied to the inbound rou'
                                + 'tes.'
                                  ;
                      type string {
                        length 1..200 ;
                      }
                      ncd:revise-date 2015-05-18 ;
                    }
                    leaf routepolicy-out-name {
                      description 'Route policy name applied to the outbound ro'
                                + 'utes.'
                                  ;
                      type string {
                        length 1..200 ;
                      }
                      ncd:revise-date 2015-05-18 ;
                    }
                  }
                  leaf nouse-peergroup-config {
                    status obsolete {
                      ncd:revise-date 2015-05-18 ;
                    }
                    description 'Peer do not use group config set.Only for get '
                              + 'operation.'
                                ;
                    type empty ;
                  }
                  container route-server-client {
                    description 'Set route server client only valid for ebgp pe'
                              + 'er.'
                                ;
                    presence route-server-client ;
                    leaf route-svr-client {
                      description 'Set route server client only valid for ebgp '
                                + 'peer.'
                                  ;
                      type empty ;
                      mandatory true ;
                    }
                    ncd:revise-date 2020-04-07 ;
                  }
                }
              }
            }
          }
          container address-family-vpnv4 {
            description 'Configuration in address family VPNv4 mode.'
                        ;
            presence 'VPNv4 address family.'
                     ;
            leaf defaults-set-flag {
              status obsolete {
                ncd:revise-date 2020-07-28 ;
              }
              description 'Flag of defaults.Only for get operation.When this va'
                        + 'lue expressed as a binary,The lowest bit indicate di'
                        + 'stance-ibgp,the next bit distance-ebgp,then maxpaths'
                        + '-ebgp,then default-metric,then wait-for-end-of-rib,t'
                        + 'hen constrain-rt-filter.'
                          ;
              type uint32 {
                range 0..4294967295 ;
              }
              default 0 ;
              ncd:revise-date 2015-06-02 ;
            }
            leaf advertise-active-only {
              description 'Advertise the active routes only.'
                          ;
              type empty ;
            }
            leaf bestpath-external {
              description 'Routes from external peer or RR client are preferred'
                        + ' in bestpath selection.'
                          ;
              type empty ;
            }
            leaf bestpath-igp-metric-ignore {
              description 'Ignore IGP metric in bestpath selection.'
                          ;
              type empty ;
            }
            leaf default-metric {
              description 'Set metric of BGP routes without MED.'
                          ;
              type uint32 {
                range 0..4294967295 ;
              }
              default 0 ;
            }
            leaf frr-capability {
              status obsolete {
                ncd:revise-date 2015-05-18 ;
              }
              description 'Enable FRR capability.'
                          ;
              type empty ;
            }
            leaf frr-wtr {
              status obsolete {
                ncd:revise-date 2015-05-18 ;
              }
              description 'Set the WTR time.'
                          ;
              type int32 {
                range 1..12 ;
              }
              units min ;
            }
            leaf label-per-nexthop {
              status obsolete {
                ncd:revise-date 2016-06-12 ;
              }
              description 'Allocate label according to nexthop.'
                          ;
              type empty ;
              ncd:revise-date 2016-01-06 ;
            }
            leaf bgp-label {
              description 'Mpls label mode.'
                          ;
              type enumeration {
                enum per-vrf-by-rt {
                  value 0 ;
                  description 'Allocate label according to per-vrf and find VRF'
                            + ' according to route-target.'
                              ;
                }
                enum per-vrf-by-rd {
                  value 3 ;
                  description 'Allocate label according to per-vrf and find VRF'
                            + ' according to route-distinguisher.'
                              ;
                }
                enum per-nexthop {
                  value 1 ;
                  description 'Allocate label according to nexthop.'
                              ;
                }
                enum per-prefix {
                  value 2 ;
                  description 'Allocate label according to prefix.'
                              ;
                }
              }
              default per-vrf-by-rt ;
              ncd:revise-date 2016-06-12 ;
            }
            leaf bestpath-igp-metric-compare {
              description 'Compare IGP metric in maximum-paths.'
                          ;
              type empty ;
              ncd:revise-date 2017-07-05 ;
            }
            leaf nexthop-recursive-default-route {
              description 'Nexthop recursive lookup default-route.'
                          ;
              type enumeration {
                enum enable {
                  value 1 ;
                }
                enum disable {
                  value 0 ;
                }
              }
              default enable ;
              ncd:revise-date 2020-07-28 ;
            }
            leaf nexthop-recursive-null1 {
              description 'Nexthop recursive lookup null1.'
                          ;
              type enumeration {
                enum enable {
                  value 1 ;
                }
                enum disable {
                  value 0 ;
                }
              }
              default enable ;
              ncd:revise-date 2020-12-09 ;
            }
            container damp-vpnv4 {
              description 'Enable route-flap dampening.'
                          ;
              presence damp-vpnv4 ;
              choice damp {
                description 'Enable route-flap dampening.'
                            ;
                case route-map {
                  description 'Route-map to specify criteria for dampening.'
                              ;
                  leaf route-map-name {
                    description 'Route-map to specify criteria for dampening.'
                                ;
                    type string {
                      length 1..200 ;
                    }
                  }
                  leaf route-policy-name {
                    description 'Route-policy to specify criteria for dampening.'
                                ;
                    type string {
                      length 1..200 ;
                    }
                    ncd:revise-date 2020-10-10 ;
                  }
                }
                case parameter {
                  description 'Damp parameter.'
                              ;
                  leaf half-time {
                    description 'Half-life time for the penalty.'
                                ;
                    type uint32 {
                      range 1..45 ;
                    }
                    units min ;
                    mandatory true ;
                  }
                  leaf reuse {
                    description 'Value to start reusing a route.'
                                ;
                    type uint32 {
                      range 1..20000 ;
                    }
                    mandatory true ;
                  }
                  leaf suppress {
                    description 'Value to start suppressing a route.'
                                ;
                    type uint32 {
                      range 1..20000 ;
                    }
                    mandatory true ;
                  }
                  leaf max-suppress-time {
                    description 'Maximum duration to suppress a route.'
                                ;
                    type uint32 {
                      range 1..255 ;
                    }
                    mandatory true ;
                  }
                }
              }
            }
            container neighbor-vpnv4 {
              description 'Specify a neighbor.'
                          ;
              presence neighbor-vpnv4 ;
              container neighbor-group {
                description 'Specify a peergroup neighbor.'
                            ;
                list neighbor-peergroup {
                  description 'Specify a neighbor.'
                              ;
                  key neighbor-group ;
                  leaf neighbor-group {
                    description 'Peer group name (1-31 characters).'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf monitor {
                    description 'Config BMP monitor for the address family of t'
                              + 'his neighbor.'
                                ;
                    type enumeration {
                      enum disable {
                        value 2 ;
                      }
                      enum enable {
                        value 1 ;
                      }
                      enum inherit-global-config {
                        value 0 ;
                      }
                    }
                    ncd:revise-date 2019-07-29 ;
                  }
                  leaf advertise-maximum-prefix {
                    description 'Maximum number of prefix send to this peer.'
                                ;
                    type uint32 {
                      range 1..4294967295 ;
                    }
                    ncd:revise-date 2016-01-06 ;
                  }
                  leaf allowas-in {
                    description 'Accept as-path with my AS present in it.'
                                ;
                    type uint32 {
                      range 1..10 ;
                    }
                  }
                  leaf as-path-loopcheck {
                    description 'Check as-path sending BGP routing to EBGP neig'
                              + 'hbor.'
                                ;
                    type empty ;
                  }
                  leaf maxas-in {
                    description 'Accept as-path not exceeded maxas-in.'
                                ;
                    type uint32 {
                      range 1..250 ;
                    }
                  }
                  leaf next-hop-self {
                    description 'Disable the next hop calculation for this neig'
                              + 'hbor.'
                                ;
                    type enumeration {
                      enum enable {
                        value 1 ;
                        description 'Apply next-hop-self for EBGP route.'
                                    ;
                      }
                      enum all {
                        value 2 ;
                        description 'Apply next-hop-self for both EBGP and IBGP'
                                  + ' route.'
                                    ;
                      }
                    }
                  }
                  choice nh-unchanged {
                    case next-hop-unchanged {
                      description 'NEXT_HOP of the IBGP path propagated unchang'
                                + 'ed to this neighbor.'
                                  ;
                      leaf next-hop-unchanged {
                        description 'Propagate next hop unchanged for IBGP path'
                                  + 's to this neighbor.'
                                    ;
                        type empty ;
                      }
                    }
                    case next-hop-unchanged-all {
                      description 'NEXT_HOP of either EBGP or IBGP path propaga'
                                + 'ted unchanged to this neighbor.'
                                  ;
                      leaf next-hop-unchanged-all {
                        description 'NEXT_HOP of either EBGP or IBGP path propa'
                                  + 'gated unchanged to this neighbor.'
                                    ;
                        type empty ;
                      }
                      ncd:revise-date 2020-04-07 ;
                    }
                  }
                  leaf remove-private-as {
                    description 'EBGP use to remove private AS number.'
                                ;
                    type enumeration {
                      enum disable {
                        value 0 ;
                      }
                      enum enable {
                        value 1 ;
                      }
                    }
                  }
                  leaf route-reflector-client {
                    description 'Set this neighbor as a client peer.'
                                ;
                    type empty ;
                  }
                  leaf send-community {
                    description 'Send community to this neighbor.'
                                ;
                    type empty ;
                  }
                  leaf send-large-community {
                    description 'Send Large-community to this neighbor.'
                                ;
                    type empty ;
                    ncd:revise-date 2020-04-16 ;
                  }
                  leaf send-med {
                    description 'Send metric attribute to this neighbor.'
                                ;
                    type empty ;
                  }
                  leaf inherit-igp-metric {
                    description 'Med attribute inherited from IGP metric before'
                              + ' sending updates'
                                ;
                    type empty ;
                    ncd:revise-date 2017-07-25 ;
                  }
                  leaf split-update-group {
                    description 'Split neighbor from update group.'
                                ;
                    type empty ;
                  }
                  leaf weight {
                    description 'Set weight for routes from this neighbor.'
                                ;
                    type uint32 {
                      range 1..65535 ;
                    }
                  }
                  leaf default-originate-all {
                    description 'Notify all VPN default route.'
                                ;
                    type empty ;
                  }
                  leaf default-originate-routemap {
                    description 'Map external entry attributes into routing tab'
                              + 'le.'
                                ;
                    type string {
                      length 1..200 ;
                    }
                    ncd:revise-date 2020-07-28 ;
                  }
                  leaf default-originate-routepolicy {
                    description 'Set external entry attributes into routing tab'
                              + 'le.'
                                ;
                    type string {
                      length 1..200 ;
                    }
                    ncd:revise-date 2020-10-10 ;
                  }
                  leaf aigp {
                    description 'Enable AIGP for this neighbor.'
                                ;
                    type empty ;
                    ncd:revise-date 2017-11-01 ;
                  }
                  container default-originate-vrf {
                    description 'Originate default route to this neighbor for c'
                              + 'ertain vrf.'
                                ;
                    list default-originate-vrf {
                      description 'Originate default route to this neighbor for'
                                + ' certain vrf.'
                                  ;
                      key vrf-name ;
                      leaf vrf-name {
                        description 'VPN Routing/Forwarding instance.'
                                    ;
                        type string {
                          length 1..32 ;
                        }
                      }
                      choice prefix-list {
                        description 'Prefix list name.'
                                    ;
                        case peer-list {
                          description 'Prefix list name of peer list.'
                                      ;
                          leaf peer-list-name {
                            description 'Prefix list name of peer list.'
                                        ;
                            type string {
                              length 1..169 ;
                            }
                          }
                          ncd:revise-date 2015-12-08 ;
                        }
                        case vrf-peer-list {
                          description 'Prefix list name of VRF routes list.'
                                      ;
                          leaf vrf-peer-list-name {
                            description 'Prefix list name of VRF routes list.'
                                        ;
                            type string {
                              length 1..169 ;
                            }
                          }
                          ncd:revise-date 2019-09-04 ;
                        }
                        ncd:revise-date 2015-12-08 ;
                      }
                    }
                  }
                  container virtual {
                    description 'Set spoke PE.'
                                ;
                    presence virtual ;
                    leaf virtual-spoke {
                      description 'Enable spoke PE.'
                                  ;
                      type empty ;
                      mandatory true ;
                    }
                    leaf reflect-next-hop-self {
                      description 'Set next-hop self when reflection.'
                                  ;
                      type empty ;
                    }
                    leaf check-upstream-pe {
                      description 'Check upstream PE when advertising default r'
                                + 'oute.'
                                  ;
                      type empty ;
                    }
                    leaf by-vrf {
                      description 'Send specific route by default-originate con'
                                + 'fig.'
                                  ;
                      type empty ;
                      ncd:revise-date 2019-12-31 ;
                    }
                  }
                  container advertise-map {
                    description 'Specify route-map for conditional advertisemen'
                              + 't.'
                                ;
                    presence 'Specify route-map for conditional advertisement'
                             ;
                    leaf advertise-map-name {
                      description 'Advertise route-map name.'
                                  ;
                      type string {
                        length 1..200 ;
                      }
                      mandatory true ;
                    }
                    choice advertise-map {
                      description 'Specify route-map for conditional advertisem'
                                + 'ent.'
                                  ;
                      mandatory true ;
                      case exist-map {
                        description 'Advertise prefix only if prefix exists.'
                                    ;
                        leaf exist-map-name {
                          description 'Advertise prefix only if prefix exists.'
                                      ;
                          type string {
                            length 1..200 ;
                          }
                          mandatory true ;
                        }
                      }
                      case nonexist-map {
                        description 'Advertise prefix only if prefix does not e'
                                  + 'xist.'
                                    ;
                        leaf nonexist-map-name {
                          description 'Advertise prefix only if prefix does not'
                                    + ' exist.'
                                      ;
                          type string {
                            length 1..200 ;
                          }
                          mandatory true ;
                        }
                      }
                    }
                  }
                  leaf capability-orf-prefix-list {
                    description 'Advertise prefixlist ORF capability to this ne'
                              + 'ighbor.'
                                ;
                    type enumeration {
                      enum receive {
                        value 1 ;
                        description 'Capability to receive the ORF from this ne'
                                  + 'ighbor.'
                                    ;
                      }
                      enum send {
                        value 2 ;
                        description 'Capability to send the ORF to this neighbo'
                                  + 'r.'
                                    ;
                      }
                      enum both {
                        value 3 ;
                        description 'Capability to send and receive the ORF.'
                                    ;
                      }
                    }
                  }
                  leaf adv-tunnel-encap {
                    description 'Advertise tunnel encapsulation type'
                                ;
                    type enumeration {
                      enum mpls {
                        value 2 ;
                      }
                      enum srv6 {
                        value 4 ;
                      }
                    }
                    ncd:revise-date 2020-08-18 ;
                  }
                  container neighbor-extend {
                    description 'Specify a neighbor.'
                                ;
                    leaf additional-paths-receive {
                      description 'Receive additional paths from this neighbor.'
                                  ;
                      type empty ;
                    }
                    container maximum-prefix {
                      description 'The action that generated when threshold val'
                                + 'ue reached.'
                                  ;
                      presence 'The action that generated when threshold value '
                             + 'reached'
                               ;
                      leaf maximum-prefix-number {
                        description 'Maximum number of prefix limit.'
                                    ;
                        type uint32 {
                          range 1..4294967295 ;
                        }
                        mandatory true ;
                      }
                      leaf maximum-prefix-threshold {
                        description 'Threshold value(%) at which to generate a '
                                  + 'warning.'
                                    ;
                        type uint32 {
                          range 1..100 ;
                        }
                        mandatory true ;
                      }
                      choice maximum-prefix-action {
                        description 'The action that generated when threshold v'
                                  + 'alue reached.'
                                    ;
                        mandatory true ;
                        case peer-action {
                          description 'The action that generated when threshold'
                                    + ' value reached.'
                                      ;
                          leaf action {
                            description 'The action that generated when threshold value reached.'
                                        ;
                            type enumeration {
                              enum down {
                                value 0 ;
                                description 'Break down BGP connection after limit is exceeded.'
                                            ;
                              }
                              enum warning-only {
                                value 1 ;
                                description 'Only give warning message when limit is exceeded.'
                                            ;
                              }
                              enum drop-routes {
                                value 2 ;
                                description 'Drop routes that exceed the maximum-prefix.'
                                            ;
                              }
                            }
                            mandatory true ;
                          }
                        }
                        case restart {
                          description 'Restart BGP connection after limit is ex'
                                    + 'ceeded.'
                                      ;
                          leaf restart-time {
                            description 'Restart interval in minutes.'
                                        ;
                            type uint32 {
                              range 1..30000 ;
                            }
                            units min ;
                            mandatory true ;
                          }
                        }
                      }
                    }
                    leaf prefix-list-in-name {
                      description 'Apply prefix list to incoming routes.'
                                  ;
                      type string {
                        length 1..169 ;
                      }
                    }
                    leaf prefix-list-out-name {
                      description 'Apply  prefix list to outbound routes.'
                                  ;
                      type string {
                        length 1..169 ;
                      }
                    }
                    leaf route-map-in-name {
                      description 'Apply route-map to incoming routes.'
                                  ;
                      type string {
                        length 1..200 ;
                      }
                    }
                    leaf route-map-out-name {
                      description 'Apply route-map to outbound routes.'
                                  ;
                      type string {
                        length 1..200 ;
                      }
                    }
                    container diverse-path-receive {
                      description 'Advertise diverse path to this neighbor.'
                                  ;
                      presence diverse-path-receive ;
                      choice diverse-path-receive {
                        description 'Advertise diverse path to this neighbor.'
                                    ;
                        mandatory true ;
                        case backup {
                          description 'Advertisement of the backup path.'
                                      ;
                          leaf backup {
                            description 'Advertisement of the backup path.'
                                        ;
                            type empty ;
                            mandatory true ;
                          }
                        }
                        case multipath {
                          description 'Sequence number of multipath.'
                                      ;
                          leaf sequence-number {
                            description 'Sequence number of multipath.'
                                        ;
                            type uint32 {
                              range 2..32 ;
                            }
                            mandatory true ;
                          }
                        }
                      }
                      leaf route-map {
                        description 'Apply route-map to neighbor.'
                                    ;
                        type string {
                          length 1..200 ;
                        }
                        ncd:revise-date 2016-01-06 ;
                      }
                    }
                    container additional-paths-send {
                      description 'Send additional paths to this neighbor.'
                                  ;
                      choice additional-paths-send {
                        description 'Send additional paths to this neighbor.'
                                    ;
                        default send-one-path ;
                        case send-one-path {
                          description 'Send one additional path to this neighbo'
                                    + 'r.'
                                      ;
                          leaf send {
                            description 'Send additional paths to this neighbor.'
                                        ;
                            type empty ;
                          }
                        }
                        case send-multi-paths {
                          description 'Send additional multi-paths to this neig'
                                    + 'hbor.'
                                      ;
                          leaf paths-number {
                            description 'Number of paths for a prefix.'
                                        ;
                            type uint32 {
                              range 2..32 ;
                            }
                            mandatory true ;
                          }
                          leaf prefixlist {
                            description 'Prefixlist of filtering additional paths.'
                                        ;
                            type string {
                              length 1..169 ;
                            }
                          }
                        }
                      }
                    }
                    leaf routepolicy-in-name {
                      description 'Route policy name applied to the inbound rou'
                                + 'tes.'
                                  ;
                      type string {
                        length 1..200 ;
                      }
                      ncd:revise-date 2015-05-18 ;
                    }
                    leaf routepolicy-out-name {
                      description 'Route policy name applied to the outbound ro'
                                + 'utes.'
                                  ;
                      type string {
                        length 1..200 ;
                      }
                      ncd:revise-date 2015-05-18 ;
                    }
                    container connector {
                      description 'Send connector to this neighbor.'
                                  ;
                      presence connector ;
                      leaf send-connector {
                        description 'Send connector to this neighbor.'
                                    ;
                        type empty ;
                        mandatory true ;
                      }
                      leaf route-map {
                        description 'Apply route-map to neighbor.'
                                    ;
                        type string {
                          length 1..200 ;
                        }
                      }
                      ncd:revise-date 2016-01-06 ;
                    }
                    container withdraw {
                      description 'Withdraw routes when state of track-group is'
                                + ' down.'
                                  ;
                      presence withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                      ncd:revise-date 2016-02-06 ;
                    }
                    container second-withdraw {
                      description 'Withdraw routes when state of the second tra'
                                + 'ck-group is down.'
                                  ;
                      presence second-withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                      ncd:revise-date 2018-07-12 ;
                    }
                  }
                  container route-filter-group {
                    description 'Specify a neighbor to join a route-filter-grou'
                              + 'p.'
                                ;
                    presence route-filter-group ;
                    leaf filter-group {
                      description 'Route filter group name (1-31 characters).'
                                  ;
                      type string {
                        length 1..31 ;
                      }
                      mandatory true ;
                    }
                    leaf next-hop-self {
                      description 'Disable the next hop calculation for this ne'
                                + 'ighbor.'
                                  ;
                      type empty ;
                    }
                    ncd:revise-date 2017-06-12 ;
                  }
                  leaf announce-sid {
                    description 'Enable Prefix-SID attribute for this neighbor.'
                                ;
                    type enumeration {
                      enum enable {
                        value 1 ;
                        description 'Enable Prefix-SID attribute for this neigh'
                                  + 'bor.'
                                    ;
                      }
                    }
                    ncd:revise-date 2018-05-14 ;
                  }
                  leaf soft-reconfig {
                    description 'Neighbor soft reconfiguration.'
                                ;
                    type enumeration {
                      enum soft-reconfiguration {
                        value 1 ;
                        description Soft-reconfiguration. ;
                      }
                      enum enforce-soft-reconfiguration {
                        value 2 ;
                        description 'Enforce soft-reconfiguration instead of se'
                                  + 'nding route-refresh.'
                                    ;
                      }
                    }
                    ncd:revise-date 2019-08-08 ;
                  }
                  leaf vpn-orf {
                    description 'Peer route-target ORF capability'
                                ;
                    type enumeration {
                      enum disable {
                        value 0 ;
                        description 'Disable peer route-target ORF capability'
                                    ;
                      }
                      enum enable {
                        value 1 ;
                        description 'Enable peer route-target ORF capability'
                                    ;
                      }
                    }
                    ncd:revise-date 2020-02-08 ;
                  }
                  leaf send-link-bw {
                    description 'Send link bandwidth to this neighbor.'
                                ;
                    type enumeration {
                      enum disable {
                        value 0 ;
                        description 'Disable peer send link bandwidth'
                                    ;
                      }
                      enum enable {
                        value 1 ;
                        description 'Enable peer send link bandwidth'
                                    ;
                      }
                    }
                    ncd:revise-date 2019-10-22 ;
                  }
                  container route-server-client {
                    description 'Set route server client only valid for ebgp pe'
                              + 'er.'
                                ;
                    presence route-server-client ;
                    leaf route-svr-client {
                      description 'Set route server client only valid for ebgp '
                                + 'peer.'
                                  ;
                      type empty ;
                      mandatory true ;
                    }
                    ncd:revise-date 2020-04-07 ;
                  }
                }
              }
              container neighbor-ipv4 {
                description 'Specify a IPv4 neighbor.'
                            ;
                list neighbor {
                  description 'Specify a neighbor.'
                              ;
                  key ipv4-addr ;
                  leaf ipv4-addr {
                    description 'Neighbor IPv4 address.'
                                ;
                    type ncd:ipv4-address ;
                  }
                  leaf joined-group {
                    description 'Only for read operation. The joined group name.'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf monitor {
                    description 'Config BMP monitor for the address family of t'
                              + 'his neighbor.'
                                ;
                    type enumeration {
                      enum disable {
                        value 2 ;
                      }
                      enum enable {
                        value 1 ;
                      }
                      enum inherit-global-config {
                        value 0 ;
                      }
                    }
                    ncd:revise-date 2019-07-29 ;
                  }
                  leaf advertise-maximum-prefix {
                    description 'Maximum number of prefix send to this peer.'
                                ;
                    type uint32 {
                      range 1..4294967295 ;
                    }
                    ncd:revise-date 2016-01-06 ;
                  }
                  leaf allowas-in {
                    description 'Accept as-path with my AS present in it.'
                                ;
                    type uint32 {
                      range 1..10 ;
                    }
                  }
                  leaf as-path-loopcheck {
                    description 'Check as-path sending BGP routing to EBGP neig'
                              + 'hbor.'
                                ;
                    type empty ;
                  }
                  leaf maxas-in {
                    description 'Accept as-path not exceeded maxas-in.'
                                ;
                    type uint32 {
                      range 1..250 ;
                    }
                  }
                  leaf next-hop-self {
                    description 'Disable the next hop calculation for this neig'
                              + 'hbor.'
                                ;
                    type enumeration {
                      enum enable {
                        value 1 ;
                        description 'Apply next-hop-self for EBGP route.'
                                    ;
                      }
                      enum all {
                        value 2 ;
                        description 'Apply next-hop-self for both EBGP and IBGP'
                                  + ' route.'
                                    ;
                      }
                    }
                  }
                  choice nh-unchanged {
                    case next-hop-unchanged {
                      description 'NEXT_HOP of the IBGP path propagated unchang'
                                + 'ed to this neighbor.'
                                  ;
                      leaf next-hop-unchanged {
                        description 'Propagate next hop unchanged for IBGP path'
                                  + 's to this neighbor.'
                                    ;
                        type empty ;
                      }
                    }
                    case next-hop-unchanged-all {
                      description 'NEXT_HOP of either EBGP or IBGP path propaga'
                                + 'ted unchanged to this neighbor.'
                                  ;
                      leaf next-hop-unchanged-all {
                        description 'NEXT_HOP of either EBGP or IBGP path propa'
                                  + 'gated unchanged to this neighbor.'
                                    ;
                        type empty ;
                      }
                      ncd:revise-date 2020-04-07 ;
                    }
                  }
                  leaf remove-private-as {
                    description 'EBGP use to remove private AS number.'
                                ;
                    type enumeration {
                      enum disable {
                        value 0 ;
                      }
                      enum enable {
                        value 1 ;
                      }
                    }
                  }
                  leaf route-reflector-client {
                    description 'Set this neighbor as a client peer.'
                                ;
                    type empty ;
                  }
                  leaf send-community {
                    description 'Send community to this neighbor.'
                                ;
                    type empty ;
                  }
                  leaf send-large-community {
                    description 'Send Large-community to this neighbor.'
                                ;
                    type empty ;
                    ncd:revise-date 2020-04-16 ;
                  }
                  leaf send-med {
                    description 'Send metric attribute to this neighbor.'
                                ;
                    type empty ;
                  }
                  leaf inherit-igp-metric {
                    description 'Med attribute inherited from IGP metric before'
                              + ' sending updates'
                                ;
                    type empty ;
                    ncd:revise-date 2017-07-25 ;
                  }
                  leaf split-update-group {
                    description 'Split neighbor from update group.'
                                ;
                    type empty ;
                  }
                  leaf weight {
                    description 'Set weight for routes from this neighbor.'
                                ;
                    type uint32 {
                      range 1..65535 ;
                    }
                  }
                  leaf default-originate-all {
                    description 'Notify all VPN default route.'
                                ;
                    type empty ;
                  }
                  leaf default-originate-routemap {
                    description 'Map external entry attributes into routing tab'
                              + 'le.'
                                ;
                    type string {
                      length 1..200 ;
                    }
                    ncd:revise-date 2020-07-28 ;
                  }
                  leaf default-originate-routepolicy {
                    description 'Set external entry attributes into routing tab'
                              + 'le.'
                                ;
                    type string {
                      length 1..200 ;
                    }
                    ncd:revise-date 2020-10-10 ;
                  }
                  leaf aigp {
                    description 'Enable AIGP for this neighbor.'
                                ;
                    type empty ;
                    ncd:revise-date 2017-11-01 ;
                  }
                  container default-originate-vrf {
                    description 'Originate default route to this neighbor for c'
                              + 'ertain vrf.'
                                ;
                    list default-originate-vrf {
                      description 'Originate default route to this neighbor for'
                                + ' certain vrf.'
                                  ;
                      key vrf-name ;
                      leaf vrf-name {
                        description 'VPN Routing/Forwarding instance.'
                                    ;
                        type string {
                          length 1..32 ;
                        }
                      }
                      choice prefix-list {
                        description 'Prefix list name.'
                                    ;
                        case peer-list {
                          description 'Prefix list name of peer list.'
                                      ;
                          leaf peer-list-name {
                            description 'Prefix list name of peer list.'
                                        ;
                            type string {
                              length 1..169 ;
                            }
                          }
                          ncd:revise-date 2015-12-08 ;
                        }
                        case vrf-peer-list {
                          description 'Prefix list name of VRF routes list.'
                                      ;
                          leaf vrf-peer-list-name {
                            description 'Prefix list name of VRF routes list.'
                                        ;
                            type string {
                              length 1..169 ;
                            }
                          }
                          ncd:revise-date 2019-09-04 ;
                        }
                        ncd:revise-date 2015-12-08 ;
                      }
                    }
                  }
                  container virtual {
                    description 'Set spoke PE.'
                                ;
                    presence virtual ;
                    leaf virtual-spoke {
                      description 'Enable spoke PE.'
                                  ;
                      type empty ;
                      mandatory true ;
                    }
                    leaf reflect-next-hop-self {
                      description 'Set next-hop self when reflection.'
                                  ;
                      type empty ;
                    }
                    leaf check-upstream-pe {
                      description 'Set next-hop self when reflection.'
                                  ;
                      type empty ;
                    }
                    leaf by-vrf {
                      description 'Send specific route by default-originate con'
                                + 'fig.'
                                  ;
                      type empty ;
                      ncd:revise-date 2019-12-31 ;
                    }
                  }
                  container advertise-map {
                    description 'Specify route-map for conditional advertisemen'
                              + 't.'
                                ;
                    presence 'Specify route-map for conditional advertisement'
                             ;
                    leaf advertise-map-name {
                      description 'Advertise route-map name.'
                                  ;
                      type string {
                        length 1..200 ;
                      }
                      mandatory true ;
                    }
                    choice advertise-map {
                      description 'Specify route-map for conditional advertisem'
                                + 'ent.'
                                  ;
                      mandatory true ;
                      case exist-map {
                        description 'Advertise prefix only if prefix exists.'
                                    ;
                        leaf exist-map-name {
                          description 'Advertise prefix only if prefix exists.'
                                      ;
                          type string {
                            length 1..200 ;
                          }
                          mandatory true ;
                        }
                      }
                      case nonexist-map {
                        description 'Advertise prefix only if prefix does not e'
                                  + 'xist.'
                                    ;
                        leaf nonexist-map-name {
                          description 'Advertise prefix only if prefix does not'
                                    + ' exist.'
                                      ;
                          type string {
                            length 1..200 ;
                          }
                          mandatory true ;
                        }
                      }
                    }
                  }
                  leaf adv-tunnel-encap {
                    description 'Advertise tunnel encapsulation type'
                                ;
                    type enumeration {
                      enum mpls {
                        value 2 ;
                      }
                      enum srv6 {
                        value 4 ;
                      }
                    }
                    ncd:revise-date 2020-08-18 ;
                  }
                  leaf capability-orf-prefix-list {
                    description 'Advertise prefixlist ORF capability to this ne'
                              + 'ighbor.'
                                ;
                    type enumeration {
                      enum receive {
                        value 1 ;
                        description 'Capability to receive the ORF from this ne'
                                  + 'ighbor.'
                                    ;
                      }
                      enum send {
                        value 2 ;
                        description 'Capability to send the ORF to this neighbo'
                                  + 'r.'
                                    ;
                      }
                      enum both {
                        value 3 ;
                        description 'Capability to send and receive the ORF.'
                                    ;
                      }
                    }
                  }
                  container neighbor-extend {
                    description 'Specify a neighbor.'
                                ;
                    leaf additional-paths-receive {
                      description 'Receive additional paths from this neighbor.'
                                  ;
                      type empty ;
                    }
                    container maximum-prefix {
                      description 'The action that generated when threshold val'
                                + 'ue reached.'
                                  ;
                      presence 'The action that generated when threshold value '
                             + 'reached'
                               ;
                      leaf maximum-prefix-number {
                        description 'Maximum number of prefix limit.'
                                    ;
                        type uint32 {
                          range 1..4294967295 ;
                        }
                        mandatory true ;
                      }
                      leaf maximum-prefix-threshold {
                        description 'Threshold value(%) at which to generate a '
                                  + 'warning.'
                                    ;
                        type uint32 {
                          range 1..100 ;
                        }
                        mandatory true ;
                      }
                      choice maximum-prefix-action {
                        description 'The action that generated when threshold v'
                                  + 'alue reached.'
                                    ;
                        mandatory true ;
                        case peer-action {
                          description 'The action that generated when threshold'
                                    + ' value reached.'
                                      ;
                          leaf action {
                            description 'The action that generated when threshold value reached.'
                                        ;
                            type enumeration {
                              enum down {
                                value 0 ;
                                description 'Break down BGP connection after limit is exceeded.'
                                            ;
                              }
                              enum warning-only {
                                value 1 ;
                                description 'Only give warning message when limit is exceeded.'
                                            ;
                              }
                              enum drop-routes {
                                value 2 ;
                                description 'Drop routes that exceed the maximum-prefix.'
                                            ;
                              }
                            }
                            mandatory true ;
                          }
                        }
                        case restart {
                          description 'Restart BGP connection after limit is ex'
                                    + 'ceeded.'
                                      ;
                          leaf restart-time {
                            description 'Restart interval in minutes.'
                                        ;
                            type uint32 {
                              range 1..30000 ;
                            }
                            units min ;
                            mandatory true ;
                          }
                        }
                      }
                    }
                    leaf prefix-list-in-name {
                      description 'Apply prefix list to incoming routes.'
                                  ;
                      type string {
                        length 1..169 ;
                      }
                    }
                    leaf prefix-list-out-name {
                      description 'Apply  prefix list to outbound routes.'
                                  ;
                      type string {
                        length 1..169 ;
                      }
                    }
                    leaf route-map-in-name {
                      description 'Apply route-map to incoming routes.'
                                  ;
                      type string {
                        length 1..200 ;
                      }
                    }
                    leaf route-map-out-name {
                      description 'Apply route-map to outbound routes.'
                                  ;
                      type string {
                        length 1..200 ;
                      }
                    }
                    container diverse-path-receive {
                      description 'Advertise diverse path to this neighbor.'
                                  ;
                      presence diverse-path-receive ;
                      choice diverse-path-receive {
                        description 'Advertise diverse path to this neighbor.'
                                    ;
                        mandatory true ;
                        case backup {
                          description 'Advertisement of the backup path.'
                                      ;
                          leaf backup {
                            description 'Advertisement of the backup path.'
                                        ;
                            type empty ;
                            mandatory true ;
                          }
                        }
                        case multipath {
                          description 'Sequence number of multipath.'
                                      ;
                          leaf sequence-number {
                            description 'Sequence number of multipath.'
                                        ;
                            type uint32 {
                              range 2..32 ;
                            }
                            mandatory true ;
                          }
                        }
                      }
                      leaf route-map {
                        description 'Apply route-map to neighbor.'
                                    ;
                        type string {
                          length 1..200 ;
                        }
                        ncd:revise-date 2016-01-06 ;
                      }
                    }
                    container additional-paths-send {
                      description 'Send additional paths to this neighbor.'
                                  ;
                      choice additional-paths-send {
                        description 'Send additional paths to this neighbor.'
                                    ;
                        default send-one-path ;
                        case send-one-path {
                          description 'Send one additional path to this neighbo'
                                    + 'r.'
                                      ;
                          leaf send {
                            description 'Send additional paths to this neighbor.'
                                        ;
                            type empty ;
                          }
                        }
                        case send-multi-paths {
                          description 'Send additional multi-paths to this neig'
                                    + 'hbor.'
                                      ;
                          leaf paths-number {
                            description 'Number of paths for a prefix.'
                                        ;
                            type uint32 {
                              range 2..32 ;
                            }
                            mandatory true ;
                          }
                          leaf prefixlist {
                            description 'Prefixlist of filtering additional paths.'
                                        ;
                            type string {
                              length 1..169 ;
                            }
                          }
                        }
                      }
                    }
                    leaf routepolicy-in-name {
                      description 'Route policy name applied to the inbound rou'
                                + 'tes.'
                                  ;
                      type string {
                        length 1..200 ;
                      }
                      ncd:revise-date 2015-05-18 ;
                    }
                    leaf routepolicy-out-name {
                      description 'Route policy name applied to the outbound ro'
                                + 'utes.'
                                  ;
                      type string {
                        length 1..200 ;
                      }
                      ncd:revise-date 2015-05-18 ;
                    }
                    container connector {
                      description 'Send connector to this neighbor.'
                                  ;
                      presence connector ;
                      leaf send-connector {
                        description 'Send connector to this neighbor.'
                                    ;
                        type empty ;
                        mandatory true ;
                      }
                      leaf route-map {
                        description 'Apply route-map to neighbor.'
                                    ;
                        type string {
                          length 1..200 ;
                        }
                      }
                      ncd:revise-date 2016-01-06 ;
                    }
                    container withdraw {
                      description 'Withdraw routes when state of track-group is'
                                + ' down.'
                                  ;
                      presence withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                      ncd:revise-date 2016-02-06 ;
                    }
                    container second-withdraw {
                      description 'Withdraw routes when state of the second tra'
                                + 'ck-group is down.'
                                  ;
                      presence second-withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                      ncd:revise-date 2018-07-12 ;
                    }
                  }
                  leaf nouse-peergroup-config {
                    status obsolete {
                      ncd:revise-date 2015-05-18 ;
                    }
                    description 'Peer do not use group config set.Only for get '
                              + 'operation.'
                                ;
                    type empty ;
                  }
                  container route-filter-group {
                    description 'Specify a neighbor to join a route-filter-grou'
                              + 'p.'
                                ;
                    presence route-filter-group ;
                    leaf filter-group {
                      description 'Route filter group name (1-31 characters).'
                                  ;
                      type string {
                        length 1..31 ;
                      }
                      mandatory true ;
                    }
                    leaf next-hop-self {
                      description 'Disable the next hop calculation for this ne'
                                + 'ighbor.'
                                  ;
                      type empty ;
                    }
                    ncd:revise-date 2017-06-12 ;
                  }
                  leaf announce-sid {
                    description 'Enable Prefix-SID attribute for this neighbor.'
                                ;
                    type enumeration {
                      enum enable {
                        value 1 ;
                        description 'Enable Prefix-SID attribute for this neigh'
                                  + 'bor.'
                                    ;
                      }
                    }
                    ncd:revise-date 2018-05-14 ;
                  }
                  leaf soft-reconfig {
                    description 'Neighbor soft reconfiguration.'
                                ;
                    type enumeration {
                      enum soft-reconfiguration {
                        value 1 ;
                        description Soft-reconfiguration. ;
                      }
                      enum enforce-soft-reconfiguration {
                        value 2 ;
                        description 'Enforce soft-reconfiguration instead of se'
                                  + 'nding route-refresh.'
                                    ;
                      }
                    }
                    ncd:revise-date 2019-08-08 ;
                  }
                  leaf vpn-orf {
                    description 'Peer route-target ORF capability'
                                ;
                    type enumeration {
                      enum disable {
                        value 0 ;
                        description 'Disable peer route-target ORF capability'
                                    ;
                      }
                      enum enable {
                        value 1 ;
                        description 'Enable peer route-target ORF capability'
                                    ;
                      }
                      enum inherit {
                        value 2 ;
                        description 'If the neighbor joined a group, the status'
                                  + ' inherited from group.'
                                    ;
                      }
                    }
                    ncd:revise-date 2020-02-08 ;
                  }
                  leaf send-link-bw {
                    description 'Send link bandwidth to this neighbor.'
                                ;
                    type enumeration {
                      enum disable {
                        value 0 ;
                        description 'Disable peer send link bandwidth'
                                    ;
                      }
                      enum enable {
                        value 1 ;
                        description 'Enable peer send link bandwidth'
                                    ;
                      }
                      enum inherit {
                        value 2 ;
                        description 'If the neighbor joined a group, the status'
                                  + ' inherited from group.'
                                    ;
                      }
                    }
                    ncd:revise-date 2019-10-22 ;
                  }
                  container route-server-client {
                    description 'Set route server client only valid for ebgp pe'
                              + 'er.'
                                ;
                    presence route-server-client ;
                    leaf route-svr-client {
                      description 'Set route server client only valid for ebgp '
                                + 'peer.'
                                  ;
                      type empty ;
                      mandatory true ;
                    }
                    ncd:revise-date 2020-04-07 ;
                  }
                }
              }
              container neighbor-ipv6 {
                description 'Specify a IPv6 neighbor.'
                            ;
                list neighbor {
                  description 'Specify a neighbor.'
                              ;
                  key ipv6-addr ;
                  leaf ipv6-addr {
                    description 'Neighbor IPv6 address.'
                                ;
                    type ncd:ipv6-address ;
                  }
                  leaf joined-group {
                    description 'Only for read operation. The joined group name.'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf monitor {
                    description 'Config BMP monitor for the address family of t'
                              + 'his neighbor.'
                                ;
                    type enumeration {
                      enum disable {
                        value 2 ;
                      }
                      enum enable {
                        value 1 ;
                      }
                      enum inherit-global-config {
                        value 0 ;
                      }
                    }
                    ncd:revise-date 2019-07-29 ;
                  }
                  leaf advertise-maximum-prefix {
                    description 'Maximum number of prefix send to this peer.'
                                ;
                    type uint32 {
                      range 1..4294967295 ;
                    }
                  }
                  leaf allowas-in {
                    description 'Accept as-path with my AS present in it.'
                                ;
                    type uint32 {
                      range 1..10 ;
                    }
                  }
                  leaf as-path-loopcheck {
                    description 'Check as-path sending BGP routing to EBGP neig'
                              + 'hbor.'
                                ;
                    type empty ;
                  }
                  leaf maxas-in {
                    description 'Accept as-path not exceeded maxas-in.'
                                ;
                    type uint32 {
                      range 1..250 ;
                    }
                  }
                  leaf next-hop-self {
                    description 'Disable the next hop calculation for this neig'
                              + 'hbor.'
                                ;
                    type enumeration {
                      enum enable {
                        value 1 ;
                        description 'Apply next-hop-self for EBGP route.'
                                    ;
                      }
                      enum all {
                        value 2 ;
                        description 'Apply next-hop-self for both EBGP and IBGP'
                                  + ' route.'
                                    ;
                      }
                    }
                  }
                  choice nh-unchanged {
                    case next-hop-unchanged {
                      description 'NEXT_HOP of the IBGP path propagated unchang'
                                + 'ed to this neighbor.'
                                  ;
                      leaf next-hop-unchanged {
                        description 'Propagate next hop unchanged for IBGP path'
                                  + 's to this neighbor.'
                                    ;
                        type empty ;
                      }
                    }
                    case next-hop-unchanged-all {
                      description 'NEXT_HOP of either EBGP or IBGP path propaga'
                                + 'ted unchanged to this neighbor.'
                                  ;
                      leaf next-hop-unchanged-all {
                        description 'NEXT_HOP of either EBGP or IBGP path propa'
                                  + 'gated unchanged to this neighbor.'
                                    ;
                        type empty ;
                      }
                      ncd:revise-date 2020-04-07 ;
                    }
                  }
                  leaf remove-private-as {
                    description 'EBGP use to remove private AS number.'
                                ;
                    type enumeration {
                      enum disable {
                        value 0 ;
                      }
                      enum enable {
                        value 1 ;
                      }
                    }
                  }
                  leaf route-reflector-client {
                    description 'Set this neighbor as a client peer.'
                                ;
                    type empty ;
                  }
                  leaf send-community {
                    description 'Send community to this neighbor.'
                                ;
                    type empty ;
                  }
                  leaf send-large-community {
                    description 'Send Large-community to this neighbor.'
                                ;
                    type empty ;
                    ncd:revise-date 2020-04-16 ;
                  }
                  leaf send-med {
                    description 'Send metric attribute to this neighbor.'
                                ;
                    type empty ;
                  }
                  leaf inherit-igp-metric {
                    description 'Med attribute inherited from IGP metric before'
                              + ' sending updates'
                                ;
                    type empty ;
                  }
                  leaf split-update-group {
                    description 'Split neighbor from update group.'
                                ;
                    type empty ;
                  }
                  leaf weight {
                    description 'Set weight for routes from this neighbor.'
                                ;
                    type uint32 {
                      range 1..65535 ;
                    }
                  }
                  leaf default-originate-all {
                    description 'Notify all VPN default route.'
                                ;
                    type empty ;
                  }
                  leaf default-originate-routemap {
                    description 'Map external entry attributes into routing tab'
                              + 'le.'
                                ;
                    type string {
                      length 1..200 ;
                    }
                    ncd:revise-date 2020-07-28 ;
                  }
                  leaf default-originate-routepolicy {
                    description 'Set external entry attributes into routing tab'
                              + 'le.'
                                ;
                    type string {
                      length 1..200 ;
                    }
                    ncd:revise-date 2020-10-10 ;
                  }
                  leaf aigp {
                    description 'Enable AIGP for this neighbor.'
                                ;
                    type empty ;
                  }
                  container default-originate-vrf {
                    description 'Originate default route to this neighbor for c'
                              + 'ertain vrf.'
                                ;
                    list default-originate-vrf {
                      description 'Originate default route to this neighbor for'
                                + ' certain vrf.'
                                  ;
                      key vrf-name ;
                      leaf vrf-name {
                        description 'VPN Routing/Forwarding instance.'
                                    ;
                        type string {
                          length 1..32 ;
                        }
                      }
                      choice prefix-list {
                        description 'Prefix list name.'
                                    ;
                        case peer-list {
                          description 'Prefix list name of peer list.'
                                      ;
                          leaf peer-list-name {
                            description 'Prefix list name of peer list.'
                                        ;
                            type string {
                              length 1..169 ;
                            }
                          }
                          ncd:revise-date 2018-05-14 ;
                        }
                        case vrf-peer-list {
                          description 'Prefix list name of VRF routes list.'
                                      ;
                          leaf vrf-peer-list-name {
                            description 'Prefix list name of VRF routes list.'
                                        ;
                            type string {
                              length 1..169 ;
                            }
                          }
                          ncd:revise-date 2019-09-04 ;
                        }
                        ncd:revise-date 2018-05-14 ;
                      }
                    }
                  }
                  container virtual {
                    description 'Set spoke PE.'
                                ;
                    presence virtual ;
                    leaf virtual-spoke {
                      description 'Enable spoke PE.'
                                  ;
                      type empty ;
                      mandatory true ;
                    }
                    leaf reflect-next-hop-self {
                      description 'Set next-hop self when reflection.'
                                  ;
                      type empty ;
                    }
                    leaf check-upstream-pe {
                      description 'Set next-hop self when reflection.'
                                  ;
                      type empty ;
                    }
                    leaf by-vrf {
                      description 'Send specific route by default-originate con'
                                + 'fig.'
                                  ;
                      type empty ;
                      ncd:revise-date 2019-12-31 ;
                    }
                  }
                  container advertise-map {
                    description 'Specify route-map for conditional advertisemen'
                              + 't.'
                                ;
                    presence 'Specify route-map for conditional advertisement'
                             ;
                    leaf advertise-map-name {
                      description 'Advertise route-map name.'
                                  ;
                      type string {
                        length 1..200 ;
                      }
                      mandatory true ;
                    }
                    choice advertise-map {
                      description 'Specify route-map for conditional advertisem'
                                + 'ent.'
                                  ;
                      mandatory true ;
                      case exist-map {
                        description 'Advertise prefix only if prefix exists.'
                                    ;
                        leaf exist-map-name {
                          description 'Advertise prefix only if prefix exists.'
                                      ;
                          type string {
                            length 1..200 ;
                          }
                          mandatory true ;
                        }
                      }
                      case nonexist-map {
                        description 'Advertise prefix only if prefix does not e'
                                  + 'xist.'
                                    ;
                        leaf nonexist-map-name {
                          description 'Advertise prefix only if prefix does not'
                                    + ' exist.'
                                      ;
                          type string {
                            length 1..200 ;
                          }
                          mandatory true ;
                        }
                      }
                    }
                  }
                  leaf adv-tunnel-encap {
                    description 'Advertise tunnel encapsulation type'
                                ;
                    type enumeration {
                      enum mpls {
                        value 2 ;
                      }
                      enum srv6 {
                        value 4 ;
                      }
                    }
                    ncd:revise-date 2020-08-18 ;
                  }
                  leaf capability-orf-prefix-list {
                    description 'Advertise prefixlist ORF capability to this ne'
                              + 'ighbor.'
                                ;
                    type enumeration {
                      enum receive {
                        value 1 ;
                        description 'Capability to receive the ORF from this ne'
                                  + 'ighbor.'
                                    ;
                      }
                      enum send {
                        value 2 ;
                        description 'Capability to send the ORF to this neighbo'
                                  + 'r.'
                                    ;
                      }
                      enum both {
                        value 3 ;
                        description 'Capability to send and receive the ORF.'
                                    ;
                      }
                    }
                  }
                  container neighbor-extend {
                    description 'Specify a neighbor.'
                                ;
                    leaf additional-paths-receive {
                      description 'Receive additional paths from this neighbor.'
                                  ;
                      type empty ;
                    }
                    container maximum-prefix {
                      description 'The action that generated when threshold val'
                                + 'ue reached.'
                                  ;
                      presence 'The action that generated when threshold value '
                             + 'reached'
                               ;
                      leaf maximum-prefix-number {
                        description 'Maximum number of prefix limit.'
                                    ;
                        type uint32 {
                          range 1..4294967295 ;
                        }
                        mandatory true ;
                      }
                      leaf maximum-prefix-threshold {
                        description 'Threshold value(%) at which to generate a '
                                  + 'warning.'
                                    ;
                        type uint32 {
                          range 1..100 ;
                        }
                        mandatory true ;
                      }
                      choice maximum-prefix-action {
                        description 'The action that generated when threshold v'
                                  + 'alue reached.'
                                    ;
                        mandatory true ;
                        case peer-action {
                          description 'The action that generated when threshold'
                                    + ' value reached.'
                                      ;
                          leaf action {
                            description 'The action that generated when threshold value reached.'
                                        ;
                            type enumeration {
                              enum down {
                                value 0 ;
                                description 'Break down BGP connection after limit is exceeded.'
                                            ;
                              }
                              enum warning-only {
                                value 1 ;
                                description 'Only give warning message when limit is exceeded.'
                                            ;
                              }
                              enum drop-routes {
                                value 2 ;
                                description 'Drop routes that exceed the maximum-prefix.'
                                            ;
                              }
                            }
                            mandatory true ;
                          }
                        }
                        case restart {
                          description 'Restart BGP connection after limit is ex'
                                    + 'ceeded.'
                                      ;
                          leaf restart-time {
                            description 'Restart interval in minutes.'
                                        ;
                            type uint32 {
                              range 1..30000 ;
                            }
                            units min ;
                            mandatory true ;
                          }
                        }
                      }
                    }
                    leaf prefix-list-in-name {
                      description 'Apply prefix list to incoming routes.'
                                  ;
                      type string {
                        length 1..169 ;
                      }
                    }
                    leaf prefix-list-out-name {
                      description 'Apply  prefix list to outbound routes.'
                                  ;
                      type string {
                        length 1..169 ;
                      }
                    }
                    leaf route-map-in-name {
                      description 'Apply route-map to incoming routes.'
                                  ;
                      type string {
                        length 1..200 ;
                      }
                    }
                    leaf route-map-out-name {
                      description 'Apply route-map to outbound routes.'
                                  ;
                      type string {
                        length 1..200 ;
                      }
                    }
                    container diverse-path-receive {
                      description 'Advertise diverse path to this neighbor.'
                                  ;
                      presence diverse-path-receive ;
                      choice diverse-path-receive {
                        description 'Advertise diverse path to this neighbor.'
                                    ;
                        mandatory true ;
                        case backup {
                          description 'Advertisement of the backup path.'
                                      ;
                          leaf backup {
                            description 'Advertisement of the backup path.'
                                        ;
                            type empty ;
                            mandatory true ;
                          }
                        }
                        case multipath {
                          description 'Sequence number of multipath.'
                                      ;
                          leaf sequence-number {
                            description 'Sequence number of multipath.'
                                        ;
                            type uint32 {
                              range 2..32 ;
                            }
                            mandatory true ;
                          }
                        }
                      }
                      leaf route-map {
                        description 'Apply route-map to neighbor.'
                                    ;
                        type string {
                          length 1..200 ;
                        }
                      }
                    }
                    container additional-paths-send {
                      description 'Send additional paths to this neighbor.'
                                  ;
                      choice additional-paths-send {
                        description 'Send additional paths to this neighbor.'
                                    ;
                        default send-one-path ;
                        case send-one-path {
                          description 'Send one additional path to this neighbo'
                                    + 'r.'
                                      ;
                          leaf send {
                            description 'Send additional paths to this neighbor.'
                                        ;
                            type empty ;
                          }
                        }
                        case send-multi-paths {
                          description 'Send additional multi-paths to this neig'
                                    + 'hbor.'
                                      ;
                          leaf paths-number {
                            description 'Number of paths for a prefix.'
                                        ;
                            type uint32 {
                              range 2..32 ;
                            }
                            mandatory true ;
                          }
                          leaf prefixlist {
                            description 'Prefixlist of filtering additional paths.'
                                        ;
                            type string {
                              length 1..169 ;
                            }
                          }
                        }
                      }
                    }
                    leaf routepolicy-in-name {
                      description 'Route policy name applied to the inbound rou'
                                + 'tes.'
                                  ;
                      type string {
                        length 1..200 ;
                      }
                    }
                    leaf routepolicy-out-name {
                      description 'Route policy name applied to the outbound ro'
                                + 'utes.'
                                  ;
                      type string {
                        length 1..200 ;
                      }
                    }
                    container connector {
                      description 'Send connector to this neighbor.'
                                  ;
                      presence connector ;
                      leaf send-connector {
                        description 'Send connector to this neighbor.'
                                    ;
                        type empty ;
                        mandatory true ;
                      }
                      leaf route-map {
                        description 'Apply route-map to neighbor.'
                                    ;
                        type string {
                          length 1..200 ;
                        }
                      }
                    }
                    container withdraw {
                      description 'Withdraw routes when state of track-group is'
                                + ' down.'
                                  ;
                      presence withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                    }
                    container second-withdraw {
                      description 'Withdraw routes when state of the second tra'
                                + 'ck-group is down.'
                                  ;
                      presence second-withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                      ncd:revise-date 2018-07-12 ;
                    }
                  }
                  leaf nouse-peergroup-config {
                    status obsolete {
                      ncd:revise-date 2018-05-14 ;
                    }
                    description 'Peer do not use group config set.Only for get '
                              + 'operation.'
                                ;
                    type empty ;
                  }
                  container route-filter-group {
                    description 'Specify a neighbor to join a route-filter-grou'
                              + 'p.'
                                ;
                    presence route-filter-group ;
                    leaf filter-group {
                      description 'Route filter group name (1-31 characters).'
                                  ;
                      type string {
                        length 1..31 ;
                      }
                      mandatory true ;
                    }
                    leaf next-hop-self {
                      description 'Disable the next hop calculation for this ne'
                                + 'ighbor.'
                                  ;
                      type empty ;
                    }
                  }
                  leaf announce-sid {
                    description 'Enable Prefix-SID attribute for this neighbor.'
                                ;
                    type enumeration {
                      enum enable {
                        value 1 ;
                        description 'Enable Prefix-SID attribute for this neigh'
                                  + 'bor.'
                                    ;
                      }
                    }
                  }
                  leaf soft-reconfig {
                    description 'Neighbor soft reconfiguration.'
                                ;
                    type enumeration {
                      enum soft-reconfiguration {
                        value 1 ;
                        description Soft-reconfiguration. ;
                      }
                      enum enforce-soft-reconfiguration {
                        value 2 ;
                        description 'Enforce soft-reconfiguration instead of se'
                                  + 'nding route-refresh.'
                                    ;
                      }
                    }
                    ncd:revise-date 2019-08-08 ;
                  }
                  leaf vpn-orf {
                    description 'Peer route-target ORF capability'
                                ;
                    type enumeration {
                      enum disable {
                        value 0 ;
                        description 'Disable peer route-target ORF capability'
                                    ;
                      }
                      enum enable {
                        value 1 ;
                        description 'Enable peer route-target ORF capability'
                                    ;
                      }
                      enum inherit {
                        value 2 ;
                        description 'If the neighbor joined a group, the status'
                                  + ' inherited from group.'
                                    ;
                      }
                    }
                    ncd:revise-date 2020-02-08 ;
                  }
                  leaf send-link-bw {
                    description 'Send link bandwidth to this neighbor.'
                                ;
                    type enumeration {
                      enum disable {
                        value 0 ;
                        description 'Disable peer send link bandwidth'
                                    ;
                      }
                      enum enable {
                        value 1 ;
                        description 'Enable peer send link bandwidth'
                                    ;
                      }
                      enum inherit {
                        value 2 ;
                        description 'If the neighbor joined a group, the status'
                                  + ' inherited from group.'
                                    ;
                      }
                    }
                    ncd:revise-date 2019-10-22 ;
                  }
                  container route-server-client {
                    description 'Set route server client only valid for ebgp pe'
                              + 'er.'
                                ;
                    presence route-server-client ;
                    leaf route-svr-client {
                      description 'Set route server client only valid for ebgp '
                                + 'peer.'
                                  ;
                      type empty ;
                      mandatory true ;
                    }
                    ncd:revise-date 2020-04-07 ;
                  }
                }
                ncd:revise-date 2018-05-14 ;
              }
            }
            container additional-paths {
              description 'Additional paths in the BGP table.'
                          ;
              leaf selection-route-map {
                description 'Selection criteria to pick the additional paths.'
                            ;
                type string {
                  length 1..200 ;
                }
              }
              ncd:revise-date 2016-01-06 ;
            }
            container route-scan-time {
              description 'Adjust BGP route scan timers.'
                          ;
              presence 'The ability of BGP route scan.'
                       ;
              leaf interval-wait {
                description 'The interval of scan waiting. Default value is 500.'
                            ;
                type uint32 {
                  range 1..65535 ;
                }
                units ms ;
                mandatory true ;
              }
              leaf initial {
                description 'The initialization time of scan. Default value is '
                          + '50.'
                            ;
                type uint32 {
                  range 1..65535 ;
                }
                units ms ;
                mandatory true ;
              }
              leaf max-wait {
                description 'The max waiting time of scan. Default value is 500'
                          + '0.'
                            ;
                type uint32 {
                  range 1..65535 ;
                }
                units ms ;
                mandatory true ;
              }
              ncd:revise-date 2015-11-20 ;
            }
            leaf vpn-frr-capability {
              description 'Enable FRR capability.'
                          ;
              type empty ;
              ncd:revise-date 2017-05-24 ;
            }
            leaf vpn-frr-wtr {
              description 'Set the WTR time.'
                          ;
              type int32 {
                range 1..12 ;
              }
              units min ;
              ncd:revise-date 2017-05-24 ;
            }
            container group-to-group {
              description 'Configure filter group to filter group route reflect'
                        + 'ion.'
                          ;
              presence group-to-group ;
              leaf reflection {
                description 'Reflection of routes is allowed.'
                            ;
                type empty ;
                mandatory true ;
              }
              leaf next-hop-self {
                description 'Disable the next hop calculation.'
                            ;
                type empty ;
              }
              ncd:revise-date 2018-08-04 ;
            }
            leaf import-l2vpn-evpn {
              description 'Import L2VPN EVPN route to VPNv4 unicast table.'
                          ;
              type enumeration {
                enum disable {
                  value 0 ;
                }
                enum enable {
                  value 1 ;
                }
              }
              default disable ;
              ncd:revise-date 2019-07-07 ;
            }
            leaf bgp-bestpath-origin {
              description 'bgp bestpath origin-from L3VPN neighbor or EVPN neig'
                        + 'hbor.'
                          ;
              type enumeration {
                enum l3vpn {
                  value 1 ;
                  description 'bgp bestpath origin-from L3VPN neighbor'
                              ;
                }
                enum evpn {
                  value 2 ;
                  description 'bgp bestpath origin-from EVPN neighbor'
                              ;
                }
              }
              ncd:revise-date 2019-08-08 ;
            }
            leaf vpn-orf {
              description 'Generate local route-target routes'
                          ;
              type enumeration {
                enum disable {
                  value 0 ;
                  description 'Disable generate local route-target routes'
                              ;
                }
                enum enable {
                  value 1 ;
                  description 'Enable generate local route-target routes'
                              ;
                }
              }
              ncd:revise-date 2020-02-08 ;
            }
            leaf slow-peer-detection {
              description 'Set slow peer detection.'
                          ;
              type enumeration {
                enum disable {
                  value 0 ;
                  description 'Disable slow peer detection'
                              ;
                }
                enum enable {
                  value 1 ;
                  description 'Enable slow peer detection'
                              ;
                }
              }
              default disable ;
              ncd:revise-date 2020-09-08 ;
            }
            leaf slow-peer-detection-threshold {
              description 'Set threshold time for slow peer.Default value is 30'
                        + '0.'
                          ;
              type uint32 {
                range 120..3600 {
                  description 'Threshold time range.'
                              ;
                }
              }
              units s ;
              default 300 ;
              ncd:revise-date 2020-09-08 ;
            }
            leaf slow-peer-detection-recover {
              description 'Set recover time for slow peer.Default value is 300.'
                          ;
              type uint32 {
                range 120..3600 {
                  description 'Recover time range.'
                              ;
                }
              }
              units s ;
              default 300 ;
              ncd:revise-date 2020-09-08 ;
            }
            leaf nexthop-recursive-lookup-srv6-sid {
              description 'Enable or disable bgp nexthop recursive-lookup srv6-'
                        + 'sid'
                          ;
              type enumeration {
                enum disable {
                  value 0 ;
                }
                enum enable {
                  value 1 ;
                }
              }
              default disable ;
              ncd:revise-date 2020-10-28 ;
            }
          }
          container address-family-ipv4-vrf {
            description 'Specify parameters for IPv4 VRF.'
                        ;
            list address-family-vrf {
              description 'Specify parameters for VRF.'
                          ;
              key vrf-name ;
              leaf vrf-name {
                description 'VPN Routing/Forwarding instance name.'
                            ;
                type string {
                  length 1..32 ;
                }
              }
              leaf advertise-active-only {
                description 'Advertise the active routes only.'
                            ;
                type empty ;
              }
              leaf maximum-paths-ibgp {
                description 'Set IBGP-multipath.'
                            ;
                type uint32 {
                  range 1..32 ;
                }
                default 1 ;
              }
              leaf maximum-paths-ebgp {
                description 'Set EBGP-multipath.'
                            ;
                type uint32 {
                  range 1..32 ;
                }
                default 1 ;
              }
              leaf maximum-paths-eibgp {
                description 'Set EIBGP-multipath. Mutex with maximum-paths-ibgp'
                          + ' and maximum-paths-ebgp.'
                            ;
                type uint32 {
                  range 1..32 ;
                }
                default 1 ;
              }
              leaf nexthop-trigger-delay {
                description 'Set the delay time to trigger nexthop tracking.'
                            ;
                type uint32 {
                  range 1..1200 {
                    description 'Delay value.'
                                ;
                  }
                }
                units s ;
              }
              leaf router-id-addr {
                description 'Manually configured router identifier.'
                            ;
                type ncd:ipv4-address {
                  pattern '([1-9][0-9]*\.[1-9][0-9]*\.[1-9][0-9]*\.[1-9][0-9]*)'
                        + '|([1-9][0-9]*\.0\.0\.0)|(0\.[1-9][0-9]*\.0\.0)|(0\.0'
                        + '\.[1-9][0-9]*\.0)|(0\.0\.0\.[1-9][0-9]*)|([1-9][0-9]'
                        + '*\.[1-9][0-9]*\.0\.0)|(0\.[1-9][0-9]*\.[1-9][0-9]*\.'
                        + '0)|(0\.0\.[1-9][0-9]*\.[1-9][0-9]*)|([1-9][0-9]*\.0\.'
                        + '0\.[1-9][0-9]*)|(0\.[1-9][0-9]*\.0\.[1-9][0-9]*)|([1'
                        + '-9][0-9]*\.0\.[1-9][0-9]*\.0)|([1-9][0-9]*\.[1-9][0-'
                        + '9]*\.[1-9][0-9]*\.0)|([1-9][0-9]*\.[1-9][0-9]*\.0\.['
                        + '1-9][0-9]*)|([1-9][0-9]*\.0\.[1-9][0-9]*\.[1-9][0-9]'
                        + '*)|(0\.[1-9][0-9]*\.[1-9][0-9]*\.[1-9][0-9]*)'
                          ;
                }
              }
              leaf default-information-originate {
                description 'Notify default route.'
                            ;
                type empty ;
              }
              leaf default-metric {
                description 'Set metric of BGP routes without MED.'
                            ;
                type uint32 {
                  range 0..4294967295 ;
                }
                default 0 ;
              }
              leaf distance-bgp-external {
                description 'Distance for routes external to the AS.'
                            ;
                type uint32 {
                  range 1..255 ;
                }
                default 20 ;
              }
              leaf distance-bgp-internal {
                description 'Distance for routes internal to the AS.'
                            ;
                type uint32 {
                  range 1..255 ;
                }
                default 200 ;
              }
              leaf distance-bgp-local {
                description 'Distance for BGP local routes.'
                            ;
                type uint32 {
                  range 1..255 ;
                }
                default 254 ;
                ncd:revise-date 2016-05-10 ;
              }
              leaf distance-route-map {
                description 'Define distance by route-map.This node has higher '
                          + 'priority than distance-bgp-internal,distance-bgp-e'
                          + 'xternal and distance-bgp-local.'
                            ;
                type string {
                  length 1..200 ;
                }
                ncd:revise-date 2020-09-08 ;
              }
              leaf distance-route-policy {
                description 'Define distance by route-policy.This node has high'
                          + 'er priority than distance-bgp-internal,distance-bg'
                          + 'p-external and distance-bgp-local.'
                            ;
                type string {
                  length 1..200 ;
                }
                ncd:revise-date 2020-10-10 ;
              }
              leaf import-best-path {
                description 'Maximum number of paths that can be imported into '
                          + 'the VRF.'
                            ;
                type uint32 {
                  range 1..32 ;
                }
                ncd:revise-date 2016-01-06 ;
              }
              leaf table-map {
                description 'Map external entry attributes into routing table.'
                            ;
                type string {
                  length 1..200 ;
                }
              }
              leaf frr-capability {
                description 'Enable FRR capability.'
                            ;
                type empty ;
              }
              leaf frr-wtr {
                description 'Set the WTR time.'
                            ;
                type int32 {
                  range 1..12 ;
                }
                units min ;
              }
              leaf frr-enhanced {
                description 'If there is no BGP route as a backup route, then c'
                          + 'hoose the default route for FRR.'
                            ;
                type empty ;
                ncd:revise-date 2016-01-06 ;
              }
              leaf rpki-validation {
                status obsolete {
                  ncd:revise-date 2018-06-11 ;
                }
                description 'Set the BGP origin-AS validation parameters.'
                            ;
                type disable-or-enable-type ;
                default enable ;
                ncd:revise-date 2016-01-06 ;
              }
              leaf nexthop-recursive-default-route {
                description 'Nexthop recursive lookup default-route.'
                            ;
                type enumeration {
                  enum enable {
                    value 1 ;
                  }
                  enum disable {
                    value 0 ;
                  }
                }
                default enable ;
                ncd:revise-date 2020-07-28 ;
              }
              leaf nexthop-recursive-null1 {
                description 'Nexthop recursive lookup null1.'
                            ;
                type enumeration {
                  enum enable {
                    value 1 ;
                  }
                  enum disable {
                    value 0 ;
                  }
                }
                default enable ;
                ncd:revise-date 2020-12-09 ;
              }
              leaf bgp-attr-set {
                description 'Receive or/and send ATTR-SET attribute.'
                            ;
                type enumeration {
                  enum both {
                    value 1 ;
                    description 'Receive and send ATTR-SET attribute.'
                                ;
                  }
                  enum receive {
                    value 2 ;
                    description 'Receive ATTR-SET attribute.'
                                ;
                  }
                  enum send {
                    value 3 ;
                    description 'Send ATTR-SET attribute.'
                                ;
                  }
                }
                ncd:revise-date 2021-04-21 ;
              }
              container redistribute-v4-vrf {
                description 'Redistribute information from another routing prot'
                          + 'ocol.'
                            ;
                presence redistribute-v4-vrf ;
                container redistribute-vrf {
                  description 'Redistribute information from another routing pr'
                            + 'otocol.'
                              ;
                  list redistribute {
                    description 'Redistribute information from another routing '
                              + 'protocol.'
                                ;
                    key protocol ;
                    leaf protocol {
                      description 'Routing protocol type.'
                                  ;
                      type enumeration {
                        enum connected {
                          value 1 ;
                          description 'Connected routes.'
                                      ;
                        }
                        enum static {
                          value 2 ;
                          description 'Static routes.'
                                      ;
                        }
                        enum rip {
                          value 3 ;
                          description 'Routing information protocol(RIP).'
                                      ;
                        }
                        enum address {
                          value 9 ;
                          description 'Address routes.'
                                      ;
                        }
                        enum ps-busi-addr {
                          value 10 ;
                          description 'Ps-busi-addr routes.'
                                      ;
                        }
                        enum ps-user-addr {
                          value 11 ;
                          description 'Ps-user-addr routes.'
                                      ;
                        }
                        enum nat {
                          value 12 ;
                          description 'NAT routes.'
                                      ;
                        }
                        enum natpt {
                          value 13 ;
                          description 'Port-address Translation routes.'
                                      ;
                        }
                        enum subscriber-host {
                          value 14 ;
                          description "Bras subscriber's host routes."
                                      ;
                        }
                        enum subscriber-aggregation {
                          value 15 ;
                          description "Bras subscriber's aggregation routes."
                                      ;
                        }
                        enum user-special {
                          value 17 ;
                          description 'User-special routes.'
                                      ;
                        }
                        enum sl-nat64-ipv4 {
                          value 18 ;
                          description 'Stateless NAT64 prefix.'
                                      ;
                        }
                        enum bras-pool {
                          value 24 ;
                          description 'Broadband Remote Access Server pool rout'
                                    + 'es.'
                                      ;
                        }
                        enum ipsec {
                          value 25 ;
                          description 'IPsec routes'
                                      ;
                        }
                        enum hagp {
                          value 26 ;
                          description 'Hybrid access gateway protocol routes.'
                                      ;
                        }
                        enum dyn-leasedline {
                          value 29 ;
                          description 'Dynamic-leased-line routes assigned by A'
                                    + 'AA.'
                                      ;
                        }
                      }
                    }
                    leaf route-map {
                      description 'Apply route-map to redistribute.'
                                  ;
                      type string {
                        length 1..200 ;
                      }
                    }
                    leaf route-policy {
                      description 'Apply route-policy to redistribute.'
                                  ;
                      type string {
                        length 1..200 ;
                      }
                      ncd:revise-date 2020-10-10 ;
                    }
                    container set-metric {
                      description 'Set route metric.'
                                  ;
                      leaf metric {
                        description 'Set route metric.'
                                    ;
                        type uint32 {
                          range 0..4294967295 ;
                        }
                      }
                    }
                  }
                }
                container redistribute-isis-vrf {
                  description 'Redistribute information from ISIS protocol.'
                              ;
                  list redistribute-isis {
                    description 'Redistribute information from ISIS protocol.'
                                ;
                    key 'protocol process-id'
                        ;
                    leaf protocol {
                      description 'Routing protocol type(ISIS-1,ISIS-2 or ISIS-'
                                + '1-2).'
                                  ;
                      type enumeration {
                        enum isis-1 {
                          value 4 ;
                          description 'IS-IS level-1 routes only.'
                                      ;
                        }
                        enum isis-2 {
                          value 5 ;
                          description 'IS-IS level-2 routes only.'
                                      ;
                        }
                      }
                    }
                    leaf process-id {
                      description 'ISIS process ID.'
                                  ;
                      type uint32 {
                        range 0..65535 ;
                      }
                    }
                    leaf route-map {
                      description 'Apply route-map to redistribute.'
                                  ;
                      type string {
                        length 1..200 ;
                      }
                    }
                    leaf route-policy {
                      description 'Apply route-policy to redistribute.'
                                  ;
                      type string {
                        length 1..200 ;
                      }
                      ncd:revise-date 2020-10-10 ;
                    }
                    container set-metric {
                      description 'Set route metric.'
                                  ;
                      leaf metric {
                        description 'Set route metric.'
                                    ;
                        type uint32 {
                          range 0..4294967295 ;
                        }
                      }
                    }
                  }
                }
                container redistribute-ospf-vrf {
                  description 'Redistribute information from OSPF protocol.'
                              ;
                  list redistribute-ospf {
                    description 'Redistribute information from OSPF protocol.'
                                ;
                    key 'protocol process-id'
                        ;
                    leaf protocol {
                      description 'Routing protocol type(OSPF-EXT or OSPF-INT).'
                                  ;
                      type enumeration {
                        enum ospf-ext {
                          value 7 ;
                          description 'Open shortest path first(OSPF) external '
                                    + 'routes.'
                                      ;
                        }
                        enum ospf-int {
                          value 8 ;
                          description 'Open shortest path first(OSPF) internal '
                                    + 'routes.'
                                      ;
                        }
                      }
                    }
                    leaf process-id {
                      description 'OSPF process ID.'
                                  ;
                      type uint32 {
                        range 1..65535 ;
                      }
                    }
                    leaf route-map {
                      description 'Apply route-map to redistribute.'
                                  ;
                      type string {
                        length 1..200 ;
                      }
                    }
                    leaf route-policy {
                      description 'Apply route-policy to redistribute.'
                                  ;
                      type string {
                        length 1..200 ;
                      }
                      ncd:revise-date 2020-10-10 ;
                    }
                    container set-metric {
                      description 'Set route metric.'
                                  ;
                      leaf metric {
                        description 'Set route metric.'
                                    ;
                        type uint32 {
                          range 0..4294967295 ;
                        }
                      }
                    }
                  }
                }
              }
              container network-v4-vrf {
                description 'Specify a network to announce via BGP.'
                            ;
                presence network-v4-vrf ;
                list network {
                  description 'Specify a network to announce via BGP.'
                              ;
                  key 'ip-address ip-mask'
                      ;
                  leaf ip-address {
                    description 'Network prefix.'
                                ;
                    type ncd:ipv4-address ;
                  }
                  leaf ip-mask {
                    description 'Network mask.'
                                ;
                    type ncd:ipv4-mask ;
                  }
                  leaf route-map {
                    description 'Route-map to modify the attributes.'
                                ;
                    type string {
                      length 1..200 ;
                    }
                  }
                  leaf route-policy {
                    description 'Route-policy to modify the attributes.'
                                ;
                    type string {
                      length 1..200 ;
                    }
                    ncd:revise-date 2020-10-10 ;
                  }
                }
              }
              container damp-v4-vrf {
                description 'Enable route-flap dampening.'
                            ;
                presence damp-v4-vrf ;
                choice dampening {
                  description 'Enable route-flap dampening.'
                              ;
                  case route-map {
                    description 'Route-map to specify criteria for dampening.'
                                ;
                    leaf route-map-name {
                      description 'Route-map to specify criteria for dampening.'
                                  ;
                      type string {
                        length 1..200 ;
                      }
                    }
                    leaf route-policy-name {
                      description 'Route-policy to specify criteria for dampeni'
                                + 'ng.'
                                  ;
                      type string {
                        length 1..200 ;
                      }
                      ncd:revise-date 2020-10-10 ;
                    }
                  }
                  case parameter {
                    description 'Damp parameter.'
                                ;
                    leaf half-time {
                      description 'Half-life time for the penalty.'
                                  ;
                      type uint32 {
                        range 1..45 ;
                      }
                      units min ;
                      mandatory true ;
                    }
                    leaf reuse {
                      description 'Value to start reusing a route.'
                                  ;
                      type uint32 {
                        range 1..20000 ;
                      }
                      mandatory true ;
                    }
                    leaf suppress {
                      description 'Value to start suppressing a route.'
                                  ;
                      type uint32 {
                        range 1..20000 ;
                      }
                      mandatory true ;
                    }
                    leaf max-suppress-time {
                      description 'Maximum duration to suppress a route.'
                                  ;
                      type uint32 {
                        range 1..255 ;
                      }
                      units min ;
                      mandatory true ;
                    }
                  }
                }
              }
              container aggregate-v4-vrf {
                description 'Configure BGP aggregate entries.'
                            ;
                presence aggregate-v4-vrf ;
                list aggregate {
                  description 'Configure BGP aggregate entries.'
                              ;
                  key 'aggregate-address aggregate-mask'
                      ;
                  leaf aggregate-address {
                    description 'Aggregate address.'
                                ;
                    type ncd:ipv4-address ;
                  }
                  leaf aggregate-mask {
                    description 'Aggregate mask.'
                                ;
                    type ncd:ipv4-mask ;
                  }
                  leaf as-set {
                    description 'Generate AS set path information.'
                                ;
                    type empty ;
                  }
                  leaf strict {
                    description 'Strict condition.'
                                ;
                    type empty ;
                  }
                  leaf summary-only {
                    description 'Filter more specific routes from updates.'
                                ;
                    type empty ;
                  }
                  leaf attribute-map {
                    status obsolete {
                      ncd:revise-date 2018-07-21 ;
                    }
                    description 'Attribute map name.'
                                ;
                    type string {
                      length 1..200 ;
                    }
                  }
                  leaf suppress-map {
                    status obsolete {
                      ncd:revise-date 2018-07-21 ;
                    }
                    description 'Suppress map name.'
                                ;
                    type string {
                      length 1..200 ;
                    }
                  }
                  choice agg-policy {
                    description 'Apply policy to aggregate route.'
                                ;
                    case agg-policy-choice-clear {
                      description 'Remove value of any entities which belong to'
                                + ' any case within this choice.'
                                  ;
                      container agg-policy-all-clear {
                        description 'Remove this entitiy means to remove value '
                                  + 'of any entities which belong to any case w'
                                  + 'ithin this choice.'
                                    ;
                        presence clear-agg-policy ;
                      }
                      ncd:revise-date 2020-11-11 ;
                    }
                    case route-map {
                      description 'Apply route map to aggregate route.'
                                  ;
                      leaf attr-map {
                        description 'Attribute map name.'
                                    ;
                        type string {
                          length 1..200 ;
                        }
                      }
                      leaf supp-map {
                        description 'Suppress map name.'
                                    ;
                        type string {
                          length 1..200 ;
                        }
                      }
                      leaf orig-map {
                        description 'Origin map name.'
                                    ;
                        type string {
                          length 1..200 ;
                        }
                        ncd:revise-date 2019-08-19 ;
                      }
                    }
                    case route-policy {
                      description 'Apply route-policy to aggregate route.'
                                  ;
                      leaf policy {
                        description 'Route-policy name.'
                                    ;
                        type string {
                          length 1..200 ;
                        }
                      }
                    }
                    ncd:revise-date 2018-07-21 ;
                  }
                }
              }
              container track-v4-vrf {
                description 'Event tracking.'
                            ;
                presence track-v4-vrf ;
                container track-adjust-type-with-interface {
                  description 'Configure adjust-priority of track object with i'
                            + 'nterface.'
                              ;
                  list track-adjust-with-interface {
                    description 'Configure adjust-priority of track object with'
                              + ' interface.'
                                ;
                    key 'track-name track-interface'
                        ;
                    leaf track-name {
                      description 'Name of track object (1-31 characters).'
                                  ;
                      type string {
                        length 1..31 ;
                      }
                    }
                    leaf track-interface {
                      description 'Source of track object.'
                                  ;
                      type ncd:ifname {
                        length 1..31 ;
                      }
                    }
                    leaf adjust-value {
                      description 'Value of adjust-priority.'
                                  ;
                      type uint32 {
                        range 1..100 ;
                      }
                      mandatory true ;
                    }
                  }
                }
                container track-adjust-type-without-interface {
                  description 'Configure adjust-priority of track object withou'
                            + 't interface.'
                              ;
                  list track-adjust-without-interface {
                    description 'Configure adjust-priority of track object with'
                              + 'out interface.'
                                ;
                    max-elements 1 ;
                    key track-name ;
                    leaf track-name {
                      description 'Name of track object (1-31 characters).'
                                  ;
                      type string {
                        length 1..31 ;
                      }
                    }
                    leaf adjust-value {
                      description 'Value of adjust-priority.'
                                  ;
                      type uint32 {
                        range 1..100 ;
                      }
                      mandatory true ;
                    }
                  }
                }
              }
              container neighbor-v4-vrf {
                description 'Specify a neighbor.'
                            ;
                presence neighbor-v4-vrf ;
                container neighbor-group {
                  description 'Specify a peergroup neighbor.'
                              ;
                  list neighbor-peergroup {
                    description 'Specify a neighbor.'
                                ;
                    key neighbor-group ;
                    leaf neighbor-group {
                      description 'Peer group name (1-31 characters).'
                                  ;
                      type string {
                        length 1..31 ;
                      }
                    }
                    leaf remote-as {
                      description 'Specify a BGP neighbor AS number.'
                                  ;
                      type ncd:asn-dot ;
                    }
                    leaf activate {
                      description 'Enable the address family for this neighbor.'
                                  ;
                      type enumeration {
                        enum disable {
                          value 0 ;
                        }
                        enum enable {
                          value 1 ;
                        }
                      }
                    }
                    leaf monitor {
                      description 'Config BMP monitor for the address family of'
                                + ' this neighbor.'
                                  ;
                      type enumeration {
                        enum disable {
                          value 2 ;
                        }
                        enum enable {
                          value 1 ;
                        }
                        enum inherit-global-config {
                          value 0 ;
                        }
                      }
                      ncd:revise-date 2019-07-29 ;
                    }
                    leaf advertisement-interval {
                      description 'Minimum interval between sending BGP routing'
                                + ' which is not locally originated updates.'
                                  ;
                      type uint32 {
                        range 1..65535 ;
                      }
                      units s ;
                    }
                    leaf advertise-maximum-prefix {
                      description 'Maximum number of prefix send to this peer.'
                                  ;
                      type uint32 {
                        range 1..4294967295 ;
                      }
                      ncd:revise-date 2016-01-06 ;
                    }
                    leaf allowas-in {
                      description 'Accept as-path with my AS present in it.'
                                  ;
                      type uint32 {
                        range 1..10 ;
                      }
                    }
                    leaf as-override {
                      description 'Override matching AS-number while sending up'
                                + 'date.'
                                  ;
                      type empty ;
                    }
                    leaf as-path-loopcheck {
                      description 'Check as-path sending BGP routing to EBGP ne'
                                + 'ighbor.'
                                  ;
                      type empty ;
                    }
                    leaf connect-retry-interval {
                      description 'Set data of connect-retry timer for this nei'
                                + 'ghbor.'
                                  ;
                      type uint32 {
                        range 1..65535 ;
                      }
                      units s ;
                    }
                    leaf default-originate {
                      description 'Originate default route to this neighbor.'
                                  ;
                      type empty ;
                    }
                    leaf default-originate-routemap {
                      description 'Map external entry attributes into routing t'
                                + 'able.'
                                  ;
                      type string {
                        length 1..200 ;
                      }
                      ncd:revise-date 2020-07-28 ;
                    }
                    leaf default-originate-routepolicy {
                      description 'Set external entry attributes into routing t'
                                + 'able.'
                                  ;
                      type string {
                        length 1..200 ;
                      }
                      ncd:revise-date 2020-10-10 ;
                    }
                    leaf description {
                      description 'Neighbor specific description.'
                                  ;
                      type ncd:string-with-blank {
                        length 1..80 ;
                      }
                    }
                    container fall-over {
                      description 'Set BFD supporting for fallover.'
                                  ;
                      presence 'Enable BFD support for fallover'
                               ;
                      leaf bfd {
                        description 'Enable BFD support for fallover.'
                                    ;
                        type empty ;
                        mandatory true ;
                      }
                      container bfd-parameters {
                        description 'The parameters of BFD.'
                                    ;
                        presence bfd-parameters ;
                        choice bfd-parameters {
                          description 'Config bfd parameters'
                                      ;
                          case template-name {
                            description 'Template name'
                                        ;
                            leaf template {
                              description 'BFD template name'
                                          ;
                              type string {
                                length 1..31 ;
                              }
                            }
                            ncd:revise-date 2020-03-31 ;
                          }
                          case parameters {
                            description Parameters ;
                            leaf interval {
                              description 'Minimum send interval.'
                                          ;
                              type uint32 {
                                range 10..990 ;
                              }
                              units ms ;
                              mandatory true ;
                            }
                            leaf min-rx {
                              description 'Minimum receive interval.'
                                          ;
                              type uint32 {
                                range 10..990 ;
                              }
                              units ms ;
                              mandatory true ;
                            }
                            leaf multiplier {
                              description Multiplier. ;
                              type uint8 {
                                range 3..50 ;
                              }
                              mandatory true ;
                            }
                          }
                        }
                      }
                      leaf bfd-hop {
                        description 'bfd optional hop'
                                    ;
                        type enumeration {
                          enum single-hop {
                            value 1 ;
                            description 'Set single-hop bfd'
                                        ;
                          }
                          enum multi-hop {
                            value 2 ;
                            description 'Set multi-hop bfd'
                                        ;
                          }
                        }
                        ncd:revise-date 2019-04-23 ;
                      }
                    }
                    leaf maxas-in {
                      description 'Accept as-path not exceeded maxas-in.'
                                  ;
                      type uint32 {
                        range 1..250 ;
                      }
                    }
                    leaf next-hop-self {
                      description 'Disable the next hop calculation for this ne'
                                + 'ighbor.'
                                  ;
                      type enumeration {
                        enum enable {
                          value 1 ;
                          description 'Apply next-hop-self for EBGP route.'
                                      ;
                        }
                        enum all {
                          value 2 ;
                          description 'Apply next-hop-self for both EBGP and IB'
                                    + 'GP route.'
                                      ;
                        }
                      }
                    }
                    leaf originate-interval {
                      description 'Minimum interval between sending BGP routing'
                                + ' which is locally originated updates.'
                                  ;
                      type uint32 {
                        range 1..65535 ;
                      }
                      units s ;
                    }
                    leaf passive {
                      description "Don't send open messages to this neighbor ac"
                                + "tively."
                                  ;
                      type empty ;
                    }
                    leaf remove-private-as {
                      description 'EBGP use to remove private AS number.'
                                  ;
                      type enumeration {
                        enum disable {
                          value 0 ;
                        }
                        enum enable {
                          value 1 ;
                        }
                      }
                    }
                    leaf send-community {
                      description 'Send community to this neighbor.'
                                  ;
                      type empty ;
                    }
                    leaf send-large-community {
                      description 'Send Large-community to this neighbor.'
                                  ;
                      type empty ;
                      ncd:revise-date 2020-04-16 ;
                    }
                    leaf route-reflector-client {
                      description 'Set this neighbor as a client peer.'
                                  ;
                      type empty ;
                      ncd:revise-date 2019-08-19 ;
                    }
                    leaf send-med {
                      description 'Send metric attribute to this neighbor.'
                                  ;
                      type empty ;
                    }
                    leaf inherit-igp-metric {
                      description 'Med attribute inherited from IGP metric befo'
                                + 're sending updates'
                                  ;
                      type empty ;
                      ncd:revise-date 2017-07-25 ;
                    }
                    leaf shut-down {
                      status obsolete {
                        ncd:revise-date 2016-06-12 ;
                      }
                      description 'Administratively shut down this neighbor.'
                                  ;
                      type empty ;
                    }
                    leaf soft-reconfiguration {
                      status obsolete {
                        ncd:revise-date 2018-01-31 ;
                      }
                      description 'Neighbor soft reconfiguration.'
                                  ;
                      type empty ;
                    }
                    leaf soft-reconfig {
                      description 'Neighbor soft reconfiguration.'
                                  ;
                      type enumeration {
                        enum soft-reconfiguration {
                          value 1 ;
                          description Soft-reconfiguration. ;
                        }
                        enum enforce-soft-reconfiguration {
                          value 2 ;
                          description 'Enforce soft-reconfiguration instead of '
                                    + 'sending route-refresh.'
                                      ;
                        }
                      }
                      ncd:revise-date 2018-01-31 ;
                    }
                    leaf soo {
                      description 'Site-of-Origin extended community.'
                                  ;
                      type union {
                        type ncd:asn-nn ;
                        type ncd:asnd-nn ;
                        type ncd:ipadd-nn ;
                      }
                    }
                    leaf split-update-group {
                      description 'Split neighbor from update group.'
                                  ;
                      type empty ;
                    }
                    leaf update-source {
                      status obsolete {
                        ncd:revise-date 2018-11-27 ;
                      }
                      description 'Source of routing updates.'
                                  ;
                      type ncd:ifname {
                        length 1..31 ;
                      }
                    }
                    leaf orf-prefix-filter {
                      description 'Advertise prefixlist ORF capability to this '
                                + 'neighbor.'
                                  ;
                      type enumeration {
                        enum receive {
                          value 1 ;
                          description 'Capability to receive the ORF from this '
                                    + 'neighbor.'
                                      ;
                        }
                        enum send {
                          value 2 ;
                          description 'Capability to send the ORF to this neigh'
                                    + 'bor.'
                                      ;
                        }
                        enum both {
                          value 3 ;
                          description 'Capability to send and receive the ORF.'
                                      ;
                        }
                      }
                    }
                    leaf orf-prefix-filter-cisco {
                      description 'Compatible with CISCO.'
                                  ;
                      type empty ;
                    }
                    leaf weight {
                      description 'Set weight for routes from this neighbor.'
                                  ;
                      type uint32 {
                        range 1..65535 ;
                      }
                    }
                    leaf aigp {
                      description 'Enable AIGP for this neighbor.'
                                  ;
                      type empty ;
                      ncd:revise-date 2017-11-01 ;
                    }
                    leaf send-label {
                      description 'Send NLRI with MPLS label to this neighbor.'
                                  ;
                      type empty ;
                      ncd:revise-date 2018-11-06 ;
                    }
                    container advertise-map {
                      description 'Specify route-map for conditional advertisem'
                                + 'ent.'
                                  ;
                      presence 'Specify route-map for conditional advertisement'
                               ;
                      leaf advertise-map-name {
                        description 'Advertise route-map name.'
                                    ;
                        type string {
                          length 1..200 ;
                        }
                        mandatory true ;
                      }
                      choice advertise-map {
                        description 'Specify route-map for conditional advertis'
                                  + 'ement.'
                                    ;
                        mandatory true ;
                        case exist-map {
                          description 'Advertise prefix only if prefix exists.'
                                      ;
                          leaf exist-map-name {
                            description 'Advertise prefix only if prefix exists.'
                                        ;
                            type string {
                              length 1..200 ;
                            }
                            mandatory true ;
                          }
                        }
                        case nonexist-map {
                          description 'Advertise prefix only if prefix does not'
                                    + ' exist.'
                                      ;
                          leaf non-exist-map-name {
                            description 'Advertise prefix only if prefix does not exist.'
                                        ;
                            type string {
                              length 1..200 ;
                            }
                            mandatory true ;
                          }
                        }
                      }
                    }
                    container set-ttl {
                      description 'ebgp-multihop-ttl and ttl-security-hops are '
                                + 'mutex.'
                                  ;
                      choice set-ttl {
                        description 'ebgp-multihop-ttl and ttl-security-hops ar'
                                  + 'e mutex.'
                                    ;
                        case ebgp-multihop-ttl {
                          description 'Allow EBGP neighbors not on directly con'
                                    + 'nected net.'
                                      ;
                          leaf ebgp-multihop {
                            description 'Allow EBGP neighbors not on directly connected net.'
                                        ;
                            type uint8 {
                              range 1..255 ;
                            }
                          }
                        }
                        case ttl-security-hops {
                          description 'Enable EBGP TTL security check.'
                                      ;
                          leaf ttl-security-hops {
                            description 'Enable EBGP TTL security check.'
                                        ;
                            type uint8 {
                              range 1..254 ;
                            }
                          }
                        }
                      }
                    }
                    container neighbor-extend {
                      description 'Specify a neighbor.'
                                  ;
                      container local-as {
                        description 'Specify a local-as number.'
                                    ;
                        presence local-as ;
                        leaf as-number {
                          description 'Autonomous system number (normal or 4 Oc'
                                    + 'tets).'
                                      ;
                          type ncd:asn-dot {
                            pattern '-?([1-9]+(\.(\d*)|0)?)|(0(\.\d+){1})'
                                    ;
                          }
                          mandatory true ;
                        }
                        leaf no-prepend {
                          description 'Do not prepend local-as to updates from '
                                    + 'EBGP peer.'
                                      ;
                          type empty ;
                        }
                        leaf replace-as {
                          description 'Replace real AS with local AS in the EBG'
                                    + 'P updates.'
                                      ;
                          type empty ;
                        }
                        leaf dual-as {
                          description 'Accept real AS or local AS from the EBGP'
                                    + ' peer.'
                                      ;
                          type empty ;
                        }
                      }
                      container password {
                        description 'Set a password of the neighbor.'
                                    ;
                        choice password {
                          description 'Set a password of the neighbor.'
                                      ;
                          case clear-words {
                            description 'Specify the clear password (1-80 characters).'
                                        ;
                            leaf clear-words {
                              description 'The clear password (1-80 characters).'
                                          ;
                              type string {
                                length 1..80 ;
                              }
                            }
                          }
                          case encrypt-words {
                            description 'Specify the encrypted password.'
                                        ;
                            leaf encrypt-words {
                              description 'Specify the encrypted password.'
                                          ;
                              type string {
                                length 64..172 ;
                              }
                            }
                          }
                        }
                      }
                      leaf prefix-list-in-name {
                        description 'Apply prefix list to incoming routes.'
                                    ;
                        type string {
                          length 1..169 ;
                        }
                      }
                      leaf prefix-list-out-name {
                        description 'Apply  prefix list to outbound routes.'
                                    ;
                        type string {
                          length 1..169 ;
                        }
                      }
                      leaf route-map-in-name {
                        description 'Apply route-map to incoming routes.'
                                    ;
                        type string {
                          length 1..200 ;
                        }
                      }
                      leaf route-map-out-name {
                        description 'Apply route-map to outbound routes.'
                                    ;
                        type string {
                          length 1..200 ;
                        }
                      }
                      container maximum-prefix {
                        description 'The action that generated when threshold v'
                                  + 'alue reached.'
                                    ;
                        presence 'The action that generated when threshold valu'
                               + 'e reached'
                                 ;
                        leaf maximum-prefix-number {
                          description 'Maximum number of prefix limit.'
                                      ;
                          type uint32 {
                            range 1..4294967295 ;
                          }
                          mandatory true ;
                        }
                        leaf maximum-prefix-threshold {
                          description 'Threshold value(%) at which to generate '
                                    + 'a warning.'
                                      ;
                          type uint32 {
                            range 1..100 ;
                          }
                          mandatory true ;
                        }
                        choice maximum-prefix-action {
                          description 'The action that generated when threshold'
                                    + ' value reached.'
                                      ;
                          mandatory true ;
                          case peer-action {
                            description 'The action that generated when threshold value reached.'
                                        ;
                            leaf action {
                              description 'The action that generated when threshold value reached.'
                                          ;
                              type enumeration {
                                enum down {
                                  value 0 ;
                                  description 'Break down BGP connection after limit is exceeded.'
                                              ;
                                }
                                enum warning-only {
                                  value 1 ;
                                  description 'Only give warning message when limit is exceeded.'
                                              ;
                                }
                                enum drop-routes {
                                  value 2 ;
                                  description 'Drop routes that exceed the maximum-prefix.'
                                              ;
                                }
                              }
                              mandatory true ;
                            }
                          }
                          case restart {
                            description 'Restart BGP connection after limit is exceeded.'
                                        ;
                            leaf restart-time {
                              description 'Restart interval in minutes.'
                                          ;
                              type uint32 {
                                range 1..30000 ;
                              }
                              units min ;
                              mandatory true ;
                            }
                          }
                        }
                      }
                      container timers {
                        description 'BGP per neighbor timers.'
                                    ;
                        presence timers ;
                        leaf keepalive {
                          description 'Adjust keepalive interval.'
                                      ;
                          type uint32 {
                            range 0..65535 ;
                          }
                          units s ;
                          mandatory true ;
                        }
                        leaf holdtime {
                          description 'Adjust holdtime.'
                                      ;
                          type uint32 {
                            range '0 | 3..65535'
                                  ;
                          }
                          units s ;
                          mandatory true ;
                        }
                      }
                      leaf routepolicy-in-name {
                        description 'Route policy name applied to the inbound r'
                                  + 'outes.'
                                    ;
                        type string {
                          length 1..200 ;
                        }
                        ncd:revise-date 2015-05-18 ;
                      }
                      leaf routepolicy-out-name {
                        description 'Route policy name applied to the outbound '
                                  + 'routes.'
                                    ;
                        type string {
                          length 1..200 ;
                        }
                        ncd:revise-date 2015-05-18 ;
                      }
                      leaf keychain-name {
                        description 'keychain name associated to peer for authe'
                                  + 'ntication'
                                    ;
                        type string {
                          length 1..31 ;
                        }
                        ncd:revise-date 2015-12-21 ;
                      }
                      container transport {
                        description 'Specify TCP path MTU discovery or TCP MSS '
                                  + 'to this neighbor.'
                                    ;
                        choice transport {
                          description 'Specify TCP path MTU discovery or TCP MS'
                                    + 'S to this neighbor.'
                                      ;
                          case path-mtu-discovery {
                            description 'Use transport path MTU discovery.'
                                        ;
                            leaf path-mtu-discovery {
                              description 'Use transport path MTU discovery.'
                                          ;
                              type empty ;
                            }
                          }
                          case mss {
                            description 'Set TCP initial maximum segment size.'
                                        ;
                            leaf mss {
                              description 'Set TCP initial maximum segment size.'
                                          ;
                              type uint32 {
                                range 68..10000 ;
                              }
                            }
                          }
                        }
                        ncd:revise-date 2016-01-06 ;
                      }
                      container withdraw {
                        description 'Withdraw routes when state of track-group '
                                  + 'is down.'
                                    ;
                        presence withdraw ;
                        leaf track-group {
                          description 'Track-group name.'
                                      ;
                          type string {
                            length 1..31 ;
                          }
                          mandatory true ;
                        }
                        leaf route-map {
                          description 'Route-map name.'
                                      ;
                          type string {
                            length 1..200 ;
                          }
                        }
                        ncd:revise-date 2016-02-06 ;
                      }
                      container second-withdraw {
                        description 'Withdraw routes when state of the second t'
                                  + 'rack-group is down.'
                                    ;
                        presence second-withdraw ;
                        leaf track-group {
                          description 'Track-group name.'
                                      ;
                          type string {
                            length 1..31 ;
                          }
                          mandatory true ;
                        }
                        leaf route-map {
                          description 'Route-map name.'
                                      ;
                          type string {
                            length 1..200 ;
                          }
                        }
                        ncd:revise-date 2018-07-12 ;
                      }
                      container idle-hold-time {
                        description 'Specifiy the length of time the peer is he'
                                  + 'ld in the idle state.'
                                    ;
                        presence idle-hold-time ;
                        leaf hold-time {
                          description 'Idle hold time.'
                                      ;
                          type uint32 {
                            range 1..3000 ;
                          }
                          units s ;
                          mandatory true ;
                        }
                        leaf increase {
                          description 'Increase idle hold time doubly to maximu'
                                    + 'm 3000.'
                                      ;
                          type empty ;
                        }
                        ncd:revise-date 2016-03-23 ;
                      }
                      container tracking {
                        description 'Enable peer tracking.'
                                    ;
                        presence tracking ;
                        leaf tracking {
                          status obsolete {
                            ncd:revise-date 2019-01-15 ;
                          }
                          description 'Enable peer tracking.'
                                      ;
                          type empty ;
                          mandatory true ;
                        }
                        leaf tracking-ex {
                          description 'Peer tracking.'
                                      ;
                          type enumeration {
                            enum enable {
                              value 1 ;
                              description 'Enable peer tracking.'
                                          ;
                            }
                            enum disable {
                              value 0 ;
                              description 'Disable peer tracking.'
                                          ;
                            }
                          }
                          ncd:revise-date 2019-01-15 ;
                        }
                        leaf delay {
                          description 'Delay time to reset the session.'
                                      ;
                          type uint32 {
                            range 1..65535 ;
                          }
                          units s ;
                        }
                        ncd:revise-date 2018-08-29 ;
                      }
                      leaf neighbor-stalepath-time {
                        description "Set the max time to hold on to restarting "
                                  + "peer's stale paths."
                                    ;
                        type uint32 {
                          range 1..604800 {
                            description 'Delay value.'
                                        ;
                          }
                        }
                        units s ;
                        ncd:revise-date 2021-02-01 ;
                      }
                      leaf neighbor-stalepath-time-permanent {
                        description 'Hold on stale paths permanently.'
                                    ;
                        type empty ;
                        ncd:revise-date 2021-02-01 ;
                      }
                    }
                    leaf open-delay {
                      description 'Delay to send open message.'
                                  ;
                      type uint32 {
                        range 1..240 ;
                      }
                      units s ;
                    }
                    container shutdown {
                      description 'Shut down this neighbor administratively or '
                                + 'when state of track-group is down.'
                                  ;
                      presence shut-down ;
                      leaf shut-down {
                        description 'Administratively shut down this neighbor.'
                                    ;
                        type empty ;
                        mandatory true ;
                      }
                      leaf track-group {
                        description 'Shut down this neighbor when state of trac'
                                  + 'k-group is down.'
                                    ;
                        type string {
                          length 1..31 ;
                        }
                      }
                      ncd:revise-date 2016-06-12 ;
                    }
                    container route-filter-group {
                      description 'Specify a neighbor to join a route-filter-gr'
                                + 'oup.'
                                  ;
                      presence route-filter-group ;
                      leaf filter-group {
                        description 'Route filter group name (1-31 characters).'
                                    ;
                        type string {
                          length 1..31 ;
                        }
                        mandatory true ;
                      }
                      leaf next-hop-self {
                        description 'Disable the next hop calculation for this '
                                  + 'neighbor.'
                                    ;
                        type empty ;
                      }
                      ncd:revise-date 2017-06-12 ;
                    }
                    leaf enforce-first-as-disable {
                      description 'Not enforce the first AS for EBGP neighbor r'
                                + 'outes'
                                  ;
                      type empty ;
                      ncd:revise-date 2018-01-10 ;
                    }
                    leaf announce-sid {
                      description 'Enable Prefix-SID attribute for this neighbo'
                                + 'r.'
                                  ;
                      type enumeration {
                        enum enable {
                          value 1 ;
                          description 'Enable Prefix-SID attribute for this nei'
                                    + 'ghbor.'
                                      ;
                        }
                      }
                      ncd:revise-date 2018-05-14 ;
                    }
                    leaf enhanced-route-refresh-disable {
                      description 'Enhanced route refresh capability.'
                                  ;
                      type empty ;
                      ncd:revise-date 2018-10-23 ;
                    }
                    container update-source-ex {
                      description 'Specify the update-source configuration of t'
                                + 'he neighbor.'
                                  ;
                      presence 'Specify the update-source configuration of the '
                             + 'neighbor.'
                               ;
                      choice update-source {
                        description 'Specify the update-source configuration of'
                                  + ' the neighbor.'
                                    ;
                        case update-source-if {
                          description 'Specify the update-source interface name'
                                    + ' of the neighbor.'
                                      ;
                          leaf update-source-ifname {
                            description 'Specify the update-source interface name of the neighbor.'
                                        ;
                            type ncd:ifname ;
                          }
                        }
                        case update-source-ipv4 {
                          description 'Specify the update-source IPv4 address o'
                                    + 'f the neighbor.'
                                      ;
                          leaf update-source-addrv4 {
                            description 'Specify the update-source IPv4 address of the neighbor.'
                                        ;
                            type ncd:ipv4-address-none-zero ;
                          }
                        }
                      }
                      ncd:revise-date 2018-11-27 ;
                    }
                    leaf four-byte-as-disable {
                      description 'Disable 4-byte AS capability.'
                                  ;
                      type empty ;
                      ncd:revise-date 2019-01-15 ;
                    }
                    leaf receive-single-label {
                      description 'Receive single label only for label unicast '
                                + 'route.'
                                  ;
                      type enumeration {
                        enum disable {
                          value 0 ;
                          description 'Disable receive single label only for la'
                                    + 'bel unicast route'
                                      ;
                        }
                        enum enable {
                          value 1 ;
                          description 'Enable receive single label only for lab'
                                    + 'el unicast route'
                                      ;
                        }
                      }
                      ncd:revise-date 2019-11-29 ;
                    }
                    leaf receive-single-label-compatible {
                      description 'Receive single label only for label unicast '
                                + 'route.The function is the same as receive-si'
                                + 'ngle-label node.'
                                  ;
                      type enumeration {
                        enum disable {
                          value 0 ;
                          description 'Disable receive single label only for la'
                                    + 'bel unicast route'
                                      ;
                        }
                        enum enable {
                          value 1 ;
                          description 'Enable receive single label only for lab'
                                    + 'el unicast route'
                                      ;
                        }
                      }
                      ncd:revise-date 2020-07-28 ;
                    }
                    leaf ignore-error-packet {
                      description 'Ignore error packet for this neighbor.'
                                  ;
                      type enumeration {
                        enum disable {
                          value 0 ;
                          description 'Disable peer ignore error packet'
                                      ;
                        }
                        enum enable {
                          value 1 ;
                          description 'Enable peer ignore error packet'
                                      ;
                        }
                      }
                      default disable ;
                      ncd:revise-date 2020-01-13 ;
                    }
                  }
                }
                container neighbor-ipv4 {
                  description 'Specify a IPv4 neighbor.'
                              ;
                  list neighbor {
                    description 'Specify a neighbor.'
                                ;
                    key ipv4-address ;
                    leaf ipv4-address {
                      description 'Neighbor IPv4 address.'
                                  ;
                      type ncd:ipv4-address ;
                    }
                    leaf remote-as {
                      description 'Specify a BGP neighbor AS number.'
                                  ;
                      type ncd:asn-dot ;
                    }
                    leaf join-peergroup {
                      description 'Create/Join a peer group(1-31 characters).'
                                  ;
                      type string {
                        length 1..31 ;
                      }
                    }
                    leaf activate {
                      description 'Enable the address family for this neighbor.'
                                  ;
                      type enumeration {
                        enum disable {
                          value 0 ;
                        }
                        enum enable {
                          value 1 ;
                        }
                      }
                    }
                    leaf monitor {
                      description 'Config BMP monitor for the address family of'
                                + ' this neighbor.'
                                  ;
                      type enumeration {
                        enum disable {
                          value 2 ;
                        }
                        enum enable {
                          value 1 ;
                        }
                        enum inherit-global-config {
                          value 0 ;
                        }
                      }
                      ncd:revise-date 2019-07-29 ;
                    }
                    leaf advertisement-interval {
                      description 'Minimum interval between sending BGP routing'
                                + ' which is not locally originated updates.'
                                  ;
                      type uint32 {
                        range 1..65535 ;
                      }
                      units s ;
                    }
                    leaf advertise-maximum-prefix {
                      description 'Maximum number of prefix send to this peer.'
                                  ;
                      type uint32 {
                        range 1..4294967295 ;
                      }
                      ncd:revise-date 2016-01-06 ;
                    }
                    leaf allowas-in {
                      description 'Accept as-path with my AS present in it.'
                                  ;
                      type uint32 {
                        range 1..10 ;
                      }
                    }
                    leaf as-override {
                      description 'Override matching AS-number while sending up'
                                + 'date.'
                                  ;
                      type empty ;
                    }
                    leaf as-path-loopcheck {
                      description 'Check as-path sending BGP routing to EBGP ne'
                                + 'ighbor.'
                                  ;
                      type empty ;
                    }
                    leaf connect-retry-interval {
                      description 'Set data of connect-retry timer for this nei'
                                + 'ghbor.'
                                  ;
                      type uint32 {
                        range 1..65535 ;
                      }
                      units s ;
                    }
                    leaf default-originate {
                      description 'Originate default route to this neighbor.'
                                  ;
                      type empty ;
                    }
                    leaf default-originate-routemap {
                      description 'Map external entry attributes into routing t'
                                + 'able.'
                                  ;
                      type string {
                        length 1..200 ;
                      }
                      ncd:revise-date 2020-07-28 ;
                    }
                    leaf default-originate-routepolicy {
                      description 'Set external entry attributes into routing t'
                                + 'able.'
                                  ;
                      type string {
                        length 1..200 ;
                      }
                      ncd:revise-date 2020-10-10 ;
                    }
                    leaf description {
                      description 'Neighbor specific description.'
                                  ;
                      type ncd:string-with-blank {
                        length 1..80 ;
                      }
                    }
                    container fall-over {
                      description 'Set BFD supporting for fallover.'
                                  ;
                      presence 'Set BFD supporting for fallover'
                               ;
                      leaf bfd {
                        description 'Enable BFD support for fallover.'
                                    ;
                        type empty ;
                        mandatory true ;
                      }
                      container bfd-parameters {
                        description 'The parameters of BFD.'
                                    ;
                        presence bfd-parameters ;
                        choice bfd-parameters {
                          description 'Config bfd parameters'
                                      ;
                          case template-name {
                            description 'Template name'
                                        ;
                            leaf template {
                              description 'BFD template name'
                                          ;
                              type string {
                                length 1..31 ;
                              }
                            }
                            ncd:revise-date 2020-03-31 ;
                          }
                          case parameters {
                            description Parameters ;
                            leaf interval {
                              description 'Minimum send interval.'
                                          ;
                              type uint32 {
                                range 10..990 ;
                              }
                              units ms ;
                              mandatory true ;
                            }
                            leaf min-rx {
                              description 'Minimum receive interval.'
                                          ;
                              type uint32 {
                                range 10..990 ;
                              }
                              units ms ;
                              mandatory true ;
                            }
                            leaf multiplier {
                              description Multiplier. ;
                              type uint8 {
                                range 3..50 ;
                              }
                              mandatory true ;
                            }
                          }
                        }
                      }
                      leaf bfd-hop {
                        description 'bfd optional hop'
                                    ;
                        type enumeration {
                          enum single-hop {
                            value 1 ;
                            description 'Set single-hop bfd'
                                        ;
                          }
                          enum multi-hop {
                            value 2 ;
                            description 'Set multi-hop bfd'
                                        ;
                          }
                        }
                        ncd:revise-date 2019-04-23 ;
                      }
                    }
                    leaf maxas-in {
                      description 'Accept as-path not exceeded maxas-in.'
                                  ;
                      type uint32 {
                        range 1..250 ;
                      }
                    }
                    leaf next-hop-self {
                      description 'Disable the next hop calculation for this ne'
                                + 'ighbor.'
                                  ;
                      type enumeration {
                        enum enable {
                          value 1 ;
                          description 'Apply next-hop-self for EBGP route.'
                                      ;
                        }
                        enum all {
                          value 2 ;
                          description 'Apply next-hop-self for both EBGP and IB'
                                    + 'GP route.'
                                      ;
                        }
                      }
                    }
                    leaf originate-interval {
                      description 'Minimum interval between sending BGP routing'
                                + ' which is locally originated updates.'
                                  ;
                      type uint32 {
                        range 1..65535 ;
                      }
                      units s ;
                    }
                    leaf passive {
                      description "Don't send open messages to this neighbor ac"
                                + "tively."
                                  ;
                      type empty ;
                    }
                    leaf remove-private-as {
                      description 'EBGP use to remove private AS number.'
                                  ;
                      type enumeration {
                        enum disable {
                          value 0 ;
                        }
                        enum enable {
                          value 1 ;
                        }
                      }
                    }
                    leaf send-community {
                      description 'Send community to this neighbor.'
                                  ;
                      type empty ;
                    }
                    leaf send-large-community {
                      description 'Send Large-community to this neighbor.'
                                  ;
                      type empty ;
                      ncd:revise-date 2020-04-16 ;
                    }
                    leaf route-reflector-client {
                      description 'Set this neighbor as a client peer.'
                                  ;
                      type empty ;
                      ncd:revise-date 2019-08-19 ;
                    }
                    leaf send-label {
                      description 'Send NLRI with MPLS label to this neighbor.'
                                  ;
                      type empty ;
                    }
                    leaf send-med {
                      description 'Send metric attribute to this neighbor.'
                                  ;
                      type empty ;
                    }
                    leaf inherit-igp-metric {
                      description 'Med attribute inherited from IGP metric befo'
                                + 're sending updates'
                                  ;
                      type empty ;
                      ncd:revise-date 2017-07-25 ;
                    }
                    leaf shut-down {
                      status obsolete {
                        ncd:revise-date 2016-06-12 ;
                      }
                      description 'Administratively shut down this neighbor.'
                                  ;
                      type empty ;
                    }
                    leaf soft-reconfiguration {
                      status obsolete {
                        ncd:revise-date 2018-01-31 ;
                      }
                      description 'Neighbor soft reconfiguration.'
                                  ;
                      type empty ;
                    }
                    leaf soft-reconfig {
                      type enumeration {
                        enum soft-reconfiguration {
                          value 1 ;
                          description Soft-reconfiguration. ;
                        }
                        enum enforce-soft-reconfiguration {
                          value 2 ;
                          description 'Enforce soft-reconfiguration instead of '
                                    + 'sending route-refresh.'
                                      ;
                        }
                      }
                      ncd:revise-date 2018-01-31 ;
                    }
                    leaf soo {
                      description 'Site-of-Origin extended community.'
                                  ;
                      type union {
                        type ncd:asn-nn ;
                        type ncd:asnd-nn ;
                        type ncd:ipadd-nn ;
                      }
                    }
                    leaf split-update-group {
                      description 'Split neighbor from update group.'
                                  ;
                      type empty ;
                    }
                    leaf update-source {
                      status obsolete {
                        ncd:revise-date 2018-11-27 ;
                      }
                      description 'Source of routing updates.'
                                  ;
                      type ncd:ifname {
                        length 1..31 ;
                      }
                    }
                    leaf weight {
                      description 'Set weight for routes from this neighbor.'
                                  ;
                      type uint32 {
                        range 1..65535 ;
                      }
                    }
                    leaf orf-prefix-filter {
                      description 'Advertise prefixlist ORF capability to this '
                                + 'neighbor.'
                                  ;
                      type enumeration {
                        enum receive {
                          value 1 ;
                          description 'Capability to receive the ORF from this '
                                    + 'neighbor.'
                                      ;
                        }
                        enum send {
                          value 2 ;
                          description 'Capability to send the ORF to this neigh'
                                    + 'bor.'
                                      ;
                        }
                        enum both {
                          value 3 ;
                          description 'Capability to send and receive the ORF.'
                                      ;
                        }
                      }
                    }
                    leaf orf-prefix-filter-cisco {
                      description 'Compatible with CISCO.'
                                  ;
                      type empty ;
                    }
                    leaf aigp {
                      description 'Enable AIGP for this neighbor.'
                                  ;
                      type empty ;
                      ncd:revise-date 2017-11-01 ;
                    }
                    container advertise-map {
                      description 'Specify route-map for conditional advertisem'
                                + 'ent.'
                                  ;
                      presence 'Specify route-map for conditional advertisement'
                               ;
                      leaf advertise-map-name {
                        description 'Advertise route-map name.'
                                    ;
                        type string {
                          length 1..200 ;
                        }
                        mandatory true ;
                      }
                      choice advertise-map {
                        description 'Specify route-map for conditional advertis'
                                  + 'ement.'
                                    ;
                        mandatory true ;
                        case exist-map {
                          description 'Advertise prefix only if prefix exists.'
                                      ;
                          leaf exist-map-name {
                            description 'Advertise prefix only if prefix exists.'
                                        ;
                            type string {
                              length 1..200 ;
                            }
                            mandatory true ;
                          }
                        }
                        case nonexist-map {
                          description 'Advertise prefix only if prefix does not'
                                    + ' exist.'
                                      ;
                          leaf non-exist-map-name {
                            description 'Advertise prefix only if prefix does not exist.'
                                        ;
                            type string {
                              length 1..200 ;
                            }
                            mandatory true ;
                          }
                        }
                      }
                    }
                    container set-ttl {
                      description 'ebgp-multihop-ttl and ttl-security-hops are '
                                + 'mutex.'
                                  ;
                      choice set-ttl {
                        description 'ebgp-multihop-ttl and ttl-security-hops ar'
                                  + 'e mutex.'
                                    ;
                        case ebgp-multihop-ttl {
                          description 'Allow EBGP neighbors not on directly con'
                                    + 'nected net.'
                                      ;
                          leaf ebgp-multihop {
                            description 'Allow EBGP neighbors not on directly connected net.'
                                        ;
                            type uint8 {
                              range 1..255 ;
                            }
                          }
                        }
                        case ttl-security-hops {
                          description 'Enable EBGP TTL security check.'
                                      ;
                          leaf ttl-security-hops {
                            description 'Enable EBGP TTL security check.'
                                        ;
                            type uint8 {
                              range 1..254 ;
                            }
                          }
                        }
                      }
                    }
                    container neighbor-extend {
                      description 'Specify a neighbor.'
                                  ;
                      container local-as {
                        description 'Specify a local-as number.'
                                    ;
                        presence local-as ;
                        leaf as-number {
                          description 'Autonomous system number (normal or 4 Oc'
                                    + 'tets).'
                                      ;
                          type ncd:asn-dot {
                            pattern '-?([1-9]+(\.(\d*)|0)?)|(0(\.\d+){1})'
                                    ;
                          }
                          mandatory true ;
                        }
                        leaf replace-as {
                          description 'Replace real AS with local AS in the EBG'
                                    + 'P updates.'
                                      ;
                          type empty ;
                        }
                        leaf no-prepend {
                          description 'Do not prepend local-as to updates from '
                                    + 'EBGP peer.'
                                      ;
                          type empty ;
                        }
                        leaf dual-as {
                          description 'Accept real AS or local AS from the EBGP'
                                    + ' peer.'
                                      ;
                          type empty ;
                        }
                      }
                      container password {
                        description 'Set a password of the neighbor.'
                                    ;
                        choice password {
                          description 'Set a password of the neighbor.'
                                      ;
                          case clear-words {
                            description 'Specify the clear password (1-80 characters).'
                                        ;
                            leaf clear-words {
                              description 'The clear password (1-80 characters).'
                                          ;
                              type string {
                                length 1..80 ;
                              }
                            }
                          }
                          case encrypt-words {
                            description 'Specify the encrypted password.'
                                        ;
                            leaf encrypt-words {
                              description 'Specify the encrypted password.'
                                          ;
                              type string {
                                length 64..172 ;
                              }
                            }
                          }
                        }
                      }
                      leaf prefix-list-in-name {
                        description 'Apply prefix list to incoming routes.'
                                    ;
                        type string {
                          length 1..169 ;
                        }
                      }
                      leaf prefix-list-out-name {
                        description 'Apply  prefix list to outbound routes.'
                                    ;
                        type string {
                          length 1..169 ;
                        }
                      }
                      leaf route-map-in-name {
                        description 'Apply route-map to incoming routes.'
                                    ;
                        type string {
                          length 1..200 ;
                        }
                      }
                      leaf route-map-out-name {
                        description 'Apply route-map to outbound routes.'
                                    ;
                        type string {
                          length 1..200 ;
                        }
                      }
                      container maximum-prefix {
                        description 'The action that generated when threshold v'
                                  + 'alue reached.'
                                    ;
                        presence 'The action that generated when threshold valu'
                               + 'e reached'
                                 ;
                        leaf maximum-prefix-number {
                          description 'Maximum number of prefix limit.'
                                      ;
                          type uint32 {
                            range 1..4294967295 ;
                          }
                          mandatory true ;
                        }
                        leaf maximum-prefix-threshold {
                          description 'Threshold value(%) at which to generate '
                                    + 'a warning.'
                                      ;
                          type uint32 {
                            range 1..100 ;
                          }
                          mandatory true ;
                        }
                        choice maximum-prefix-action {
                          description 'The action that generated when threshold'
                                    + ' value reached.'
                                      ;
                          mandatory true ;
                          case peer-action {
                            description 'The action that generated when threshold value reached.'
                                        ;
                            leaf action {
                              description 'The action that generated when threshold value reached.'
                                          ;
                              type enumeration {
                                enum down {
                                  value 0 ;
                                  description 'Break down BGP connection after limit is exceeded.'
                                              ;
                                }
                                enum warning-only {
                                  value 1 ;
                                  description 'Only give warning message when limit is exceeded.'
                                              ;
                                }
                                enum drop-routes {
                                  value 2 ;
                                  description 'Drop routes that exceed the maximum-prefix.'
                                              ;
                                }
                              }
                              mandatory true ;
                            }
                          }
                          case restart {
                            description 'Restart BGP connection after limit is exceeded.'
                                        ;
                            leaf restart-time {
                              description 'Restart interval in minutes.'
                                          ;
                              type uint32 {
                                range 1..30000 ;
                              }
                              units min ;
                              mandatory true ;
                            }
                          }
                        }
                      }
                      container timers {
                        description 'BGP per neighbor timers.'
                                    ;
                        presence timers ;
                        leaf keepalive {
                          description 'Adjust keepalive interval.'
                                      ;
                          type uint32 {
                            range 0..65535 ;
                          }
                          units s ;
                          mandatory true ;
                        }
                        leaf holdtime {
                          description 'Adjust holdtime.'
                                      ;
                          type uint32 {
                            range '0 | 3..65535'
                                  ;
                          }
                          units s ;
                          mandatory true ;
                        }
                      }
                      leaf routepolicy-in-name {
                        description 'Route policy name applied to the inbound r'
                                  + 'outes.'
                                    ;
                        type string {
                          length 1..200 ;
                        }
                        ncd:revise-date 2015-05-18 ;
                      }
                      leaf routepolicy-out-name {
                        description 'Route policy name applied to the outbound '
                                  + 'routes.'
                                    ;
                        type string {
                          length 1..200 ;
                        }
                        ncd:revise-date 2015-05-18 ;
                      }
                      leaf keychain-name {
                        description 'Keychain name associated to peer for authe'
                                  + 'ntication.'
                                    ;
                        type string {
                          length 1..31 ;
                        }
                        ncd:revise-date 2015-12-21 ;
                      }
                      container transport {
                        description 'Specify TCP path MTU discovery or TCP MSS '
                                  + 'to this neighbor.'
                                    ;
                        choice transport {
                          description 'Specify TCP path MTU discovery or TCP MS'
                                    + 'S to this neighbor.'
                                      ;
                          case path-mtu-discovery {
                            description 'Use transport path MTU discovery.'
                                        ;
                            leaf path-mtu-discovery {
                              description 'Use transport path MTU discovery.'
                                          ;
                              type empty ;
                            }
                          }
                          case mss {
                            description 'Specify TCP MSS to this neighbor.'
                                        ;
                            leaf mss {
                              description 'Set TCP initial maximum segment size.'
                                          ;
                              type uint32 {
                                range 68..10000 ;
                              }
                            }
                          }
                        }
                        ncd:revise-date 2016-01-06 ;
                      }
                      container withdraw {
                        description 'Withdraw routes when state of track-group '
                                  + 'is down.'
                                    ;
                        presence withdraw ;
                        leaf track-group {
                          description 'Track-group name.'
                                      ;
                          type string {
                            length 1..31 ;
                          }
                          mandatory true ;
                        }
                        leaf route-map {
                          description 'Route-map name.'
                                      ;
                          type string {
                            length 1..200 ;
                          }
                        }
                        ncd:revise-date 2016-02-06 ;
                      }
                      container second-withdraw {
                        description 'Withdraw routes when state of the second t'
                                  + 'rack-group is down.'
                                    ;
                        presence second-withdraw ;
                        leaf track-group {
                          description 'Track-group name.'
                                      ;
                          type string {
                            length 1..31 ;
                          }
                          mandatory true ;
                        }
                        leaf route-map {
                          description 'Route-map name.'
                                      ;
                          type string {
                            length 1..200 ;
                          }
                        }
                        ncd:revise-date 2018-07-12 ;
                      }
                      container idle-hold-time {
                        description 'Specifiy the length of time the peer is he'
                                  + 'ld in the idle state.'
                                    ;
                        presence idle-hold-time ;
                        leaf hold-time {
                          description 'Idle hold time.'
                                      ;
                          type uint32 {
                            range 1..3000 ;
                          }
                          units s ;
                          mandatory true ;
                        }
                        leaf increase {
                          description 'Increase idle hold time doubly to maximu'
                                    + 'm 3000.'
                                      ;
                          type empty ;
                        }
                        ncd:revise-date 2016-03-23 ;
                      }
                      container tracking {
                        description 'Enable peer tracking.'
                                    ;
                        presence tracking ;
                        leaf tracking {
                          status obsolete {
                            ncd:revise-date 2019-01-15 ;
                          }
                          description 'Enable peer tracking.'
                                      ;
                          type empty ;
                          mandatory true ;
                        }
                        leaf tracking-ex {
                          description 'Peer tracking.'
                                      ;
                          type enumeration {
                            enum enable {
                              value 1 ;
                              description 'Enable peer tracking.'
                                          ;
                            }
                            enum disable {
                              value 0 ;
                              description 'Disable peer tracking.'
                                          ;
                            }
                            enum inherit {
                              value 2 ;
                              description 'If the neighbor joined a group, the status of tracking inherited from group.'
                                          ;
                            }
                          }
                          ncd:revise-date 2019-01-15 ;
                        }
                        leaf delay {
                          description 'Delay time to reset the session.'
                                      ;
                          type uint32 {
                            range 1..65535 ;
                          }
                          units s ;
                        }
                        ncd:revise-date 2018-08-29 ;
                      }
                      leaf neighbor-stalepath-time {
                        description "Set the max time to hold on to restarting "
                                  + "peer's stale paths."
                                    ;
                        type uint32 {
                          range 1..604800 {
                            description 'Delay value.'
                                        ;
                          }
                        }
                        units s ;
                        ncd:revise-date 2021-02-01 ;
                      }
                      leaf neighbor-stalepath-time-permanent {
                        description 'Hold on stale paths permanently.'
                                    ;
                        type empty ;
                        ncd:revise-date 2021-02-01 ;
                      }
                    }
                    leaf nouse-peergroup-config {
                      description 'Peer do not use group config set.Only for ge'
                                + 't operation.'
                                  ;
                      type empty ;
                    }
                    leaf open-delay {
                      description 'Delay to send open message.'
                                  ;
                      type uint32 {
                        range 1..240 ;
                      }
                      units s ;
                    }
                    container shutdown {
                      description 'Shut down this neighbor administratively or '
                                + 'when state of track-group is down.'
                                  ;
                      presence shut-down ;
                      leaf shut-down {
                        description 'Administratively shut down this neighbor.'
                                    ;
                        type empty ;
                        mandatory true ;
                      }
                      leaf track-group {
                        description 'Shut down this neighbor when state of trac'
                                  + 'k-group is down.'
                                    ;
                        type string {
                          length 1..31 ;
                        }
                      }
                      ncd:revise-date 2016-06-12 ;
                    }
                    container route-filter-group {
                      description 'Specify a neighbor to join a route-filter-gr'
                                + 'oup.'
                                  ;
                      presence route-filter-group ;
                      leaf filter-group {
                        description 'Route filter group name (1-31 characters).'
                                    ;
                        type string {
                          length 1..31 ;
                        }
                        mandatory true ;
                      }
                      leaf next-hop-self {
                        description 'Disable the next hop calculation for this '
                                  + 'neighbor.'
                                    ;
                        type empty ;
                      }
                      ncd:revise-date 2017-06-12 ;
                    }
                    leaf enforce-first-as-disable {
                      description 'Not enforce the first AS for EBGP neighbor r'
                                + 'outes'
                                  ;
                      type empty ;
                      ncd:revise-date 2018-01-10 ;
                    }
                    leaf announce-sid {
                      description 'Enable Prefix-SID attribute for this neighbo'
                                + 'r.'
                                  ;
                      type enumeration {
                        enum enable {
                          value 1 ;
                          description 'Enable Prefix-SID attribute for this nei'
                                    + 'ghbor.'
                                      ;
                        }
                      }
                      ncd:revise-date 2018-05-14 ;
                    }
                    leaf enhanced-route-refresh-disable {
                      description 'Enhanced route refresh capability.'
                                  ;
                      type empty ;
                      ncd:revise-date 2018-10-23 ;
                    }
                    container update-source-ex {
                      description 'Specify the update-source configuration of t'
                                + 'he neighbor.'
                                  ;
                      presence 'Specify the update-source configuration of the '
                             + 'neighbor.'
                               ;
                      choice update-source {
                        description 'Specify the update-source configuration of'
                                  + ' the neighbor.'
                                    ;
                        case update-source-if {
                          description 'Specify the update-source interface name'
                                    + ' of the neighbor.'
                                      ;
                          leaf update-source-ifname {
                            description 'Specify the update-source interface name of the neighbor.'
                                        ;
                            type ncd:ifname ;
                          }
                        }
                        case update-source-ipv4 {
                          description 'Specify the update-source IPv4 address o'
                                    + 'f the neighbor.'
                                      ;
                          leaf update-source-addrv4 {
                            description 'Specify the update-source IPv4 address of the neighbor.'
                                        ;
                            type ncd:ipv4-address-none-zero ;
                          }
                        }
                      }
                      ncd:revise-date 2018-11-27 ;
                    }
                    leaf four-byte-as-disable {
                      description 'Disable 4-byte AS capability.'
                                  ;
                      type empty ;
                      ncd:revise-date 2019-01-15 ;
                    }
                    leaf receive-single-label {
                      description 'Receive single label only for label unicast '
                                + 'route.'
                                  ;
                      type enumeration {
                        enum disable {
                          value 0 ;
                          description 'Disable receive single label only for la'
                                    + 'bel unicast route'
                                      ;
                        }
                        enum enable {
                          value 1 ;
                          description 'Enable receive single label only for lab'
                                    + 'el unicast route'
                                      ;
                        }
                        enum inherit {
                          value 2 ;
                          description 'If the neighbor joined a group, the stat'
                                    + 'us inherited from group'
                                      ;
                        }
                      }
                      ncd:revise-date 2019-11-29 ;
                    }
                    leaf receive-single-label-compatible {
                      description 'Receive single label only for label unicast '
                                + 'route.The function is the same as receive-si'
                                + 'ngle-label node.'
                                  ;
                      type enumeration {
                        enum disable {
                          value 0 ;
                          description 'Disable receive single label only for la'
                                    + 'bel unicast route'
                                      ;
                        }
                        enum enable {
                          value 1 ;
                          description 'Enable receive single label only for lab'
                                    + 'el unicast route'
                                      ;
                        }
                        enum inherit {
                          value 2 ;
                          description 'If the neighbor joined a group, the stat'
                                    + 'us inherited from group'
                                      ;
                        }
                      }
                      ncd:revise-date 2020-07-28 ;
                    }
                    leaf ignore-error-packet {
                      description 'Ignore error packet for this neighbor.'
                                  ;
                      type enumeration {
                        enum disable {
                          value 0 ;
                          description 'Disable peer ignore error packet'
                                      ;
                        }
                        enum enable {
                          value 1 ;
                          description 'Enable peer ignore error packet'
                                      ;
                        }
                        enum inherit {
                          value 2 ;
                          description 'If the neighbor joined a group, the stat'
                                    + 'us inherited from group.'
                                      ;
                        }
                      }
                      ncd:revise-date 2020-01-13 ;
                    }
                  }
                }
              }
              leaf table-policy {
                description 'Set external entry attributes into routing table.'
                            ;
                type string {
                  length 1..200 ;
                }
                ncd:revise-date 2015-05-18 ;
              }
              container route-scan-time {
                description 'Adjust BGP route scan timers.'
                            ;
                presence 'The ability of BGP route scan.'
                         ;
                leaf interval-wait {
                  description 'The interval of scan waiting. Default value is 5'
                            + '00.'
                              ;
                  type uint32 {
                    range 1..65535 ;
                  }
                  units ms ;
                  mandatory true ;
                }
                leaf initial {
                  description 'The initialization time of scan. Default value i'
                            + 's 50.'
                              ;
                  type uint32 {
                    range 1..65535 ;
                  }
                  units ms ;
                  mandatory true ;
                }
                leaf max-wait {
                  description 'The max waiting time of scan. Default value is 5'
                            + '000.'
                              ;
                  type uint32 {
                    range 1..65535 ;
                  }
                  units ms ;
                  mandatory true ;
                }
                ncd:revise-date 2015-11-20 ;
              }
              container multicast {
                description 'Specify parameters for IPv4 multicast VRF.'
                            ;
                presence 'IPv4 multicast VRF address family.'
                         ;
                container neighbor-ipv4 {
                  description 'Specify a IPv4 neighbor.'
                              ;
                  list neighbor {
                    description 'Specify a neighbor.'
                                ;
                    key ipv4-address ;
                    leaf ipv4-address {
                      description 'Neighbor IPv4 address.'
                                  ;
                      type ncd:ipv4-address ;
                    }
                    leaf activate {
                      description 'Enable the address family for this neighbor.'
                                  ;
                      type enumeration {
                        enum disable {
                          value 0 ;
                        }
                        enum enable {
                          value 1 ;
                        }
                      }
                      default disable ;
                    }
                    leaf as-path-loopcheck {
                      description 'Check as-path sending BGP routing to EBGP ne'
                                + 'ighbor.'
                                  ;
                      type empty ;
                    }
                    leaf split-update-group {
                      description 'Split neighbor from update group.'
                                  ;
                      type empty ;
                    }
                  }
                }
                container network {
                  description 'Specify a network to announce via BGP.'
                              ;
                  presence network-ipv4-multi ;
                  list network {
                    description 'Specify a network to announce via BGP.'
                                ;
                    key 'ip-address ip-mask'
                        ;
                    leaf ip-address {
                      description 'Network prefix.'
                                  ;
                      type ncd:ipv4-address ;
                    }
                    leaf ip-mask {
                      description 'Network mask.'
                                  ;
                      type ncd:ipv4-mask ;
                    }
                    leaf route-map {
                      description 'Route-map to modify the attributes.'
                                  ;
                      type string {
                        length 1..200 ;
                      }
                    }
                    leaf route-policy {
                      description 'Route-policy to modify the attributes.'
                                  ;
                      type string {
                        length 1..200 ;
                      }
                      ncd:revise-date 2020-10-10 ;
                    }
                  }
                }
                container redistribute {
                  description 'Redistribute information from another routing pr'
                            + 'otocol.'
                              ;
                  presence redistribute ;
                  container redistribute {
                    description 'Redistribute information from another routing '
                              + 'protocol.'
                                ;
                    list redistribute {
                      description 'Redistribute information from another routin'
                                + 'g protocol.'
                                  ;
                      key protocol ;
                      leaf protocol {
                        description 'Routing protocol type.'
                                    ;
                        type enumeration {
                          enum connected {
                            value 1 ;
                            description 'Connected routes.'
                                        ;
                          }
                          enum static {
                            value 2 ;
                            description 'Static routes.'
                                        ;
                          }
                          enum rip {
                            value 3 ;
                            description 'Routing information protocol(RIP).'
                                        ;
                          }
                          enum bras-pool {
                            value 24 ;
                            description 'Broadband Remote Access Server pool routes.'
                                        ;
                          }
                          enum ipsec {
                            value 25 ;
                            description 'IPsec routes'
                                        ;
                          }
                          enum hagp {
                            value 26 ;
                            description 'Hybrid access gateway protocol routes.'
                                        ;
                          }
                          enum dyn-leasedline {
                            value 29 ;
                            description 'Dynamic-leased-line routes assigned by AAA.'
                                        ;
                          }
                          enum address {
                            value 9 ;
                            description 'Address routes.'
                                        ;
                          }
                        }
                      }
                      leaf route-map {
                        description 'Apply route-map to redistribute.'
                                    ;
                        type string {
                          length 1..200 ;
                        }
                      }
                      leaf route-policy {
                        description 'Apply route-policy to redistribute.'
                                    ;
                        type string {
                          length 1..200 ;
                        }
                        ncd:revise-date 2020-10-10 ;
                      }
                      container set-metric {
                        description 'Set route metric.'
                                    ;
                        leaf metric {
                          description 'Set route metric.'
                                      ;
                          type uint32 {
                            range 0..4294967295 ;
                          }
                        }
                      }
                    }
                  }
                  container redistribute-isis {
                    description 'Redistribute information from ISIS protocol.'
                                ;
                    list redistribute-isis {
                      description 'Redistribute information from ISIS protocol.'
                                  ;
                      key 'protocol process-id'
                          ;
                      leaf protocol {
                        description 'Routing protocol type(ISIS-1,ISIS-2 or ISI'
                                  + 'S-1-2).'
                                    ;
                        type enumeration {
                          enum isis-1 {
                            value 4 ;
                            description 'IS-IS level-1 routes only.'
                                        ;
                          }
                          enum isis-2 {
                            value 5 ;
                            description 'IS-IS level-2 routes only.'
                                        ;
                          }
                        }
                      }
                      leaf process-id {
                        description 'ISIS process ID.'
                                    ;
                        type uint32 {
                          range 0..65535 ;
                        }
                      }
                      leaf route-map {
                        description 'Apply route-map to redistribute.'
                                    ;
                        type string {
                          length 1..200 ;
                        }
                      }
                      leaf route-policy {
                        description 'Apply route-policy to redistribute.'
                                    ;
                        type string {
                          length 1..200 ;
                        }
                        ncd:revise-date 2020-10-10 ;
                      }
                      container set-metric {
                        description 'Set route metric.'
                                    ;
                        leaf metric {
                          description 'Set route metric.'
                                      ;
                          type uint32 {
                            range 0..4294967295 ;
                          }
                        }
                      }
                    }
                  }
                  container redistribute-ospf {
                    description 'Redistribute information from OSPF protocol.'
                                ;
                    list redistribute-ospf {
                      description 'Redistribute information from OSPF protocol.'
                                  ;
                      key 'protocol process-id'
                          ;
                      leaf protocol {
                        description 'Routing protocol type(OSPF-EXT or OSPF-INT'
                                  + ').'
                                    ;
                        type enumeration {
                          enum ospf-ext {
                            value 7 ;
                            description 'Open shortest path first(OSPF) external routes.'
                                        ;
                          }
                          enum ospf-int {
                            value 8 ;
                            description 'Open shortest path first(OSPF) internal routes.'
                                        ;
                          }
                        }
                      }
                      leaf process-id {
                        description 'OSPF process ID.'
                                    ;
                        type uint32 {
                          range 1..65535 ;
                        }
                      }
                      leaf route-map {
                        description 'Apply route-map to redistribute.'
                                    ;
                        type string {
                          length 1..200 ;
                        }
                      }
                      leaf route-policy {
                        description 'Apply route-policy to redistribute.'
                                    ;
                        type string {
                          length 1..200 ;
                        }
                        ncd:revise-date 2020-10-10 ;
                      }
                      container set-metric {
                        description 'Set route metric.'
                                    ;
                        leaf metric {
                          description 'Set route metric.'
                                      ;
                          type uint32 {
                            range 0..4294967295 ;
                          }
                        }
                      }
                    }
                  }
                }
                leaf default-metric {
                  description 'Set metric of BGP routes without MED.'
                              ;
                  type uint32 {
                    range 0..4294967295 ;
                  }
                  default 0 ;
                  ncd:revise-date 2019-04-10 ;
                }
                ncd:revise-date 2016-01-29 ;
              }
              container additional-paths {
                description 'Additional paths in the BGP table.'
                            ;
                leaf selection-route-map {
                  description 'Selection criteria to pick the additional paths.'
                              ;
                  type string {
                    length 1..200 ;
                  }
                }
                ncd:revise-date 2016-01-06 ;
              }
              leaf urpf-id-download {
                description 'Download URPF-ID information to RTM.'
                            ;
                type empty ;
                ncd:revise-date 2017-11-16 ;
              }
              container group-to-group {
                description 'Configure filter group to filter group route refle'
                          + 'ction.'
                            ;
                presence group-to-group ;
                leaf reflection {
                  description 'Reflection of routes is allowed.'
                              ;
                  type empty ;
                  mandatory true ;
                }
                leaf next-hop-self {
                  description 'Disable the next hop calculation.'
                              ;
                  type empty ;
                }
                ncd:revise-date 2018-08-04 ;
              }
              leaf default-set-mpls-label {
                description 'Set MPLS label for local route.'
                            ;
                type empty ;
                ncd:revise-date 2018-09-03 ;
              }
              leaf ebgp-interface-sensitive {
                description 'Enable or disable interface sensitive for EBGP nei'
                          + 'ghbor.'
                            ;
                type enumeration {
                  enum disable {
                    value 0 ;
                  }
                  enum enable {
                    value 1 ;
                  }
                }
                default enable ;
                ncd:revise-date 2018-12-11 ;
              }
              leaf entropy-label {
                description 'entropy-label enable or disable'
                            ;
                type enumeration {
                  enum disable {
                    value 0 ;
                  }
                  enum enable {
                    value 1 ;
                  }
                }
                ncd:revise-date 2019-02-21 ;
              }
              leaf bgp-bestpath-origin {
                description 'bgp bestpath origin-from L3VPN neighbor or EVPN ne'
                          + 'ighbor.'
                            ;
                type enumeration {
                  enum l3vpn {
                    value 1 ;
                    description 'bgp bestpath origin-from L3VPN neighbor'
                                ;
                  }
                  enum evpn {
                    value 2 ;
                    description 'bgp bestpath origin-from EVPN neighbor'
                                ;
                  }
                }
                ncd:revise-date 2019-08-08 ;
              }
              leaf link-bandwidth-download {
                description 'Download link-bandwidth information to RTM.'
                            ;
                type empty ;
                ncd:revise-date 2019-10-22 ;
              }
              leaf bgp-bestpath-nexthop-priority {
                description 'Set BGP bestpath nexthop priority.'
                            ;
                type enumeration {
                  enum ipv4 {
                    value 1 ;
                    description 'BGP bestpath nexthop priority is ipv4'
                                ;
                  }
                  enum ipv6 {
                    value 2 ;
                    description 'BGP bestpath nexthop priority is ipv6'
                                ;
                  }
                }
                ncd:revise-date 2020-08-29 ;
              }
              container rib-only {
                description 'BGP routes are not delivered to the IP routing tab'
                          + 'le.'
                            ;
                presence 'BGP routes are not delivered to the IP routing table'
                         ;
                leaf rib-only-set {
                  description 'Enable rib-only.'
                              ;
                  type empty ;
                  mandatory true ;
                }
                leaf rib-only-routemap {
                  description 'Routing policy.'
                              ;
                  type string {
                    length 1..200 ;
                  }
                }
                leaf rib-only-routepolicy {
                  description 'Routing policy.'
                              ;
                  type string {
                    length 1..200 ;
                  }
                  ncd:revise-date 2020-10-10 ;
                }
                ncd:revise-date 2020-03-02 ;
              }
              leaf slow-peer-detection {
                description 'Set slow peer detection.'
                            ;
                type enumeration {
                  enum disable {
                    value 0 ;
                    description 'Disable slow peer detection'
                                ;
                  }
                  enum enable {
                    value 1 ;
                    description 'Enable slow peer detection'
                                ;
                  }
                }
                default disable ;
                ncd:revise-date 2020-09-08 ;
              }
              leaf slow-peer-detection-threshold {
                description 'Set threshold time for slow peer.Default value is '
                          + '300.'
                            ;
                type uint32 {
                  range 120..3600 {
                    description 'Threshold time range.'
                                ;
                  }
                }
                units s ;
                default 300 ;
                ncd:revise-date 2020-09-08 ;
              }
              leaf slow-peer-detection-recover {
                description 'Set recover time for slow peer.Default value is 30'
                          + '0.'
                            ;
                type uint32 {
                  range 120..3600 {
                    description 'Recover time range.'
                                ;
                  }
                }
                units s ;
                default 300 ;
                ncd:revise-date 2020-09-08 ;
              }
              leaf download-community {
                description 'The maximum number of communities for one route.'
                            ;
                type uint8 {
                  range 1..255 ;
                }
                ncd:revise-date 2020-10-10 ;
              }
              leaf bestpath-external {
                description 'Routes from external peer or RR client are preferr'
                          + 'ed in bestpath selection.'
                            ;
                type enumeration {
                  enum inherit {
                    value 0 ;
                    description 'Inherit from address family VPNv4 or L2VPN EVPN'
                                ;
                  }
                  enum enable {
                    value 1 ;
                  }
                  enum disable {
                    value 2 ;
                  }
                }
                default inherit ;
                ncd:revise-date 2020-11-23 ;
              }
              leaf bestpath-igp-metric-compare {
                description 'Compare IGP metric in maximum-paths.'
                            ;
                type enumeration {
                  enum inherit {
                    value 0 ;
                    description 'Inherit from address family VPNv4 or L2VPN EVPN'
                                ;
                  }
                  enum enable {
                    value 1 ;
                  }
                  enum disable {
                    value 2 ;
                  }
                }
                default inherit ;
                ncd:revise-date 2020-11-23 ;
              }
              leaf bestpath-igp-metric-ignore {
                description 'Ignore IGP metric in bestpath selection.'
                            ;
                type enumeration {
                  enum inherit {
                    value 0 ;
                    description 'Inherit from address family VPNv4 or L2VPN EVPN'
                                ;
                  }
                  enum enable {
                    value 1 ;
                  }
                  enum disable {
                    value 2 ;
                  }
                }
                default inherit ;
                ncd:revise-date 2020-11-23 ;
              }
            }
          }
          container address-family-evpn {
            description 'Configuration in address family L2VPN-EVPN mode.'
                        ;
            presence 'L2VPN-EVPN address family.'
                     ;
            leaf defaults-set-flag {
              status obsolete {
                ncd:revise-date 2020-07-28 ;
              }
              description 'Flag of defaults.Only for get operation.When this va'
                        + 'lue expressed as a binary,The lowest bit indicate di'
                        + 'stance-ibgp,the next bit distance-ebgp,then maxpaths'
                        + '-ebgp,then default-metric,then wait-for-end-of-rib,t'
                        + 'hen constrain-rt-filter.'
                          ;
              type uint32 ;
              default 0 ;
              ncd:revise-date 2018-01-31 ;
            }
            leaf default-metric {
              description 'Set metric of BGP routes without MED.'
                          ;
              type uint32 {
                range 0..4294967295 ;
              }
              default 0 ;
              ncd:revise-date 2017-02-23 ;
            }
            leaf distance-bgp-external {
              description 'Distance for routes external to the AS.'
                          ;
              type uint32 {
                range 1..255 ;
              }
              default 20 ;
              ncd:revise-date 2020-09-08 ;
            }
            leaf distance-bgp-internal {
              description 'Distance for routes internal to the AS.'
                          ;
              type uint32 {
                range 1..255 ;
              }
              default 200 ;
              ncd:revise-date 2020-09-08 ;
            }
            leaf distance-route-map {
              description 'Define distance by route-map.This node has higher pr'
                        + 'iority than distance-bgp-internal and distance-bgp-e'
                        + 'xternal.'
                          ;
              type string {
                length 1..200 ;
              }
              ncd:revise-date 2020-09-08 ;
            }
            leaf distance-route-policy {
              description 'Define distance by route-policy.This node has higher'
                        + ' priority than distance-bgp-internal and distance-bg'
                        + 'p-external.'
                          ;
              type string {
                length 1..200 ;
              }
              ncd:revise-date 2020-10-10 ;
            }
            leaf frr-capability {
              description 'Enable FRR capability.'
                          ;
              type empty ;
              ncd:revise-date 2020-03-02 ;
            }
            leaf frr-wtr {
              description 'Set the WTR time.'
                          ;
              type int32 {
                range 1..12 ;
              }
              units min ;
              ncd:revise-date 2020-03-02 ;
            }
            leaf nexthop-recursive-default-route {
              description 'Nexthop recursive lookup default-route.'
                          ;
              type enumeration {
                enum enable {
                  value 1 ;
                }
                enum disable {
                  value 0 ;
                }
              }
              default enable ;
              ncd:revise-date 2020-07-28 ;
            }
            leaf nexthop-recursive-null1 {
              description 'Nexthop recursive lookup null1.'
                          ;
              type enumeration {
                enum enable {
                  value 1 ;
                }
                enum disable {
                  value 0 ;
                }
              }
              default enable ;
              ncd:revise-date 2020-12-09 ;
            }
            container neighbor-evpn {
              description 'Specify a neighbor.'
                          ;
              presence neighbor-evpn ;
              container neighbor-group {
                description 'Specify a peergroup neighbor.'
                            ;
                list neighbor-peergroup {
                  description 'Specify a peergroup neighbor.'
                              ;
                  key neighbor-group ;
                  leaf neighbor-group {
                    description 'Peer group name (1-31 characters).'
                                ;
                    type string {
                      length 1..31 ;
                    }
                  }
                  leaf activate {
                    description 'Enable the address family for this peergroup n'
                              + 'eighbor.'
                                ;
                    type enumeration {
                      enum disable {
                        value 0 ;
                      }
                      enum enable {
                        value 1 ;
                      }
                    }
                  }
                  leaf monitor {
                    description 'Config BMP monitor for the address family of t'
                              + 'his neighbor.'
                                ;
                    type enumeration {
                      enum disable {
                        value 2 ;
                      }
                      enum enable {
                        value 1 ;
                      }
                      enum inherit-global-config {
                        value 0 ;
                      }
                    }
                    ncd:revise-date 2019-07-29 ;
                  }
                  leaf allowas-in {
                    description 'Accept as-path with my AS present in it.'
                                ;
                    type uint32 {
                      range 1..10 ;
                    }
                    ncd:revise-date 2020-03-02 ;
                  }
                  leaf route-reflector-client {
                    description 'Set this peergroup neighbor as a client peer.'
                                ;
                    type empty ;
                  }
                  leaf send-med {
                    description 'Send metric attribute to this neighbor.'
                                ;
                    type empty ;
                    ncd:revise-date 2017-02-23 ;
                  }
                  leaf split-update-group {
                    description 'Split neighbor from update group.'
                                ;
                    type empty ;
                  }
                  choice nh-unchanged {
                    case next-hop-unchanged {
                      description 'NEXT_HOP of the IBGP path propagated unchang'
                                + 'ed to this neighbor.'
                                  ;
                      leaf next-hop-unchanged {
                        description 'Propagate next hop unchanged for IBGP path'
                                  + 's to this neighbor.'
                                    ;
                        type empty ;
                      }
                    }
                    case next-hop-unchanged-all {
                      description 'NEXT_HOP of either EBGP or IBGP path propaga'
                                + 'ted unchanged to this neighbor.'
                                  ;
                      leaf next-hop-unchanged-all {
                        description 'NEXT_HOP of either EBGP or IBGP path propa'
                                  + 'gated unchanged to this neighbor.'
                                    ;
                        type empty ;
                      }
                      ncd:revise-date 2020-04-07 ;
                    }
                  }
                  leaf next-hop-self {
                    description 'Disable the next hop calculation for this neig'
                              + 'hbor.'
                                ;
                    type enumeration {
                      enum enable {
                        value 1 ;
                        description 'Apply next-hop-self for EBGP route.'
                                    ;
                      }
                      enum all {
                        value 2 ;
                        description 'Apply next-hop-self for both EBGP and IBGP'
                                  + ' route.'
                                    ;
                      }
                    }
                    ncd:revise-date 2016-10-25 ;
                  }
                  leaf capability-orf-prefix-list {
                    description 'Advertise prefixlist ORF capability to this ne'
                              + 'ighbor.'
                                ;
                    type enumeration {
                      enum receive {
                        value 1 ;
                        description 'Capability to receive the ORF from this ne'
                                  + 'ighbor.'
                                    ;
                      }
                      enum send {
                        value 2 ;
                        description 'Capability to send the ORF to this neighbo'
                                  + 'r.'
                                    ;
                      }
                      enum both {
                        value 3 ;
                        description 'Capability to send and receive the ORF.'
                                    ;
                      }
                    }
                    ncd:revise-date 2017-04-05 ;
                  }
                  leaf default-originate-all {
                    description 'Notify all VPN default route.'
                                ;
                    type enumeration {
                      enum both {
                        value 2 ;
                        description 'IPv4 and IPv6 prefix.'
                                    ;
                      }
                      enum ipv4 {
                        value 3 ;
                        description 'IPv4 prefix.'
                                    ;
                      }
                      enum ipv6 {
                        value 4 ;
                        description 'IPv6 prefix.'
                                    ;
                      }
                    }
                    ncd:revise-date 2018-05-14 ;
                  }
                  leaf default-originate-routemap {
                    description 'Map external entry attributes into routing tab'
                              + 'le.'
                                ;
                    type string {
                      length 1..200 ;
                    }
                    ncd:revise-date 2020-07-28 ;
                  }
                  leaf default-originate-routepolicy {
                    description 'Set external entry attributes into routing tab'
                              + 'le.'
                                ;
                    type string {
                      length 1..200 ;
                    }
                    ncd:revise-date 2020-10-10 ;
                  }
                  leaf aigp {
                    description 'Enable AIGP for this neighbor.'
                                ;
                    type empty ;
                    ncd:revise-date 2017-11-01 ;
                  }
                  container neighbor-extend {
                    description 'Specify a peergroup neighbor router.'
                                ;
                    leaf prefix-list-in-name {
                      description 'Apply prefix list to incoming routes.'
                                  ;
                      type string {
                        length 1..169 ;
                      }
                      ncd:revise-date 2017-04-05 ;
                    }
                    leaf prefix-list-out-name {
                      description 'Apply  prefix list to outbound routes.'
                                  ;
                      type string {
                        length 1..169 ;
                      }
                      ncd:revise-date 2017-04-05 ;
                    }
                    leaf routemap-in-name {
                      description 'Apply map to incoming routes.'
                                  ;
                      type string {
                        length 1..200 ;
                      }
                    }
                    leaf routemap-out-name {
                      description 'Apply map to outbound routes.'
                                  ;
                      type string {
                        length 1..200 ;
                      }
                    }
                    leaf add-paths-receive {
                      description 'Receive additional paths from this neighbor.'
                                  ;
                      type empty ;
                      ncd:revise-date 2016-07-07 ;
                    }
                    container add-paths-send {
                      description 'Send additional paths to this neighbor.'
                                  ;
                      choice add-paths-send {
                        description 'Send additional paths to this neighbor.'
                                    ;
                        default send-one-path ;
                        case send-one-path {
                          description 'Send one additional path to this neighbo'
                                    + 'r.'
                                      ;
                          leaf send {
                            description 'Send additional paths to this neighbor.'
                                        ;
                            type empty ;
                          }
                        }
                        case send-multi-paths {
                          description 'Send additional multi-paths to this neig'
                                    + 'hbor.'
                                      ;
                          leaf paths-number {
                            description 'Number of paths for a prefix.'
                                        ;
                            type uint32 {
                              range 2..32 ;
                            }
                          }
                          leaf prefixlist {
                            description 'Prefixlist of filtering additional paths.'
                                        ;
                            type string {
                              length 1..169 ;
                            }
                            ncd:revise-date 2020-12-02 ;
                          }
                        }
                      }
                      ncd:revise-date 2016-07-07 ;
                    }
                    container withdraw {
                      description 'Withdraw routes when state of track-group is'
                                + ' down.'
                                  ;
                      presence withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                      ncd:revise-date 2018-06-20 ;
                    }
                    container second-withdraw {
                      description 'Withdraw routes when state of the second tra'
                                + 'ck-group is down.'
                                  ;
                      presence second-withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                      ncd:revise-date 2018-07-12 ;
                    }
                    container maximum-prefix {
                      description 'The action that generated when threshold val'
                                + 'ue reached.'
                                  ;
                      presence 'The action that generated when threshold value '
                             + 'reached'
                               ;
                      leaf maximum-prefix-number {
                        description 'Maximum number of prefix limit.'
                                    ;
                        type uint32 {
                          range 1..4294967295 ;
                        }
                        mandatory true ;
                      }
                      leaf maximum-prefix-threshold {
                        description 'Threshold value(%) at which to generate a '
                                  + 'warning.'
                                    ;
                        type uint32 {
                          range 1..100 ;
                        }
                        mandatory true ;
                      }
                      choice maximum-prefix-action {
                        description 'The action that generated when threshold v'
                                  + 'alue reached.'
                                    ;
                        mandatory true ;
                        case peer-action {
                          description 'The action that generated when threshold'
                                    + ' value reached.'
                                      ;
                          leaf action {
                            description 'The action that generated when threshold value reached.'
                                        ;
                            type enumeration {
                              enum down {
                                value 0 ;
                                description 'Break down BGP connection after limit is exceeded.'
                                            ;
                              }
                              enum warning-only {
                                value 1 ;
                                description 'Only give warning message when limit is exceeded.'
                                            ;
                              }
                              enum drop-routes {
                                value 2 ;
                                description 'Drop routes that exceed the maximum-prefix.'
                                            ;
                              }
                            }
                            mandatory true ;
                          }
                        }
                        case restart {
                          description 'Restart BGP connection after limit is ex'
                                    + 'ceeded.'
                                      ;
                          leaf restart-time {
                            description 'Restart interval in minutes.'
                                        ;
                            type uint32 {
                              range 1..30000 ;
                            }
                            units min ;
                            mandatory true ;
                          }
                        }
                      }
                      ncd:revise-date 2019-08-08 ;
                    }
                    leaf routepolicy-in-name {
                      description 'Route policy name applied to the inbound rou'
                                + 'tes.'
                                  ;
                      type string {
                        length 1..200 ;
                      }
                      ncd:revise-date 2020-10-10 ;
                    }
                    leaf routepolicy-out-name {
                      description 'Route policy name applied to the outbound ro'
                                + 'utes.'
                                  ;
                      type string {
                        length 1..200 ;
                      }
                      ncd:revise-date 2020-10-10 ;
                    }
                  }
                  container default-originate-vrf {
                    description 'Originate default route to this neighbor for c'
                              + 'ertain VRF.'
                                ;
                    list default-originate-vrf {
                      description 'Originate default route to this neighbor for'
                                + ' certain VRF.'
                                  ;
                      key vrf-name ;
                      leaf vrf-name {
                        description 'VPN Routing/Forwarding instance.'
                                    ;
                        type string {
                          length 1..32 ;
                        }
                      }
                      leaf prefix-type {
                        description 'The type of originate default route.'
                                    ;
                        type enumeration {
                          enum both {
                            value 2 ;
                            description 'IPv4 and IPv6 prefix.'
                                        ;
                          }
                          enum ipv4 {
                            value 3 ;
                            description 'IPv4 prefix.'
                                        ;
                          }
                          enum ipv6 {
                            value 4 ;
                            description 'IPv6 prefix.'
                                        ;
                          }
                        }
                        mandatory true ;
                      }
                      choice prefix-list {
                        description 'Prefix list name.'
                                    ;
                        case peer-list {
                          description 'Prefix list name of peer list.'
                                      ;
                          leaf peer-list-name {
                            description 'Prefix list name of peer list.'
                                        ;
                            type string {
                              length 1..169 ;
                            }
                          }
                          ncd:revise-date 2019-01-10 ;
                        }
                        case vrf-peer-list {
                          description 'Prefix list name of VRF routes list.'
                                      ;
                          leaf vrf-peer-list-name {
                            description 'Prefix list name of VRF routes list.'
                                        ;
                            type string {
                              length 1..169 ;
                            }
                          }
                          ncd:revise-date 2019-09-04 ;
                        }
                        ncd:revise-date 2019-01-10 ;
                      }
                    }
                    ncd:revise-date 2018-05-14 ;
                  }
                  container virtual {
                    description 'Set spoke PE.'
                                ;
                    presence virtual ;
                    leaf virtual-spoke {
                      description 'Enable spoke PE.'
                                  ;
                      type empty ;
                      mandatory true ;
                    }
                    leaf reflect-next-hop-self {
                      description 'Set next-hop self when reflection.'
                                  ;
                      type empty ;
                    }
                    leaf check-upstream-pe {
                      description 'Check upstream PE when advertising default r'
                                + 'oute.'
                                  ;
                      type empty ;
                    }
                    leaf by-vrf {
                      description 'Send specific route by default-originate con'
                                + 'fig.'
                                  ;
                      type empty ;
                      ncd:revise-date 2019-12-31 ;
                    }
                    ncd:revise-date 2018-05-14 ;
                  }
                  container route-filter-group {
                    description 'Specify a neighbor to join a route-filter-grou'
                              + 'p.'
                                ;
                    presence route-filter-group ;
                    leaf filter-group {
                      description 'Route filter group name (1-31 characters).'
                                  ;
                      type string {
                        length 1..31 ;
                      }
                      mandatory true ;
                    }
                    leaf next-hop-self {
                      description 'Disable the next hop calculation for this ne'
                                + 'ighbor.'
                                  ;
                      type empty ;
                    }
                    ncd:revise-date 2018-08-04 ;
                  }
                  leaf announce-sid {
                    description 'Enable Prefix-SID attribute for this neighbor.'
                                ;
                    type enumeration {
                      enum enable {
                        value 1 ;
                        description 'Enable Prefix-SID attribute for this neigh'
                                  + 'bor.'
                                    ;
                      }
                    }
                    ncd:revise-date 2018-05-14 ;
                  }
                  leaf send-community {
                    description 'Send community to this neighbor.'
                                ;
                    type empty ;
                    ncd:revise-date 2018-05-14 ;
                  }
                  leaf send-large-community {
                    description 'Send Large-community to this neighbor.'
                                ;
                    type empty ;
                    ncd:revise-date 2020-04-16 ;
                  }
                  leaf send-ope {
                    description 'Send OPE to this neighbor.'
                                ;
                    type empty ;
                    ncd:revise-date 2019-06-22 ;
                  }
                  leaf weight {
                    description 'Set weight for routes from this neighbor.'
                                ;
                    type uint32 {
                      range 1..65535 ;
                    }
                    ncd:revise-date 2018-05-14 ;
                  }
                  leaf send-local-route-without-esi-reference {
                    description 'Send local EVPN route without ESI reference.'
                                ;
                    type empty ;
                    ncd:revise-date 2018-07-21 ;
                  }
                  leaf soft-reconfig {
                    description 'Neighbor soft reconfiguration.'
                                ;
                    type enumeration {
                      enum soft-reconfiguration {
                        value 1 ;
                        description Soft-reconfiguration. ;
                      }
                      enum enforce-soft-reconfiguration {
                        value 2 ;
                        description 'Enforce soft-reconfiguration instead of se'
                                  + 'nding route-refresh.'
                                    ;
                      }
                    }
                    ncd:revise-date 2019-08-08 ;
                  }
                  leaf vpn-orf {
                    description 'Peer route-target ORF capability'
                                ;
                    type enumeration {
                      enum disable {
                        value 0 ;
                        description 'Disable peer route-target ORF capability'
                                    ;
                      }
                      enum enable {
                        value 1 ;
                        description 'Enable peer route-target ORF capability'
                                    ;
                      }
                    }
                    ncd:revise-date 2020-02-08 ;
                  }
                  leaf border-gateway {
                    description 'Set this peergroup as border-gateway peer'
                                ;
                    type enumeration {
                      enum disable {
                        value 0 ;
                        description 'disable peer border-gateway'
                                    ;
                      }
                      enum enable {
                        value 1 ;
                        description 'enable peer border-gateway'
                                    ;
                      }
                    }
                    ncd:revise-date 2019-09-10 ;
                  }
                  leaf adv-tunnel-encap {
                    description 'Advertise tunnel encapsulation type'
                                ;
                    type enumeration {
                      enum vxlan {
                        value 1 ;
                      }
                      enum mpls {
                        value 2 ;
                      }
                      enum srv6 {
                        value 4 ;
                      }
                    }
                    ncd:revise-date 2019-11-06 ;
                  }
                  container route-server-client {
                    description 'Set route server client only valid for ebgp pe'
                              + 'er.'
                                ;
                    presence route-server-client ;
                    leaf route-svr-client {
                      description 'Set route server client only valid for ebgp '
                                + 'peer.'
                                  ;
                      type empty ;
                      mandatory true ;
                    }
                    ncd:revise-date 2020-04-07 ;
                  }
                  leaf remove-private-as {
                    description 'EBGP use to remove private AS number.'
                                ;
                    type enumeration {
                      enum disable {
                        value 0 ;
                      }
                      enum enable {
                        value 1 ;
                      }
                    }
                    ncd:revise-date 2020-09-24 ;
                  }
                }
              }
              container neighbor-ipv4 {
                description 'Specify a IPv4 neighbor router.'
                            ;
                list neighbor {
                  description 'Specify a neighbor.'
                              ;
                  key ipv4-address ;
                  leaf ipv4-address {
                    description 'Neighbor IP address.'
                                ;
                    type ncd:ipv4-address ;
                  }
                  leaf joined-group {
                    description 'Only for read operation. The joined group name.'
                                ;
                    type string {
                      length 1..31 ;
                    }
                    ncd:revise-date 2016-05-16 ;
                  }
                  leaf activate {
                    description 'Enable the address family for this neighbor.'
                                ;
                    type enumeration {
                      enum disable {
                        value 0 ;
                      }
                      enum enable {
                        value 1 ;
                      }
                    }
                  }
                  leaf monitor {
                    description 'Config BMP monitor for the address family of t'
                              + 'his neighbor.'
                                ;
                    type enumeration {
                      enum disable {
                        value 2 ;
                      }
                      enum enable {
                        value 1 ;
                      }
                      enum inherit-global-config {
                        value 0 ;
                      }
                    }
                    ncd:revise-date 2019-07-29 ;
                  }
                  leaf allowas-in {
                    description 'Accept as-path with my AS present in it.'
                                ;
                    type uint32 {
                      range 1..10 ;
                    }
                    ncd:revise-date 2020-03-02 ;
                  }
                  leaf route-reflector-client {
                    description 'Set this neighbor as a client peer.'
                                ;
                    type empty ;
                  }
                  leaf send-med {
                    description 'Send metric attribute to this neighbor.'
                                ;
                    type empty ;
                    ncd:revise-date 2017-02-23 ;
                  }
                  leaf split-update-group {
                    description 'Split neighbor from update group.'
                                ;
                    type empty ;
                  }
                  choice nh-unchanged {
                    case next-hop-unchanged {
                      description 'NEXT_HOP of the IBGP path propagated unchang'
                                + 'ed to this neighbor.'
                                  ;
                      leaf next-hop-unchanged {
                        description 'Propagate next hop unchanged for IBGP path'
                                  + 's to this neighbor.'
                                    ;
                        type empty ;
                      }
                    }
                    case next-hop-unchanged-all {
                      description 'NEXT_HOP of either EBGP or IBGP path propaga'
                                + 'ted unchanged to this neighbor.'
                                  ;
                      leaf next-hop-unchanged-all {
                        description 'NEXT_HOP of either EBGP or IBGP path propa'
                                  + 'gated unchanged to this neighbor.'
                                    ;
                        type empty ;
                      }
                      ncd:revise-date 2020-04-07 ;
                    }
                  }
                  leaf next-hop-self {
                    description 'Disable the next hop calculation for this neig'
                              + 'hbor.'
                                ;
                    type enumeration {
                      enum enable {
                        value 1 ;
                        description 'Apply next-hop-self for EBGP route.'
                                    ;
                      }
                      enum all {
                        value 2 ;
                        description 'Apply next-hop-self for both EBGP and IBGP'
                                  + ' route.'
                                    ;
                      }
                    }
                    ncd:revise-date 2016-10-25 ;
                  }
                  leaf capability-orf-prefix-list {
                    description 'Advertise prefixlist ORF capability to this ne'
                              + 'ighbor.'
                                ;
                    type enumeration {
                      enum receive {
                        value 1 ;
                        description 'Capability to receive the ORF from this ne'
                                  + 'ighbor.'
                                    ;
                      }
                      enum send {
                        value 2 ;
                        description 'Capability to send the ORF to this neighbo'
                                  + 'r.'
                                    ;
                      }
                      enum both {
                        value 3 ;
                        description 'Capability to send and receive the ORF.'
                                    ;
                      }
                    }
                    ncd:revise-date 2017-04-05 ;
                  }
                  leaf default-originate-all {
                    description 'Notify all VPN default route.'
                                ;
                    type enumeration {
                      enum both {
                        value 2 ;
                        description 'IPv4 and IPv6 prefix.'
                                    ;
                      }
                      enum ipv4 {
                        value 3 ;
                        description 'IPv4 prefix.'
                                    ;
                      }
                      enum ipv6 {
                        value 4 ;
                        description 'IPv6 prefix.'
                                    ;
                      }
                    }
                    ncd:revise-date 2018-05-14 ;
                  }
                  leaf default-originate-routemap {
                    description 'Map external entry attributes into routing tab'
                              + 'le.'
                                ;
                    type string {
                      length 1..200 ;
                    }
                    ncd:revise-date 2020-07-28 ;
                  }
                  leaf default-originate-routepolicy {
                    description 'Set external entry attributes into routing tab'
                              + 'le.'
                                ;
                    type string {
                      length 1..200 ;
                    }
                    ncd:revise-date 2020-10-10 ;
                  }
                  leaf aigp {
                    description 'Enable AIGP for this neighbor.'
                                ;
                    type empty ;
                    ncd:revise-date 2017-11-01 ;
                  }
                  container neighbor-extend {
                    description 'Specify a neighbor.'
                                ;
                    leaf prefix-list-in-name {
                      description 'Apply prefix list to incoming routes.'
                                  ;
                      type string {
                        length 1..169 ;
                      }
                      ncd:revise-date 2017-04-05 ;
                    }
                    leaf prefix-list-out-name {
                      description 'Apply  prefix list to outbound routes.'
                                  ;
                      type string {
                        length 1..169 ;
                      }
                      ncd:revise-date 2017-04-05 ;
                    }
                    leaf routemap-in-name {
                      description 'Apply map to incoming routes.'
                                  ;
                      type string {
                        length 1..200 ;
                      }
                    }
                    leaf routemap-out-name {
                      description 'Apply map to outbound routes.'
                                  ;
                      type string {
                        length 1..200 ;
                      }
                    }
                    leaf add-paths-receive {
                      description 'Receive additional paths from this neighbor.'
                                  ;
                      type empty ;
                      ncd:revise-date 2016-07-07 ;
                    }
                    container add-paths-send {
                      description 'Send additional paths to this neighbor.'
                                  ;
                      choice add-paths-send {
                        description 'Send additional paths to this neighbor.'
                                    ;
                        default send-one-path ;
                        case send-one-path {
                          description 'Send one additional path to this neighbo'
                                    + 'r.'
                                      ;
                          leaf send {
                            description 'Send additional paths to this neighbor.'
                                        ;
                            type empty ;
                          }
                        }
                        case send-multi-paths {
                          description 'Send additional multi-paths to this neig'
                                    + 'hbor.'
                                      ;
                          leaf paths-number {
                            description 'Number of paths for a prefix.'
                                        ;
                            type uint32 {
                              range 2..32 ;
                            }
                          }
                          leaf prefixlist {
                            description 'Prefixlist of filtering additional paths.'
                                        ;
                            type string {
                              length 1..169 ;
                            }
                            ncd:revise-date 2020-12-02 ;
                          }
                        }
                      }
                      ncd:revise-date 2016-07-07 ;
                    }
                    container withdraw {
                      description 'Withdraw routes when state of track-group is'
                                + ' down.'
                                  ;
                      presence withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                      ncd:revise-date 2018-06-20 ;
                    }
                    container second-withdraw {
                      description 'Withdraw routes when state of the second tra'
                                + 'ck-group is down.'
                                  ;
                      presence second-withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                      ncd:revise-date 2018-07-12 ;
                    }
                    container maximum-prefix {
                      description 'The action that generated when threshold val'
                                + 'ue reached.'
                                  ;
                      presence 'The action that generated when threshold value '
                             + 'reached'
                               ;
                      leaf maximum-prefix-number {
                        description 'Maximum number of prefix limit.'
                                    ;
                        type uint32 {
                          range 1..4294967295 ;
                        }
                        mandatory true ;
                      }
                      leaf maximum-prefix-threshold {
                        description 'Threshold value(%) at which to generate a '
                                  + 'warning.'
                                    ;
                        type uint32 {
                          range 1..100 ;
                        }
                        mandatory true ;
                      }
                      choice maximum-prefix-action {
                        description 'The action that generated when threshold v'
                                  + 'alue reached.'
                                    ;
                        mandatory true ;
                        case peer-action {
                          description 'The action that generated when threshold'
                                    + ' value reached.'
                                      ;
                          leaf action {
                            description 'The action that generated when threshold value reached.'
                                        ;
                            type enumeration {
                              enum down {
                                value 0 ;
                                description 'Break down BGP connection after limit is exceeded.'
                                            ;
                              }
                              enum warning-only {
                                value 1 ;
                                description 'Only give warning message when limit is exceeded.'
                                            ;
                              }
                              enum drop-routes {
                                value 2 ;
                                description 'Drop routes that exceed the maximum-prefix.'
                                            ;
                              }
                            }
                            mandatory true ;
                          }
                        }
                        case restart {
                          description 'Restart BGP connection after limit is ex'
                                    + 'ceeded.'
                                      ;
                          leaf restart-time {
                            description 'Restart interval in minutes.'
                                        ;
                            type uint32 {
                              range 1..30000 ;
                            }
                            units min ;
                            mandatory true ;
                          }
                        }
                      }
                      ncd:revise-date 2019-08-08 ;
                    }
                    leaf routepolicy-in-name {
                      description 'Route policy name applied to the inbound rou'
                                + 'tes.'
                                  ;
                      type string {
                        length 1..200 ;
                      }
                      ncd:revise-date 2020-10-10 ;
                    }
                    leaf routepolicy-out-name {
                      description 'Route policy name applied to the outbound ro'
                                + 'utes.'
                                  ;
                      type string {
                        length 1..200 ;
                      }
                      ncd:revise-date 2020-10-10 ;
                    }
                  }
                  container default-originate-vrf {
                    description 'Originate default route to this neighbor for c'
                              + 'ertain VRF.'
                                ;
                    list default-originate-vrf {
                      description 'Originate default route to this neighbor for'
                                + ' certain VRF.'
                                  ;
                      key vrf-name ;
                      leaf vrf-name {
                        description 'VPN Routing/Forwarding instance.'
                                    ;
                        type string {
                          length 1..32 ;
                        }
                      }
                      leaf prefix-type {
                        description 'The type of originate default route.'
                                    ;
                        type enumeration {
                          enum both {
                            value 2 ;
                            description 'IPv4 and IPv6 prefix.'
                                        ;
                          }
                          enum ipv4 {
                            value 3 ;
                            description 'IPv4 prefix.'
                                        ;
                          }
                          enum ipv6 {
                            value 4 ;
                            description 'IPv6 prefix'
                                        ;
                          }
                        }
                        mandatory true ;
                      }
                      choice prefix-list {
                        description 'Prefix list name.'
                                    ;
                        case peer-list {
                          description 'Prefix list name of peer list.'
                                      ;
                          leaf peer-list-name {
                            description 'Prefix list name of peer list.'
                                        ;
                            type string {
                              length 1..169 ;
                            }
                          }
                          ncd:revise-date 2019-01-10 ;
                        }
                        case vrf-peer-list {
                          description 'Prefix list name of VRF routes list.'
                                      ;
                          leaf vrf-peer-list-name {
                            description 'Prefix list name of VRF routes list.'
                                        ;
                            type string {
                              length 1..169 ;
                            }
                          }
                          ncd:revise-date 2019-09-04 ;
                        }
                        ncd:revise-date 2019-01-10 ;
                      }
                    }
                    ncd:revise-date 2018-05-14 ;
                  }
                  container virtual {
                    description 'Set spoke PE.'
                                ;
                    presence virtual ;
                    leaf virtual-spoke {
                      description 'Enable spoke PE.'
                                  ;
                      type empty ;
                      mandatory true ;
                    }
                    leaf reflect-next-hop-self {
                      description 'Set next-hop self when reflection.'
                                  ;
                      type empty ;
                    }
                    leaf check-upstream-pe {
                      description 'Check upstream PE when advertising default r'
                                + 'oute.'
                                  ;
                      type empty ;
                    }
                    leaf by-vrf {
                      description 'Send specific route by default-originate con'
                                + 'fig.'
                                  ;
                      type empty ;
                      ncd:revise-date 2019-12-31 ;
                    }
                    ncd:revise-date 2018-05-14 ;
                  }
                  container route-filter-group {
                    description 'Specify a neighbor to join a route-filter-grou'
                              + 'p.'
                                ;
                    presence route-filter-group ;
                    leaf filter-group {
                      description 'Route filter group name (1-31 characters).'
                                  ;
                      type string {
                        length 1..31 ;
                      }
                      mandatory true ;
                    }
                    leaf next-hop-self {
                      description 'Disable the next hop calculation for this ne'
                                + 'ighbor.'
                                  ;
                      type empty ;
                    }
                    ncd:revise-date 2018-08-04 ;
                  }
                  leaf announce-sid {
                    description 'Enable Prefix-SID attribute for this neighbor.'
                                ;
                    type enumeration {
                      enum enable {
                        value 1 ;
                        description 'Enable Prefix-SID attribute for this neigh'
                                  + 'bor.'
                                    ;
                      }
                    }
                    ncd:revise-date 2018-05-14 ;
                  }
                  leaf send-community {
                    description 'Send community to this neighbor.'
                                ;
                    type empty ;
                    ncd:revise-date 2018-05-14 ;
                  }
                  leaf send-large-community {
                    description 'Send Large-community to this neighbor.'
                                ;
                    type empty ;
                    ncd:revise-date 2020-04-16 ;
                  }
                  leaf send-ope {
                    description 'Send OPE to this neighbor.'
                                ;
                    type empty ;
                    ncd:revise-date 2019-06-22 ;
                  }
                  leaf weight {
                    description 'Set weight for routes from this neighbor.'
                                ;
                    type uint32 {
                      range 1..65535 ;
                    }
                    ncd:revise-date 2018-05-14 ;
                  }
                  leaf send-local-route-without-esi-reference {
                    description 'Send local EVPN route without ESI reference.'
                                ;
                    type empty ;
                    ncd:revise-date 2018-07-21 ;
                  }
                  leaf soft-reconfig {
                    description 'Neighbor soft reconfiguration.'
                                ;
                    type enumeration {
                      enum soft-reconfiguration {
                        value 1 ;
                        description Soft-reconfiguration. ;
                      }
                      enum enforce-soft-reconfiguration {
                        value 2 ;
                        description 'Enforce soft-reconfiguration instead of se'
                                  + 'nding route-refresh.'
                                    ;
                      }
                    }
                    ncd:revise-date 2019-08-08 ;
                  }
                  leaf vpn-orf {
                    description 'Peer route-target ORF capability'
                                ;
                    type enumeration {
                      enum disable {
                        value 0 ;
                        description 'Disable peer route-target ORF capability'
                                    ;
                      }
                      enum enable {
                        value 1 ;
                        description 'Enable peer route-target ORF capability'
                                    ;
                      }
                      enum inherit {
                        value 2 ;
                        description 'If the neighbor joined a group, the status'
                                  + ' inherited from group.'
                                    ;
                      }
                    }
                    ncd:revise-date 2020-02-08 ;
                  }
                  leaf border-gateway {
                    description 'Set this neighbor as border-gateway peer'
                                ;
                    type enumeration {
                      enum disable {
                        value 0 ;
                        description 'disable peer border-gateway'
                                    ;
                      }
                      enum enable {
                        value 1 ;
                        description 'enable peer border-gateway'
                                    ;
                      }
                      enum inherit {
                        value 2 ;
                        description 'If the neighbor joined a group, the status'
                                  + ' of border-gateway inherited from group.'
                                    ;
                      }
                    }
                    ncd:revise-date 2019-09-10 ;
                  }
                  leaf adv-tunnel-encap {
                    description 'Advertise tunnel encapsulation type'
                                ;
                    type enumeration {
                      enum vxlan {
                        value 1 ;
                      }
                      enum mpls {
                        value 2 ;
                      }
                      enum srv6 {
                        value 4 ;
                      }
                    }
                    ncd:revise-date 2019-11-06 ;
                  }
                  container route-server-client {
                    description 'Set route server client only valid for ebgp pe'
                              + 'er.'
                                ;
                    presence route-server-client ;
                    leaf route-svr-client {
                      description 'Set route server client only valid for ebgp '
                                + 'peer.'
                                  ;
                      type empty ;
                      mandatory true ;
                    }
                    ncd:revise-date 2020-04-07 ;
                  }
                  leaf remove-private-as {
                    description 'EBGP use to remove private AS number.'
                                ;
                    type enumeration {
                      enum disable {
                        value 0 ;
                      }
                      enum enable {
                        value 1 ;
                      }
                    }
                    ncd:revise-date 2020-09-24 ;
                  }
                }
              }
              container neighbor-ipv6 {
                description 'Specify a IPv6 neighbor router.'
                            ;
                list neighbor {
                  description 'Specify a neighbor.'
                              ;
                  key ipv6-addr ;
                  leaf ipv6-addr {
                    description 'Neighbor IPv6 address.'
                                ;
                    type ncd:ipv6-address ;
                  }
                  leaf joined-group {
                    description 'Only for read operation. The joined group name.'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf monitor {
                    description 'Config BMP monitor for the address family of t'
                              + 'his neighbor.'
                                ;
                    type enumeration {
                      enum disable {
                        value 2 ;
                      }
                      enum enable {
                        value 1 ;
                      }
                      enum inherit-global-config {
                        value 0 ;
                      }
                    }
                    ncd:revise-date 2019-07-29 ;
                  }
                  leaf allowas-in {
                    description 'Accept as-path with my AS present in it.'
                                ;
                    type uint32 {
                      range 1..10 ;
                    }
                    ncd:revise-date 2020-03-02 ;
                  }
                  leaf route-reflector-client {
                    description 'Set this neighbor as a client peer.'
                                ;
                    type empty ;
                  }
                  leaf send-med {
                    description 'Send metric attribute to this neighbor.'
                                ;
                    type empty ;
                  }
                  leaf split-update-group {
                    description 'Split neighbor from update group.'
                                ;
                    type empty ;
                  }
                  choice nh-unchanged {
                    case next-hop-unchanged {
                      description 'NEXT_HOP of the IBGP path propagated unchang'
                                + 'ed to this neighbor.'
                                  ;
                      leaf next-hop-unchanged {
                        description 'Propagate next hop unchanged for IBGP path'
                                  + 's to this neighbor.'
                                    ;
                        type empty ;
                      }
                    }
                    case next-hop-unchanged-all {
                      description 'NEXT_HOP of either EBGP or IBGP path propaga'
                                + 'ted unchanged to this neighbor.'
                                  ;
                      leaf next-hop-unchanged-all {
                        description 'NEXT_HOP of either EBGP or IBGP path propa'
                                  + 'gated unchanged to this neighbor.'
                                    ;
                        type empty ;
                      }
                      ncd:revise-date 2020-04-07 ;
                    }
                  }
                  leaf next-hop-self {
                    description 'Disable the next hop calculation for this neig'
                              + 'hbor.'
                                ;
                    type enumeration {
                      enum enable {
                        value 1 ;
                        description 'Apply next-hop-self for EBGP route.'
                                    ;
                      }
                      enum all {
                        value 2 ;
                        description 'Apply next-hop-self for both EBGP and IBGP'
                                  + ' route.'
                                    ;
                      }
                    }
                  }
                  leaf capability-orf-prefix-list {
                    description 'Advertise prefixlist ORF capability to this ne'
                              + 'ighbor.'
                                ;
                    type enumeration {
                      enum receive {
                        value 1 ;
                        description 'Capability to receive the ORF from this ne'
                                  + 'ighbor.'
                                    ;
                      }
                      enum send {
                        value 2 ;
                        description 'Capability to send the ORF to this neighbo'
                                  + 'r.'
                                    ;
                      }
                      enum both {
                        value 3 ;
                        description 'Capability to send and receive the ORF.'
                                    ;
                      }
                    }
                  }
                  leaf default-originate-all {
                    description 'Notify all VPN default route.'
                                ;
                    type enumeration {
                      enum both {
                        value 2 ;
                        description 'IPv4 and IPv6 prefix.'
                                    ;
                      }
                      enum ipv4 {
                        value 3 ;
                        description 'IPv4 prefix.'
                                    ;
                      }
                      enum ipv6 {
                        value 4 ;
                        description 'IPv6 prefix.'
                                    ;
                      }
                    }
                    ncd:revise-date 2018-05-14 ;
                  }
                  leaf default-originate-routemap {
                    description 'Map external entry attributes into routing tab'
                              + 'le.'
                                ;
                    type string {
                      length 1..200 ;
                    }
                    ncd:revise-date 2020-07-28 ;
                  }
                  leaf default-originate-routepolicy {
                    description 'Set external entry attributes into routing tab'
                              + 'le.'
                                ;
                    type string {
                      length 1..200 ;
                    }
                    ncd:revise-date 2020-10-10 ;
                  }
                  leaf aigp {
                    description 'Enable AIGP for this neighbor.'
                                ;
                    type empty ;
                  }
                  container neighbor-extend {
                    description 'Specify a neighbor.'
                                ;
                    leaf prefix-list-in-name {
                      description 'Apply prefix list to incoming routes.'
                                  ;
                      type string {
                        length 1..169 ;
                      }
                    }
                    leaf prefix-list-out-name {
                      description 'Apply  prefix list to outbound routes.'
                                  ;
                      type string {
                        length 1..169 ;
                      }
                    }
                    leaf routemap-in-name {
                      description 'Apply map to incoming routes.'
                                  ;
                      type string {
                        length 1..200 ;
                      }
                    }
                    leaf routemap-out-name {
                      description 'Apply map to outbound routes.'
                                  ;
                      type string {
                        length 1..200 ;
                      }
                    }
                    leaf add-paths-receive {
                      description 'Receive additional paths from this neighbor.'
                                  ;
                      type empty ;
                    }
                    container add-paths-send {
                      description 'Send additional paths to this neighbor.'
                                  ;
                      choice add-paths-send {
                        description 'Send additional paths to this neighbor.'
                                    ;
                        default send-one-path ;
                        case send-one-path {
                          description 'Send one additional path to this neighbo'
                                    + 'r.'
                                      ;
                          leaf send {
                            description 'Send additional paths to this neighbor.'
                                        ;
                            type empty ;
                          }
                        }
                        case send-multi-paths {
                          description 'Send additional multi-paths to this neig'
                                    + 'hbor.'
                                      ;
                          leaf paths-number {
                            description 'Number of paths for a prefix.'
                                        ;
                            type uint32 {
                              range 2..32 ;
                            }
                          }
                          leaf prefixlist {
                            description 'Prefixlist of filtering additional paths.'
                                        ;
                            type string {
                              length 1..169 ;
                            }
                            ncd:revise-date 2020-12-02 ;
                          }
                        }
                      }
                    }
                    container withdraw {
                      description 'Withdraw routes when state of track-group is'
                                + ' down.'
                                  ;
                      presence withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                      ncd:revise-date 2018-06-20 ;
                    }
                    container second-withdraw {
                      description 'Withdraw routes when state of the second tra'
                                + 'ck-group is down.'
                                  ;
                      presence second-withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                      ncd:revise-date 2018-07-12 ;
                    }
                    container maximum-prefix {
                      description 'The action that generated when threshold val'
                                + 'ue reached.'
                                  ;
                      presence 'The action that generated when threshold value '
                             + 'reached'
                               ;
                      leaf maximum-prefix-number {
                        description 'Maximum number of prefix limit.'
                                    ;
                        type uint32 {
                          range 1..4294967295 ;
                        }
                        mandatory true ;
                      }
                      leaf maximum-prefix-threshold {
                        description 'Threshold value(%) at which to generate a '
                                  + 'warning.'
                                    ;
                        type uint32 {
                          range 1..100 ;
                        }
                        mandatory true ;
                      }
                      choice maximum-prefix-action {
                        description 'The action that generated when threshold v'
                                  + 'alue reached.'
                                    ;
                        mandatory true ;
                        case peer-action {
                          description 'The action that generated when threshold'
                                    + ' value reached.'
                                      ;
                          leaf action {
                            description 'The action that generated when threshold value reached.'
                                        ;
                            type enumeration {
                              enum down {
                                value 0 ;
                                description 'Break down BGP connection after limit is exceeded.'
                                            ;
                              }
                              enum warning-only {
                                value 1 ;
                                description 'Only give warning message when limit is exceeded.'
                                            ;
                              }
                              enum drop-routes {
                                value 2 ;
                                description 'Drop routes that exceed the maximum-prefix.'
                                            ;
                              }
                            }
                            mandatory true ;
                          }
                        }
                        case restart {
                          description 'Restart BGP connection after limit is ex'
                                    + 'ceeded.'
                                      ;
                          leaf restart-time {
                            description 'Restart interval in minutes.'
                                        ;
                            type uint32 {
                              range 1..30000 ;
                            }
                            units min ;
                            mandatory true ;
                          }
                        }
                      }
                      ncd:revise-date 2019-08-08 ;
                    }
                    leaf routepolicy-in-name {
                      description 'Route policy name applied to the inbound rou'
                                + 'tes.'
                                  ;
                      type string {
                        length 1..200 ;
                      }
                      ncd:revise-date 2020-10-10 ;
                    }
                    leaf routepolicy-out-name {
                      description 'Route policy name applied to the outbound ro'
                                + 'utes.'
                                  ;
                      type string {
                        length 1..200 ;
                      }
                      ncd:revise-date 2020-10-10 ;
                    }
                  }
                  container default-originate-vrf {
                    description 'Originate default route to this neighbor for c'
                              + 'ertain VRF.'
                                ;
                    list default-originate-vrf {
                      description 'Originate default route to this neighbor for'
                                + ' certain VRF.'
                                  ;
                      key vrf-name ;
                      leaf vrf-name {
                        description 'VPN Routing/Forwarding instance.'
                                    ;
                        type string {
                          length 1..32 ;
                        }
                      }
                      leaf prefix-type {
                        description 'The type of originate default route.'
                                    ;
                        type enumeration {
                          enum both {
                            value 2 ;
                            description 'IPv4 and IPv6 prefix.'
                                        ;
                          }
                          enum ipv4 {
                            value 3 ;
                            description 'IPv4 prefix.'
                                        ;
                          }
                          enum ipv6 {
                            value 4 ;
                            description 'IPv6 prefix.'
                                        ;
                          }
                        }
                        mandatory true ;
                      }
                      choice prefix-list {
                        description 'Prefix list name.'
                                    ;
                        case peer-list {
                          description 'Prefix list name of peer list.'
                                      ;
                          leaf peer-list-name {
                            description 'Prefix list name of peer list.'
                                        ;
                            type string {
                              length 1..169 ;
                            }
                          }
                          ncd:revise-date 2019-01-10 ;
                        }
                        case vrf-peer-list {
                          description 'Prefix list name of VRF routes list.'
                                      ;
                          leaf vrf-peer-list-name {
                            description 'Prefix list name of VRF routes list.'
                                        ;
                            type string {
                              length 1..169 ;
                            }
                          }
                          ncd:revise-date 2019-09-04 ;
                        }
                        ncd:revise-date 2019-01-10 ;
                      }
                    }
                    ncd:revise-date 2018-05-14 ;
                  }
                  container virtual {
                    description 'Set spoke PE.'
                                ;
                    presence virtual ;
                    leaf virtual-spoke {
                      description 'Enable spoke PE.'
                                  ;
                      type empty ;
                      mandatory true ;
                    }
                    leaf reflect-next-hop-self {
                      description 'Set next-hop self when reflection.'
                                  ;
                      type empty ;
                    }
                    leaf check-upstream-pe {
                      description 'Check upstream PE when advertising default r'
                                + 'oute.'
                                  ;
                      type empty ;
                    }
                    leaf by-vrf {
                      description 'Send specific route by default-originate con'
                                + 'fig.'
                                  ;
                      type empty ;
                      ncd:revise-date 2019-12-31 ;
                    }
                    ncd:revise-date 2018-05-14 ;
                  }
                  container route-filter-group {
                    description 'Specify a neighbor to join a route-filter-grou'
                              + 'p.'
                                ;
                    presence route-filter-group ;
                    leaf filter-group {
                      description 'Route filter group name (1-31 characters).'
                                  ;
                      type string {
                        length 1..31 ;
                      }
                      mandatory true ;
                    }
                    leaf next-hop-self {
                      description 'Disable the next hop calculation for this ne'
                                + 'ighbor.'
                                  ;
                      type empty ;
                    }
                    ncd:revise-date 2018-08-04 ;
                  }
                  leaf announce-sid {
                    description 'Enable Prefix-SID attribute for this neighbor.'
                                ;
                    type enumeration {
                      enum enable {
                        value 1 ;
                        description 'Enable Prefix-SID attribute for this neigh'
                                  + 'bor.'
                                    ;
                      }
                    }
                    ncd:revise-date 2018-05-14 ;
                  }
                  leaf send-community {
                    description 'Send community to this neighbor.'
                                ;
                    type empty ;
                    ncd:revise-date 2018-05-14 ;
                  }
                  leaf send-large-community {
                    description 'Send Large-community to this neighbor.'
                                ;
                    type empty ;
                    ncd:revise-date 2020-04-16 ;
                  }
                  leaf send-ope {
                    description 'Send OPE to this neighbor.'
                                ;
                    type empty ;
                    ncd:revise-date 2019-06-22 ;
                  }
                  leaf weight {
                    description 'Set weight for routes from this neighbor.'
                                ;
                    type uint32 {
                      range 1..65535 ;
                    }
                    ncd:revise-date 2018-05-14 ;
                  }
                  leaf send-local-route-without-esi-reference {
                    description 'Send local EVPN route without ESI reference.'
                                ;
                    type empty ;
                    ncd:revise-date 2018-07-21 ;
                  }
                  leaf soft-reconfig {
                    description 'Neighbor soft reconfiguration.'
                                ;
                    type enumeration {
                      enum soft-reconfiguration {
                        value 1 ;
                        description Soft-reconfiguration. ;
                      }
                      enum enforce-soft-reconfiguration {
                        value 2 ;
                        description 'Enforce soft-reconfiguration instead of se'
                                  + 'nding route-refresh.'
                                    ;
                      }
                    }
                    ncd:revise-date 2019-08-08 ;
                  }
                  leaf vpn-orf {
                    description 'Peer route-target ORF capability'
                                ;
                    type enumeration {
                      enum disable {
                        value 0 ;
                        description 'Disable peer route-target ORF capability'
                                    ;
                      }
                      enum enable {
                        value 1 ;
                        description 'Enable peer route-target ORF capability'
                                    ;
                      }
                      enum inherit {
                        value 2 ;
                        description 'If the neighbor joined a group, the status'
                                  + ' inherited from group.'
                                    ;
                      }
                    }
                    ncd:revise-date 2020-02-08 ;
                  }
                  leaf border-gateway {
                    description 'Set this neighbor as border-gateway peer'
                                ;
                    type enumeration {
                      enum disable {
                        value 0 ;
                        description 'disable peer border-gateway'
                                    ;
                      }
                      enum enable {
                        value 1 ;
                        description 'enable peer border-gateway'
                                    ;
                      }
                      enum inherit {
                        value 2 ;
                        description 'If the neighbor joined a group, the status'
                                  + ' of border-gateway inherited from group.'
                                    ;
                      }
                    }
                    ncd:revise-date 2019-09-10 ;
                  }
                  leaf adv-tunnel-encap {
                    description 'Advertise tunnel encapsulation type'
                                ;
                    type enumeration {
                      enum vxlan {
                        value 1 ;
                      }
                      enum mpls {
                        value 2 ;
                      }
                      enum srv6 {
                        value 4 ;
                      }
                    }
                    ncd:revise-date 2019-11-06 ;
                  }
                  container route-server-client {
                    description 'Set route server client only valid for ebgp pe'
                              + 'er.'
                                ;
                    presence route-server-client ;
                    leaf route-svr-client {
                      description 'Set route server client only valid for ebgp '
                                + 'peer.'
                                  ;
                      type empty ;
                      mandatory true ;
                    }
                    ncd:revise-date 2020-04-07 ;
                  }
                  leaf remove-private-as {
                    description 'EBGP use to remove private AS number.'
                                ;
                    type enumeration {
                      enum disable {
                        value 0 ;
                      }
                      enum enable {
                        value 1 ;
                      }
                    }
                    ncd:revise-date 2020-09-24 ;
                  }
                }
                ncd:revise-date 2017-11-28 ;
              }
            }
            leaf mac-route-esi-index {
              description 'Set MAC route ESI index'
                          ;
              type enumeration {
                enum rt1-per-evi {
                  value 1 ;
                }
              }
              ncd:revise-date 2017-08-25 ;
            }
            leaf ip-route-esi-index {
              status obsolete {
                ncd:revise-date 2019-04-10 ;
              }
              description 'Set IP route ESI index'
                          ;
              type enumeration {
                enum rt1-per-es {
                  value 2 ;
                }
                enum rt1-per-evi {
                  value 1 ;
                }
              }
              default rt1-per-evi ;
              ncd:revise-date 2017-08-25 ;
            }
            container track-evpn {
              description 'Event tracking.'
                          ;
              presence "'enable track-evpn'"
                       ;
              container track-trigger-type {
                description 'Configure trigger of track object.'
                            ;
                list track-trigger {
                  description 'Configure trigger of track object.'
                              ;
                  key track-name ;
                  leaf track-name {
                    description 'Name of track object (1-31characters).'
                                ;
                    type string {
                      length 1..31 ;
                    }
                  }
                }
              }
              ncd:revise-date 2018-01-10 ;
            }
            leaf local-inclusive-multicast-auto-generate {
              description 'Enable or disable local inclusive-multicast route au'
                        + 'to-generate'
                          ;
              type enumeration {
                enum disable {
                  value 0 ;
                }
                enum enable {
                  value 1 ;
                }
              }
              default enable ;
              ncd:revise-date 2018-07-11 ;
            }
            container vtep-group-address {
              description 'Set underlay ip address.'
                          ;
              choice vtep-group-address {
                description 'Set underlay ip address.'
                            ;
                case address-v4 {
                  description 'Set underlay address IPv4 type.'
                              ;
                  leaf vtep-group-address-v4 {
                    description 'Set underlay IPv4 address.'
                                ;
                    type ncd:ipv4-address-none-zero ;
                  }
                }
                case address-v6 {
                  description 'Set underlay address IPv6 type.'
                              ;
                  leaf vtep-group-address-v6 {
                    status obsolete {
                      ncd:revise-date 2019-08-16 ;
                    }
                    description 'Set vtep group IPv6 address.'
                                ;
                    type ncd:ipv6-address ;
                  }
                  leaf vtep-group-address-v6-ex {
                    description 'Set underlay IPv6 address.'
                                ;
                    type ncd:ipv6-address-none-zero ;
                    ncd:revise-date 2019-08-16 ;
                  }
                }
              }
              ncd:revise-date 2018-10-11 ;
            }
            container rt3-originator-ip-address {
              description 'Set rt3 originator ip address.'
                          ;
              choice rt3-originator-ip-address {
                description 'Set rt3 originator ip address.'
                            ;
                case address-v4 {
                  description 'Set rt3 originator address to IPv4 type.'
                              ;
                  leaf rt3-originator-ip-address-v4 {
                    description 'Set rt3 originator IPv4 address.'
                                ;
                    type ncd:ipv4-address-none-zero ;
                  }
                }
                case address-v6 {
                  description 'Set rt3 originator address to IPv6 type.'
                              ;
                  leaf rt3-originator-ip-address-v6 {
                    description 'Set rt3 originator IPv6 address.'
                                ;
                    type ncd:ipv6-address-none-zero ;
                  }
                }
              }
              ncd:revise-date 2020-04-26 ;
            }
            container group-to-group {
              description 'Configure filter group to filter group route reflect'
                        + 'ion.'
                          ;
              presence group-to-group ;
              leaf reflection {
                description 'Reflection of routes is allowed.'
                            ;
                type empty ;
                mandatory true ;
              }
              leaf next-hop-self {
                description 'Disable the next hop calculation.'
                            ;
                type empty ;
              }
              leaf evpn-route-type {
                description 'EVPN route type.'
                            ;
                type enumeration {
                  enum evpn-l2-l3-route {
                    value 0 ;
                    description 'EVPN route type 1-5.'
                                ;
                  }
                  enum evpn-l2-route {
                    value 1 ;
                    description 'EVPN route type 1-4.'
                                ;
                  }
                  enum evpn-l3-route {
                    value 2 ;
                    description 'EVPN route type 5.'
                                ;
                  }
                }
              }
              ncd:revise-date 2018-08-04 ;
            }
            leaf bgp-label {
              description 'Mpls label mode.'
                          ;
              type enumeration {
                enum per-vrf-by-rt {
                  value 0 ;
                  description 'Allocate label according to per-vrf and find VRF'
                            + ' according to route-target.'
                              ;
                }
                enum per-vrf-by-rd {
                  value 3 ;
                  description 'Allocate label according to per-vrf and find VRF'
                            + ' according to route-distinguisher.'
                              ;
                }
                enum per-vrf-by-vni {
                  value 4 ;
                  description 'Allocate label according to per-vrf and find VRF'
                            + ' according to VNI label.'
                              ;
                }
                enum per-prefix {
                  value 2 ;
                  description 'Allocate label according to prefix.'
                              ;
                }
              }
              default per-vrf-by-rt ;
              ncd:revise-date 2018-10-12 ;
            }
            container bgp-routes-label {
              description 'Configure EVPN routes label mode.'
                          ;
              presence bgp-routes-label ;
              leaf ip-prefix-mode {
                description 'Configure EVPN IP Prefix label mode.'
                            ;
                type enumeration {
                  enum per-vrf-by-rt {
                    value 0 ;
                    description 'Allocate label according to per-vrf and find V'
                              + 'RF according to route-target.'
                                ;
                  }
                  enum per-vrf-by-rd {
                    value 3 ;
                    description 'Allocate label according to per-vrf and find V'
                              + 'RF according to route-distinguisher.'
                                ;
                  }
                  enum per-vrf-by-vni {
                    value 4 ;
                    description 'Allocate label according to per-vrf and find V'
                              + 'RF according to VNI label.'
                                ;
                  }
                  enum per-prefix {
                    value 2 ;
                    description 'Allocate label according to prefix.'
                                ;
                  }
                }
              }
              ncd:revise-date 2018-11-16 ;
            }
            leaf additional-paths-send-igp-path {
              description 'Send EVPN neighbor NLRI with igp-path of additional-'
                        + 'paths.'
                          ;
              type empty ;
              ncd:revise-date 2018-10-31 ;
            }
            container route-scan-time {
              description 'Adjust BGP route scan timers.'
                          ;
              presence 'The ability of BGP route scan.'
                       ;
              leaf interval-wait {
                description 'The interval of scan waiting. Default value is 500.'
                            ;
                type uint32 {
                  range 1..65535 ;
                }
                units ms ;
                mandatory true ;
              }
              leaf initial {
                description 'The initialization time of scan. Default value is '
                          + '50.'
                            ;
                type uint32 {
                  range 1..65535 ;
                }
                units ms ;
                mandatory true ;
              }
              leaf max-wait {
                description 'The max waiting time of scan. Default value is 500'
                          + '0.'
                            ;
                type uint32 {
                  range 1..65535 ;
                }
                units ms ;
                mandatory true ;
              }
              ncd:revise-date 2019-01-01 ;
            }
            leaf ip-route-esi-index-ex {
              description 'Set IP route ESI index'
                          ;
              type enumeration {
                enum rt1-per-evi {
                  value 1 ;
                }
              }
              ncd:revise-date 2019-04-10 ;
            }
            container damp-evpn {
              description 'Enable route-flap dampening.'
                          ;
              presence damp-evpn ;
              choice damp {
                description 'Enable route-flap dampening.'
                            ;
                case route-map {
                  description 'Route-map to specify criteria for dampening.'
                              ;
                  leaf route-map-name {
                    description 'Route-map to specify criteria for dampening.'
                                ;
                    type string {
                      length 1..200 ;
                    }
                  }
                  leaf route-policy-name {
                    description 'Route-policy to specify criteria for dampening.'
                                ;
                    type string {
                      length 1..200 ;
                    }
                    ncd:revise-date 2020-10-10 ;
                  }
                }
                case parameter {
                  description 'Damp parameter.'
                              ;
                  leaf half-time {
                    description 'Half-life time for the penalty.'
                                ;
                    type uint32 {
                      range 1..45 ;
                    }
                    units min ;
                    mandatory true ;
                  }
                  leaf reuse {
                    description 'Value to start reusing a route.'
                                ;
                    type uint32 {
                      range 1..20000 ;
                    }
                    mandatory true ;
                  }
                  leaf suppress {
                    description 'Value to start suppressing a route.'
                                ;
                    type uint32 {
                      range 1..20000 ;
                    }
                    mandatory true ;
                  }
                  leaf max-suppress-time {
                    description 'Maximum duration to suppress a route.'
                                ;
                    type uint32 {
                      range 1..255 ;
                    }
                    mandatory true ;
                  }
                }
              }
              ncd:revise-date 2019-06-25 ;
            }
            leaf import-vpnv4-uni {
              description 'Import VPNv4 route to L2VPN EVPN table.'
                          ;
              type enumeration {
                enum disable {
                  value 0 ;
                }
                enum enable {
                  value 1 ;
                }
              }
              default disable ;
              ncd:revise-date 2019-07-07 ;
            }
            leaf import-vpnv6-uni {
              description 'Import VPNv6 route to L2VPN EVPN table.'
                          ;
              type enumeration {
                enum disable {
                  value 0 ;
                }
                enum enable {
                  value 1 ;
                }
              }
              default disable ;
              ncd:revise-date 2019-07-07 ;
            }
            leaf bgp-bestpath-origin {
              description 'bgp bestpath origin-from L3VPN neighbor or EVPN neig'
                        + 'hbor.'
                          ;
              type enumeration {
                enum l3vpn {
                  value 1 ;
                  description 'bgp bestpath origin-from L3VPN neighbor'
                              ;
                }
                enum evpn {
                  value 2 ;
                  description 'bgp bestpath origin-from EVPN neighbor'
                              ;
                }
              }
              ncd:revise-date 2019-08-08 ;
            }
            leaf vpn-orf {
              description 'Generate local route-target routes'
                          ;
              type enumeration {
                enum disable {
                  value 0 ;
                  description 'Disable generate local route-target routes'
                              ;
                }
                enum enable {
                  value 1 ;
                  description 'Enable generate local route-target routes'
                              ;
                }
              }
              ncd:revise-date 2020-02-08 ;
            }
            leaf esi-index-ignore-rd {
              description 'Ethernet segment identifier index ignore rd.'
                          ;
              type enumeration {
                enum disable {
                  value 0 ;
                }
                enum enable {
                  value 1 ;
                }
              }
              default disable ;
              ncd:revise-date 2020-04-28 ;
            }
            container protector-ip-address {
              description 'Set protector ip address.'
                          ;
              choice protector-ip-address {
                description 'Set protector ip address.'
                            ;
                case address-v4 {
                  description 'Set protector address to IPv4 type.'
                              ;
                  leaf protector-ip-address-v4 {
                    description 'Set protector IPv4 address.'
                                ;
                    type ncd:ipv4-address-none-zero ;
                  }
                }
                case address-v6 {
                  description 'Set protector address to IPv6 type.'
                              ;
                  leaf protector-ip-address-v6 {
                    description 'Set protector IPv6 address.'
                                ;
                    type ncd:ipv6-address-none-zero ;
                  }
                }
              }
              ncd:revise-date 2020-05-29 ;
            }
            leaf slow-peer-detection {
              description 'Set slow peer detection.'
                          ;
              type enumeration {
                enum disable {
                  value 0 ;
                  description 'Disable slow peer detection'
                              ;
                }
                enum enable {
                  value 1 ;
                  description 'Enable slow peer detection'
                              ;
                }
              }
              default disable ;
              ncd:revise-date 2020-09-08 ;
            }
            leaf slow-peer-detection-threshold {
              description 'Set threshold time for slow peer.Default value is 30'
                        + '0.'
                          ;
              type uint32 {
                range 120..3600 {
                  description 'Threshold time range.'
                              ;
                }
              }
              units s ;
              default 300 ;
              ncd:revise-date 2020-09-08 ;
            }
            leaf slow-peer-detection-recover {
              description 'Set recover time for slow peer.Default value is 300.'
                          ;
              type uint32 {
                range 120..3600 {
                  description 'Recover time range.'
                              ;
                }
              }
              units s ;
              default 300 ;
              ncd:revise-date 2020-09-08 ;
            }
            leaf nexthop-recursive-lookup-srv6-sid {
              description 'Enable or disable bgp nexthop recursive-lookup srv6-'
                        + 'sid'
                          ;
              type enumeration {
                enum disable {
                  value 0 ;
                }
                enum enable {
                  value 1 ;
                }
              }
              default disable ;
              ncd:revise-date 2020-10-28 ;
            }
            leaf bestpath-external {
              description 'Routes from external peer or RR client are preferred'
                        + ' in bestpath selection.'
                          ;
              type empty ;
              ncd:revise-date 2020-11-23 ;
            }
            leaf bestpath-igp-metric-compare {
              description 'Compare IGP metric in maximum-paths.'
                          ;
              type empty ;
              ncd:revise-date 2020-11-23 ;
            }
            leaf bestpath-igp-metric-ignore {
              description 'Ignore IGP metric in bestpath selection.'
                          ;
              type empty ;
              ncd:revise-date 2020-11-23 ;
            }
            container additional-paths {
              description 'Additional paths in the BGP table'
                          ;
              leaf selection-route-map {
                description 'Selection criteria to pick the additional paths.'
                            ;
                type string {
                  length 1..200 ;
                }
              }
              ncd:revise-date 2020-12-02 ;
            }
            ncd:revise-date 2016-01-19 ;
          }
          container address-family-link-state {
            description 'Configuration in address family LINK-STATE mode.'
                        ;
            presence 'LINK-STATE address family.'
                     ;
            container neighbor-link-state {
              description 'Specify a neighbor.'
                          ;
              presence neighbor-link-state ;
              container neighbor-group {
                description 'Specify a peergroup neighbor router.'
                            ;
                list neighbor-peergroup {
                  description 'Specify a neighbor.'
                              ;
                  key neighbor-group ;
                  leaf neighbor-group {
                    description 'Peer group name (1-31 characters).'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf route-reflector-client {
                    description 'Set this neighbor as a client peer.'
                                ;
                    type empty ;
                  }
                  leaf link-state {
                    status obsolete {
                      ncd:revise-date 2019-07-11 ;
                    }
                    description 'Configure type of link-state route'
                                ;
                    type link-state ;
                    default null ;
                    ncd:revise-date 2017-07-26 ;
                  }
                  leaf backup {
                    status obsolete {
                      ncd:revise-date 2019-07-11 ;
                    }
                    description 'Configure backup route'
                                ;
                    type ncd:ipv4-address-none-zero ;
                    ncd:revise-date 2017-07-26 ;
                  }
                }
              }
              container neighbor-ipv4 {
                description 'Specify a IPv4 neighbor.'
                            ;
                list neighbor {
                  description 'Specify a neighbor.'
                              ;
                  key ipv4-address ;
                  leaf ipv4-address {
                    description 'Neighbor IPv4 address.'
                                ;
                    type ncd:ipv4-address ;
                  }
                  leaf joined-group {
                    description 'Only for read operation. The joined group name.'
                                ;
                    type string {
                      length 1..31 ;
                    }
                    ncd:revise-date 2016-05-16 ;
                  }
                  leaf activate {
                    description 'Enable the address family for this neighbor.'
                                ;
                    type enumeration {
                      enum disable {
                        value 0 ;
                      }
                      enum enable {
                        value 1 ;
                      }
                    }
                  }
                  leaf route-reflector-client {
                    description 'Set this neighbor as a client peer.'
                                ;
                    type empty ;
                  }
                  leaf link-state {
                    status obsolete {
                      ncd:revise-date 2019-07-11 ;
                    }
                    description 'Configure type of link-state route'
                                ;
                    type link-state ;
                    default null ;
                    ncd:revise-date 2017-07-26 ;
                  }
                  leaf backup {
                    status obsolete {
                      ncd:revise-date 2019-07-11 ;
                    }
                    description 'Configure backup route'
                                ;
                    type ncd:ipv4-address-none-zero ;
                    ncd:revise-date 2017-07-26 ;
                  }
                }
              }
              container neighbor-ipv6 {
                description 'Specify a IPv6 neighbor.'
                            ;
                list neighbor {
                  description 'Specify a neighbor.'
                              ;
                  key ipv6-address ;
                  leaf ipv6-address {
                    description 'Neighbor IPv6 address.'
                                ;
                    type ncd:ipv6-address ;
                  }
                  leaf joined-group {
                    description 'Only for read operation. The joined group name.'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf route-reflector-client {
                    description 'Set this neighbor as a client peer.'
                                ;
                    type empty ;
                  }
                  leaf link-state {
                    status obsolete {
                      ncd:revise-date 2019-07-11 ;
                    }
                    description 'Configure type of link-state route'
                                ;
                    type link-state ;
                    default null ;
                  }
                  leaf backup {
                    status obsolete {
                      ncd:revise-date 2019-07-11 ;
                    }
                    description 'Configure backup route'
                                ;
                    type ncd:ipv4-address-none-zero ;
                  }
                }
                ncd:revise-date 2018-12-12 ;
              }
            }
            leaf default-metric {
              description 'Set metric of BGP routes without MED.'
                          ;
              type uint32 {
                range 0..4294967295 ;
              }
              default 0 ;
              ncd:revise-date 2019-04-10 ;
            }
            ncd:revise-date 2016-03-07 ;
          }
          container address-family-link-state-vpn {
            description 'Configuration in address family LINK-STATE-VPN mode.'
                        ;
            presence 'LINK-STATE-VPN address family.'
                     ;
            container neighbor-link-state-vpn {
              description 'Specify a neighbor.'
                          ;
              presence neighbor-link-state-vpn ;
              container neighbor-group {
                description 'Specify a peergroup neighbor router.'
                            ;
                list neighbor-peergroup {
                  description 'Specify a neighbor.'
                              ;
                  key neighbor-group ;
                  leaf neighbor-group {
                    description 'Peer group name (1-31 characters).'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf route-reflector-client {
                    description 'Set this neighbor as a client peer.'
                                ;
                    type empty ;
                  }
                }
              }
              container neighbor-ipv4 {
                description 'Specify a IPv4 neighbor.'
                            ;
                list neighbor {
                  description 'Specify a neighbor.'
                              ;
                  key ipv4-address ;
                  leaf ipv4-address {
                    description 'Neighbor IPv4 address.'
                                ;
                    type ncd:ipv4-address ;
                  }
                  leaf joined-group {
                    description 'Only for read operation. The joined group name.'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf route-reflector-client {
                    description 'Set this neighbor as a client peer.'
                                ;
                    type empty ;
                  }
                }
              }
              container neighbor-ipv6 {
                description 'Specify a IPv6 neighbor.'
                            ;
                list neighbor {
                  description 'Specify a neighbor.'
                              ;
                  key ipv6-address ;
                  leaf ipv6-address {
                    description 'Neighbor IPv6 address.'
                                ;
                    type ncd:ipv6-address ;
                  }
                  leaf joined-group {
                    description 'Only for read operation. The joined group name.'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf route-reflector-client {
                    description 'Set this neighbor as a client peer.'
                                ;
                    type empty ;
                  }
                }
              }
            }
            leaf default-metric {
              description 'Set metric of BGP routes without MED.'
                          ;
              type uint32 {
                range 0..4294967295 ;
              }
              default 0 ;
              ncd:revise-date 2020-02-13 ;
            }
            ncd:revise-date 2019-10-11 ;
          }
          container address-family-ipv6-uni {
            description 'Configuration in address family IPv6 mode.'
                        ;
            presence 'IPv6 address family.'
                     ;
            leaf defaults-set-flag {
              status obsolete {
                ncd:revise-date 2020-07-28 ;
              }
              description 'Flag of defaults.Only for get operation.When this va'
                        + 'lue expressed as a binary,The lowest bit indicate di'
                        + 'stance-ibgp,the next bit distance-ebgp,then maxpaths'
                        + '-ebgp,then default-metric,then wait-for-end-of-rib,t'
                        + 'hen constrain-rt-filter.'
                          ;
              type uint32 {
                range 0..4294967295 ;
              }
              default 0 ;
            }
            leaf bestpath-external {
              description 'Routes from external peer or RR client are preferred'
                        + ' in bestpath selection.'
                          ;
              type empty ;
            }
            leaf bestpath-igp-metric-ignore {
              description 'Ignore IGP metric in bestpath selection.'
                          ;
              type empty ;
            }
            leaf frr-capability {
              description 'Enable FRR capability.'
                          ;
              type empty ;
            }
            leaf frr-wtr {
              description 'Set the WTR time.'
                          ;
              type int32 {
                range 1..12 ;
              }
              units min ;
            }
            leaf frr-enhanced {
              description 'If there is no BGP route as a backup route, then cho'
                        + 'ose the default route for FRR.'
                          ;
              type empty ;
            }
            leaf default-information-originate {
              description 'Notify default route.'
                          ;
              type empty ;
            }
            leaf default-metric {
              description 'Set the metric of BGP routes without MED.'
                          ;
              type uint32 {
                range 0..4294967295 ;
              }
              default 0 ;
            }
            leaf distance-bgp-internal {
              description 'Distance for routes internal to the AS.'
                          ;
              type uint32 {
                range 1..255 ;
              }
              default 200 ;
            }
            leaf distance-bgp-external {
              description 'Distance for routes external to the AS.'
                          ;
              type uint32 {
                range 1..255 ;
              }
              default 20 ;
            }
            leaf distance-bgp-local {
              description 'Distance for BGP local routes.'
                          ;
              type uint32 {
                range 1..255 ;
              }
              default 254 ;
              ncd:revise-date 2016-05-10 ;
            }
            leaf distance-route-map {
              description 'Define distance by route-map.This node has higher pr'
                        + 'iority than distance-bgp-internal,distance-bgp-exter'
                        + 'nal and distance-bgp-local.'
                          ;
              type string {
                length 1..200 ;
              }
              ncd:revise-date 2020-09-08 ;
            }
            leaf distance-route-policy {
              description 'Define distance by route-policy.This node has higher'
                        + ' priority than distance-bgp-internal,distance-bgp-ex'
                        + 'ternal and distance-bgp-local.'
                          ;
              type string {
                length 1..200 ;
              }
              ncd:revise-date 2020-10-10 ;
            }
            leaf maximum-paths-ibgp {
              description 'Set IBGP-multipath.'
                          ;
              type uint32 {
                range 1..32 ;
              }
              default 1 ;
            }
            leaf maximum-paths-ebgp {
              description 'Set EBGP-multipath.'
                          ;
              type uint32 {
                range 1..32 ;
              }
              default 1 ;
            }
            leaf maximum-paths-eibgp {
              description 'Set EIBGP-multipath. Mutex with maximum-paths-ibgp a'
                        + 'nd maximum-paths-ebgp.'
                          ;
              type uint32 {
                range 1..32 ;
              }
              default 1 ;
            }
            leaf rpki-validation {
              description 'Set the BGP origin-AS validation parameters.'
                          ;
              type disable-or-enable-type ;
              default enable ;
            }
            leaf send-label-explicit-null {
              status obsolete {
                ncd:revise-date 2018-05-14 ;
              }
              description 'Send explicit-null label.'
                          ;
              type empty ;
            }
            leaf send-label {
              description 'Send null label.'
                          ;
              type enumeration {
                enum explicit-null {
                  value 1 ;
                  description 'Explicit-null label.'
                              ;
                }
                enum implicit-null {
                  value 2 ;
                  description 'Implicit-null label.'
                              ;
                }
              }
              ncd:revise-date 2018-05-14 ;
            }
            leaf synchronization {
              description 'Perform IGP synchronization.'
                          ;
              type empty ;
            }
            leaf table-map {
              description 'Map external entry attributes into routing table.'
                          ;
              type string {
                length 1..200 ;
              }
            }
            leaf table-policy {
              description 'Set external entry attributes into routing table.'
                          ;
              type string {
                length 1..200 ;
              }
            }
            leaf bestpath-igp-metric-compare {
              description 'Compare IGP metric in maximum-paths.'
                          ;
              type empty ;
              ncd:revise-date 2017-07-05 ;
            }
            leaf nexthop-recursive-default-route {
              description 'Nexthop recursive lookup default-route.'
                          ;
              type enumeration {
                enum enable {
                  value 1 ;
                }
                enum disable {
                  value 0 ;
                }
              }
              default enable ;
              ncd:revise-date 2020-07-28 ;
            }
            leaf nexthop-recursive-null1 {
              description 'Nexthop recursive lookup null1.'
                          ;
              type enumeration {
                enum enable {
                  value 1 ;
                }
                enum disable {
                  value 0 ;
                }
              }
              default enable ;
              ncd:revise-date 2020-12-09 ;
            }
            container aggregate-v6-uni {
              description 'Configure BGP aggregate entries.'
                          ;
              presence aggregate-v6-uni ;
              list aggregate {
                description 'Configure BGP aggregate entries.'
                            ;
                key 'ipv6-address ipv6-mask-len'
                    ;
                leaf ipv6-address {
                  description 'Aggregate address.'
                              ;
                  type ncd:ipv6-address ;
                }
                leaf ipv6-mask-len {
                  description 'Aggregate mask length.'
                              ;
                  type uint8 {
                    range 0..128 ;
                  }
                }
                leaf as-set {
                  description 'Generate AS set path information.'
                              ;
                  type empty ;
                }
                leaf strict {
                  description 'Strict condition.'
                              ;
                  type empty ;
                }
                leaf summary-only {
                  description 'Filter more specific routes from updates.'
                              ;
                  type empty ;
                }
                leaf attribute-map {
                  status obsolete {
                    ncd:revise-date 2018-07-21 ;
                  }
                  description 'Attribute map name.'
                              ;
                  type string {
                    length 1..200 ;
                  }
                }
                leaf suppress-map {
                  status obsolete {
                    ncd:revise-date 2018-07-21 ;
                  }
                  description 'Suppress map name.'
                              ;
                  type string {
                    length 1..200 ;
                  }
                }
                choice agg-policy {
                  description 'Apply policy to aggregate route.'
                              ;
                  case agg-policy-choice-clear {
                    description 'Remove value of any entities which belong to a'
                              + 'ny case within this choice.'
                                ;
                    container agg-policy-all-clear {
                      description 'Remove this entitiy means to remove value of'
                                + ' any entities which belong to any case withi'
                                + 'n this choice.'
                                  ;
                      presence clear-agg-policy ;
                    }
                    ncd:revise-date 2020-11-11 ;
                  }
                  case route-map {
                    description 'Apply route map to aggregate route.'
                                ;
                    leaf attr-map {
                      description 'Attribute map name.'
                                  ;
                      type string {
                        length 1..200 ;
                      }
                    }
                    leaf supp-map {
                      description 'Suppress map name.'
                                  ;
                      type string {
                        length 1..200 ;
                      }
                    }
                    leaf orig-map {
                      description 'Origin map name.'
                                  ;
                      type string {
                        length 1..200 ;
                      }
                      ncd:revise-date 2019-08-19 ;
                    }
                  }
                  case route-policy {
                    description 'Apply route-policy to aggregate route.'
                                ;
                    leaf policy {
                      description 'Route-policy name.'
                                  ;
                      type string {
                        length 1..200 ;
                      }
                    }
                  }
                  ncd:revise-date 2018-07-21 ;
                }
              }
            }
            container damp-v6-uni {
              description 'Enable route-flap dampening.'
                          ;
              presence damp-v6-uni ;
              choice damp {
                description 'Enable route-flap dampening.'
                            ;
                case route-map {
                  description 'Route-map to specify criteria for dampening.'
                              ;
                  leaf route-map-name {
                    description 'Route-map to specify criteria for dampening.'
                                ;
                    type string {
                      length 1..200 ;
                    }
                  }
                  leaf route-policy-name {
                    description 'Route-policy to specify criteria for dampening.'
                                ;
                    type string {
                      length 1..200 ;
                    }
                    ncd:revise-date 2020-10-10 ;
                  }
                }
                case parameter {
                  description 'Damp parameter.'
                              ;
                  leaf half-time {
                    description 'Half-life time for the penalty.'
                                ;
                    type uint32 {
                      range 1..45 ;
                    }
                    units min ;
                    mandatory true ;
                  }
                  leaf reuse {
                    description 'Value to start reusing a route.'
                                ;
                    type uint32 {
                      range 1..20000 ;
                    }
                    units min ;
                    mandatory true ;
                  }
                  leaf suppress {
                    description 'Value to start suppressing a route.'
                                ;
                    type uint32 {
                      range 1..20000 ;
                    }
                    units min ;
                    mandatory true ;
                  }
                  leaf max-suppress-time {
                    description 'Maximum duration to suppress a route.'
                                ;
                    type uint32 {
                      range 1..255 ;
                    }
                    units min ;
                    mandatory true ;
                  }
                }
              }
            }
            leaf dampening-ibgp {
              description 'IBGP route-flap dampening.'
                          ;
              type enumeration {
                enum disable {
                  value 0 ;
                }
                enum enable {
                  value 1 ;
                }
              }
              default enable ;
              ncd:revise-date 2020-08-18 ;
            }
            container neighbor-ipv6-uni {
              description 'Specify a neighbor.'
                          ;
              presence neighbor-ipv6-uni ;
              container neighbor-group {
                description 'Specify a peergroup neighbor.'
                            ;
                list neighbor-peergroup {
                  description 'Specify a neighbor peergroup.'
                              ;
                  key neighbor-group ;
                  leaf neighbor-group {
                    description 'Peer group name (1-31 characters).'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf monitor {
                    description 'Config BMP monitor for the address family of t'
                              + 'his neighbor.'
                                ;
                    type enumeration {
                      enum disable {
                        value 2 ;
                      }
                      enum enable {
                        value 1 ;
                      }
                      enum inherit-global-config {
                        value 0 ;
                      }
                    }
                    ncd:revise-date 2019-07-29 ;
                  }
                  leaf advertise-maximum-prefix {
                    description 'Maximum number of prefix send to this peer.'
                                ;
                    type uint32 {
                      range 1..4294967295 ;
                    }
                  }
                  leaf allowas-in {
                    description 'Accept as-path with my AS present in it.'
                                ;
                    type uint32 {
                      range 1..10 ;
                    }
                  }
                  leaf as-path-loopcheck {
                    description 'Check as-path sending BGP routing to EBGP neig'
                              + 'hbor.'
                                ;
                    type empty ;
                  }
                  leaf default-originate {
                    description 'Originate default route to this neighbor.'
                                ;
                    type empty ;
                  }
                  leaf default-originate-routemap {
                    description 'Map external entry attributes into routing tab'
                              + 'le.'
                                ;
                    type string {
                      length 1..200 ;
                    }
                    ncd:revise-date 2020-07-28 ;
                  }
                  leaf default-originate-routepolicy {
                    description 'Set external entry attributes into routing tab'
                              + 'le.'
                                ;
                    type string {
                      length 1..200 ;
                    }
                    ncd:revise-date 2020-10-10 ;
                  }
                  leaf maxas-in {
                    description 'Accept as-path not exceeded maxas-in.'
                                ;
                    type uint32 {
                      range 1..250 ;
                    }
                  }
                  leaf next-hop-self {
                    description 'Disable the next hop calculation for this neig'
                              + 'hbor.'
                                ;
                    type enumeration {
                      enum enable {
                        value 1 ;
                        description 'Apply next-hop-self for EBGP route.'
                                    ;
                      }
                      enum all {
                        value 2 ;
                        description 'Apply next-hop-self for both EBGP and IBGP'
                                  + ' route.'
                                    ;
                      }
                    }
                  }
                  choice nh-unchanged {
                    case next-hop-unchanged {
                      description 'NEXT_HOP of the IBGP path propagated unchang'
                                + 'ed to this neighbor.'
                                  ;
                      leaf next-hop-unchanged {
                        description 'Propagate next hop unchanged for IBGP path'
                                  + 's to this neighbor.'
                                    ;
                        type empty ;
                      }
                      ncd:revise-date 2019-06-04 ;
                    }
                    case next-hop-unchanged-all {
                      description 'NEXT_HOP of either EBGP or IBGP path propaga'
                                + 'ted unchanged to this neighbor.'
                                  ;
                      leaf next-hop-unchanged-all {
                        description 'NEXT_HOP of either EBGP or IBGP path propa'
                                  + 'gated unchanged to this neighbor.'
                                    ;
                        type empty ;
                      }
                      ncd:revise-date 2020-04-07 ;
                    }
                  }
                  leaf remove-private-as {
                    description 'EBGP use to remove private AS number.'
                                ;
                    type enumeration {
                      enum disable {
                        value 0 ;
                      }
                      enum enable {
                        value 1 ;
                      }
                    }
                  }
                  leaf route-reflector-client {
                    description 'Set this neighbor as a client peer.'
                                ;
                    type empty ;
                  }
                  leaf send-community {
                    description 'Send community to this neighbor.'
                                ;
                    type empty ;
                  }
                  leaf send-large-community {
                    description 'Send Large-community to this neighbor.'
                                ;
                    type empty ;
                    ncd:revise-date 2020-04-16 ;
                  }
                  leaf send-med {
                    description 'Send metric attribute to this neighbor.'
                                ;
                    type empty ;
                  }
                  leaf inherit-igp-metric {
                    description 'Med attribute inherited from IGP metric before'
                              + ' sending updates.'
                                ;
                    type empty ;
                    ncd:revise-date 2017-07-25 ;
                  }
                  leaf soft-reconfiguration {
                    status obsolete {
                      ncd:revise-date 2018-01-31 ;
                    }
                    description 'Neighbor soft reconfiguration.'
                                ;
                    type empty ;
                  }
                  leaf soft-reconfig {
                    description 'Neighbor soft reconfiguration.'
                                ;
                    type enumeration {
                      enum soft-reconfiguration {
                        value 1 ;
                        description Soft-reconfiguration. ;
                      }
                      enum enforce-soft-reconfiguration {
                        value 2 ;
                        description 'Enforce soft-reconfiguration instead of se'
                                  + 'nding route-refresh.'
                                    ;
                      }
                    }
                    ncd:revise-date 2018-01-31 ;
                  }
                  leaf split-update-group {
                    description 'Split neighbor from update group.'
                                ;
                    type empty ;
                  }
                  leaf weight {
                    description 'Set weight for routes from this neighbor.'
                                ;
                    type uint32 {
                      range 1..65535 ;
                    }
                  }
                  leaf aigp {
                    description 'Enable AIGP for this neighbor.'
                                ;
                    type empty ;
                    ncd:revise-date 2017-11-01 ;
                  }
                  leaf send-label {
                    description 'Send NLRI with MPLS label to this neighbor.'
                                ;
                    type empty ;
                    ncd:revise-date 2018-11-06 ;
                  }
                  container neighbor-extend {
                    description 'Specify a neighbor.'
                                ;
                    leaf additional-paths-receive {
                      description 'Receive additional paths from this neighbor.'
                                  ;
                      type empty ;
                    }
                    container maximum-prefix {
                      description 'The action that generated when threshold val'
                                + 'ue reached.'
                                  ;
                      presence 'The action that generated when threshold value '
                             + 'reached'
                               ;
                      leaf maximum-prefix-number {
                        description 'Maximum number of prefix limit.'
                                    ;
                        type uint32 {
                          range 1..4294967295 ;
                        }
                        mandatory true ;
                      }
                      leaf maximum-prefix-threshold {
                        description 'Threshold value(%) at which to generate a '
                                  + 'warning.'
                                    ;
                        type uint32 {
                          range 1..100 ;
                        }
                        mandatory true ;
                      }
                      choice maximum-prefix-action {
                        description 'The action that generated when threshold v'
                                  + 'alue reached.'
                                    ;
                        mandatory true ;
                        case peer-action {
                          description 'The action that generated when threshold'
                                    + ' value reached.'
                                      ;
                          leaf action {
                            description 'The action that generated when threshold value reached.'
                                        ;
                            type enumeration {
                              enum down {
                                value 0 ;
                                description 'Break down BGP connection after limit is exceeded.'
                                            ;
                              }
                              enum warning-only {
                                value 1 ;
                                description 'Only give warning message when limit is exceeded.'
                                            ;
                              }
                              enum drop-routes {
                                value 2 ;
                                description 'Drop routes that exceed the maximum-prefix.'
                                            ;
                              }
                            }
                            mandatory true ;
                          }
                        }
                        case restart {
                          description 'Restart BGP connection after limit is ex'
                                    + 'ceeded.'
                                      ;
                          leaf restart-time {
                            description 'Restart interval in minutes.'
                                        ;
                            type uint32 {
                              range 1..30000 ;
                            }
                            units min ;
                            mandatory true ;
                          }
                        }
                      }
                    }
                    leaf prefix-list-in-name {
                      description 'Apply prefix list to incoming routes.'
                                  ;
                      type string {
                        length 1..169 ;
                      }
                    }
                    leaf prefix-list-out-name {
                      description 'Apply  prefix list to outbound routes.'
                                  ;
                      type string {
                        length 1..169 ;
                      }
                    }
                    leaf route-map-in-name {
                      description 'Apply route-map to incoming routes.'
                                  ;
                      type string {
                        length 1..200 ;
                      }
                    }
                    leaf route-map-out-name {
                      description 'Apply route-map to outbound routes.'
                                  ;
                      type string {
                        length 1..200 ;
                      }
                    }
                    container diverse-path {
                      description 'Advertise diverse path to this neighbor.'
                                  ;
                      presence diverse-path ;
                      choice diverse-path {
                        description 'Advertise diverse path to this neighbor.'
                                    ;
                        mandatory true ;
                        case backup {
                          description 'Advertisement of the backup path.'
                                      ;
                          leaf backup {
                            description 'Advertisement of the backup path.'
                                        ;
                            type empty ;
                            mandatory true ;
                          }
                        }
                        case multipath {
                          description 'Sequence number of multipath.'
                                      ;
                          leaf sequence-number {
                            description 'Sequence number of multipath.'
                                        ;
                            type uint32 {
                              range 2..32 ;
                            }
                            mandatory true ;
                          }
                        }
                      }
                      leaf route-map {
                        description 'Apply route-map to neighbor.'
                                    ;
                        type string {
                          length 1..200 ;
                        }
                      }
                    }
                    container additional-paths-send {
                      description 'Send additional paths to this neighbor.'
                                  ;
                      choice additional-paths-send {
                        description 'Send additional paths to this neighbor.'
                                    ;
                        default send-one-path ;
                        case send-one-path {
                          description 'Send one additional path to this neighbo'
                                    + 'r.'
                                      ;
                          leaf send {
                            description 'Send additional paths to this neighbor.'
                                        ;
                            type empty ;
                          }
                        }
                        case send-multi-paths {
                          description 'Send additional multi-paths to this neig'
                                    + 'hbor.'
                                      ;
                          leaf paths-number {
                            description 'Number of paths for a prefix.'
                                        ;
                            type uint32 {
                              range 2..32 ;
                            }
                            mandatory true ;
                          }
                          leaf prefixlist {
                            description 'Prefixlist of filtering additional paths.'
                                        ;
                            type string {
                              length 1..169 ;
                            }
                          }
                        }
                      }
                    }
                    leaf routepolicy-in-name {
                      description 'Route policy name applied to the inbound rou'
                                + 'tes.'
                                  ;
                      type string {
                        length 1..200 ;
                      }
                    }
                    leaf routepolicy-out-name {
                      description 'Route policy name applied to the outbound ro'
                                + 'utes.'
                                  ;
                      type string {
                        length 1..200 ;
                      }
                    }
                    container withdraw {
                      description 'Withdraw routes when state of track-group is'
                                + ' down.'
                                  ;
                      presence withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                      ncd:revise-date 2016-02-06 ;
                    }
                    container second-withdraw {
                      description 'Withdraw routes when state of the second tra'
                                + 'ck-group is down.'
                                  ;
                      presence second-withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                      ncd:revise-date 2018-07-12 ;
                    }
                  }
                  container advertise-map-uni {
                    description 'Specify route-map for conditional advertisemen'
                              + 't.'
                                ;
                    presence 'Specify route-map for conditional advertisement'
                             ;
                    leaf advertise-map-name {
                      description 'Advertise route-map name.'
                                  ;
                      type string {
                        length 1..200 ;
                      }
                      mandatory true ;
                    }
                    choice advertise-map {
                      description 'Specify route-map for conditional advertisem'
                                + 'ent.'
                                  ;
                      mandatory true ;
                      case exist-map {
                        description 'Advertise prefix only if prefix exists.'
                                    ;
                        leaf exist-map-name {
                          description 'Advertise prefix only if prefix exists.'
                                      ;
                          type string {
                            length 1..200 ;
                          }
                          mandatory true ;
                        }
                      }
                      case nonexist-map {
                        description 'Advertise prefix only if prefix does not e'
                                  + 'xist.'
                                    ;
                        leaf nonexist-map-name {
                          description 'Advertise prefix only if prefix does not'
                                    + ' exist.'
                                      ;
                          type string {
                            length 1..200 ;
                          }
                          mandatory true ;
                        }
                      }
                    }
                    ncd:revise-date 2016-11-15 ;
                  }
                  container route-filter-group {
                    description 'Specify a neighbor to join a route-filter-grou'
                              + 'p.'
                                ;
                    presence route-filter-group ;
                    leaf filter-group {
                      description 'Route filter group name (1-31 characters).'
                                  ;
                      type string {
                        length 1..31 ;
                      }
                      mandatory true ;
                    }
                    leaf next-hop-self {
                      description 'Disable the next hop calculation for this ne'
                                + 'ighbor.'
                                  ;
                      type empty ;
                    }
                    ncd:revise-date 2017-06-12 ;
                  }
                  leaf announce-sid {
                    description 'Enable Prefix-SID attribute for this neighbor.'
                                ;
                    type enumeration {
                      enum enable {
                        value 1 ;
                        description 'Enable Prefix-SID attribute for this neigh'
                                  + 'bor.'
                                    ;
                      }
                    }
                    ncd:revise-date 2018-05-14 ;
                  }
                  leaf send-link-bw {
                    description 'Send link bandwidth to this neighbor.'
                                ;
                    type enumeration {
                      enum disable {
                        value 0 ;
                        description 'Disable peer send link bandwidth'
                                    ;
                      }
                      enum enable {
                        value 1 ;
                        description 'Enable peer send link bandwidth'
                                    ;
                      }
                    }
                    ncd:revise-date 2019-10-22 ;
                  }
                  container route-server-client {
                    description 'Set route server client only valid for ebgp pe'
                              + 'er.'
                                ;
                    presence route-server-client ;
                    leaf route-svr-client {
                      description 'Set route server client only valid for ebgp '
                                + 'peer.'
                                  ;
                      type empty ;
                      mandatory true ;
                    }
                    ncd:revise-date 2020-04-07 ;
                  }
                }
              }
              container neighbor-ipv4 {
                description 'Specify a IPv4 neighbor.'
                            ;
                list neighbor {
                  description 'Specify a neighbor.'
                              ;
                  key ipv4-addr ;
                  leaf ipv4-addr {
                    description 'Neighbor IPv4 address.'
                                ;
                    type ncd:ipv4-address ;
                  }
                  leaf joined-group {
                    description 'Only for read operation. The joined group name.'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf monitor {
                    description 'Config BMP monitor for the address family of t'
                              + 'his neighbor.'
                                ;
                    type enumeration {
                      enum disable {
                        value 2 ;
                      }
                      enum enable {
                        value 1 ;
                      }
                      enum inherit-global-config {
                        value 0 ;
                      }
                    }
                    ncd:revise-date 2019-07-29 ;
                  }
                  leaf advertise-maximum-prefix {
                    description 'Maximum number of prefix send to this peer.'
                                ;
                    type uint32 {
                      range 1..4294967295 ;
                    }
                  }
                  leaf allowas-in {
                    description 'Accept as-path with my AS present in it.'
                                ;
                    type uint32 {
                      range 1..10 ;
                    }
                  }
                  leaf as-path-loopcheck {
                    description 'Check as-path sending BGP routing to EBGP neig'
                              + 'hbor.'
                                ;
                    type empty ;
                  }
                  leaf maxas-in {
                    description 'Accept as-path not exceeded maxas-in.'
                                ;
                    type uint32 {
                      range 1..250 ;
                    }
                  }
                  leaf next-hop-self {
                    description 'Disable the next hop calculation for this neig'
                              + 'hbor.'
                                ;
                    type enumeration {
                      enum enable {
                        value 1 ;
                        description 'Apply next-hop-self for EBGP route.'
                                    ;
                      }
                      enum all {
                        value 2 ;
                        description 'Apply next-hop-self for both EBGP and IBGP'
                                  + ' route.'
                                    ;
                      }
                    }
                  }
                  choice nh-unchanged {
                    case next-hop-unchanged {
                      description 'NEXT_HOP of the IBGP path propagated unchang'
                                + 'ed to this neighbor.'
                                  ;
                      leaf next-hop-unchanged {
                        description 'Propagate next hop unchanged for IBGP path'
                                  + 's to this neighbor.'
                                    ;
                        type empty ;
                      }
                      ncd:revise-date 2019-06-04 ;
                    }
                    case next-hop-unchanged-all {
                      description 'NEXT_HOP of either EBGP or IBGP path propaga'
                                + 'ted unchanged to this neighbor.'
                                  ;
                      leaf next-hop-unchanged-all {
                        description 'NEXT_HOP of either EBGP or IBGP path propa'
                                  + 'gated unchanged to this neighbor.'
                                    ;
                        type empty ;
                      }
                      ncd:revise-date 2020-04-07 ;
                    }
                  }
                  leaf remove-private-as {
                    description 'EBGP use to remove private AS number.'
                                ;
                    type enumeration {
                      enum disable {
                        value 0 ;
                      }
                      enum enable {
                        value 1 ;
                      }
                    }
                  }
                  leaf route-reflector-client {
                    description 'Set this neighbor as a client peer.'
                                ;
                    type empty ;
                  }
                  leaf send-community {
                    description 'Send community to this neighbor.'
                                ;
                    type empty ;
                  }
                  leaf send-large-community {
                    description 'Send Large-community to this neighbor.'
                                ;
                    type empty ;
                    ncd:revise-date 2020-04-16 ;
                  }
                  leaf send-label {
                    description 'Send NLRI with MPLS label to this neighbor.'
                                ;
                    type empty ;
                  }
                  leaf send-med {
                    description 'Send metric attribute to this neighbor.'
                                ;
                    type empty ;
                  }
                  leaf inherit-igp-metric {
                    description 'Med attribute inherited from IGP metric before'
                              + ' sending updates.'
                                ;
                    type empty ;
                    ncd:revise-date 2017-07-25 ;
                  }
                  leaf soft-reconfiguration {
                    status obsolete {
                      ncd:revise-date 2018-01-31 ;
                    }
                    description 'Neighbor soft reconfiguration.'
                                ;
                    type empty ;
                  }
                  leaf soft-reconfig {
                    description 'Neighbor soft reconfiguration.'
                                ;
                    type enumeration {
                      enum soft-reconfiguration {
                        value 1 ;
                        description Soft-reconfiguration. ;
                      }
                      enum enforce-soft-reconfiguration {
                        value 2 ;
                        description 'Enforce soft-reconfiguration instead of se'
                                  + 'nding route-refresh.'
                                    ;
                      }
                    }
                    ncd:revise-date 2018-01-31 ;
                  }
                  leaf split-update-group {
                    description 'Split neighbor from update group.'
                                ;
                    type empty ;
                  }
                  leaf weight {
                    description 'Set weight for routes from this neighbor.'
                                ;
                    type uint32 {
                      range 1..65535 ;
                    }
                  }
                  leaf default-originate {
                    description 'Originate default route to this neighbor.'
                                ;
                    type empty ;
                  }
                  leaf default-originate-routemap {
                    description 'Map external entry attributes into routing tab'
                              + 'le.'
                                ;
                    type string {
                      length 1..200 ;
                    }
                    ncd:revise-date 2020-07-28 ;
                  }
                  leaf default-originate-routepolicy {
                    description 'Set external entry attributes into routing tab'
                              + 'le.'
                                ;
                    type string {
                      length 1..200 ;
                    }
                    ncd:revise-date 2020-10-10 ;
                  }
                  leaf aigp {
                    description 'Enable AIGP for this neighbor.'
                                ;
                    type empty ;
                    ncd:revise-date 2017-11-01 ;
                  }
                  container neighbor-extend {
                    description 'Specify a neighbor.'
                                ;
                    leaf additional-paths-receive {
                      description 'Receive additional paths from this neighbor.'
                                  ;
                      type empty ;
                    }
                    leaf prefix-list-in-name {
                      description 'Apply prefix list to incoming routes.'
                                  ;
                      type string {
                        length 1..169 ;
                      }
                    }
                    leaf prefix-list-out-name {
                      description 'Apply prefix list to outbound routes.'
                                  ;
                      type string {
                        length 1..169 ;
                      }
                    }
                    leaf route-map-in-name {
                      description 'Apply route-map to incoming routes.'
                                  ;
                      type string {
                        length 1..200 ;
                      }
                    }
                    leaf route-map-out-name {
                      description 'Apply route-map to outbound routes.'
                                  ;
                      type string {
                        length 1..200 ;
                      }
                    }
                    leaf routepolicy-in-name {
                      description 'Route policy name applied to the inbound rou'
                                + 'tes.'
                                  ;
                      type string {
                        length 1..200 ;
                      }
                    }
                    leaf routepolicy-out-name {
                      description 'Route policy name applied to the outbound ro'
                                + 'utes.'
                                  ;
                      type string {
                        length 1..200 ;
                      }
                    }
                    container maximum-prefix {
                      description 'The action that generated when threshold val'
                                + 'ue reached.'
                                  ;
                      presence 'The action that generated when threshold value '
                             + 'reached'
                               ;
                      leaf maximum-prefix-number {
                        description 'Maximum number of prefix limit.'
                                    ;
                        type uint32 {
                          range 1..4294967295 ;
                        }
                        mandatory true ;
                      }
                      leaf maximum-prefix-threshold {
                        description 'Threshold value(%) at which to generate a '
                                  + 'warning.'
                                    ;
                        type uint32 {
                          range 1..100 ;
                        }
                        mandatory true ;
                      }
                      choice maximum-prefix-action {
                        description 'The action that generated when threshold v'
                                  + 'alue reached.'
                                    ;
                        mandatory true ;
                        case peer-action {
                          description 'The action that generated when threshold'
                                    + ' value reached.'
                                      ;
                          leaf action {
                            description 'The action that generated when threshold value reached.'
                                        ;
                            type enumeration {
                              enum down {
                                value 0 ;
                                description 'Break down BGP connection after limit is exceeded.'
                                            ;
                              }
                              enum warning-only {
                                value 1 ;
                                description 'Only give warning message when limit is exceeded.'
                                            ;
                              }
                              enum drop-routes {
                                value 2 ;
                                description 'Drop routes that exceed the maximum-prefix.'
                                            ;
                              }
                            }
                            mandatory true ;
                          }
                        }
                        case restart {
                          description 'Restart BGP connection after limit is ex'
                                    + 'ceeded.'
                                      ;
                          leaf restart-time {
                            description 'Restart interval in minutes.'
                                        ;
                            type uint32 {
                              range 1..30000 ;
                            }
                            units min ;
                            mandatory true ;
                          }
                        }
                      }
                    }
                    container diverse-path {
                      description 'Advertise diverse path to this neighbor.'
                                  ;
                      presence diverse-path ;
                      choice diverse-path {
                        description 'Advertise diverse path to this neighbor.'
                                    ;
                        mandatory true ;
                        case backup {
                          description 'Advertisement of the backup path.'
                                      ;
                          leaf backup {
                            description 'Advertisement of the backup path.'
                                        ;
                            type empty ;
                            mandatory true ;
                          }
                        }
                        case multipath {
                          description 'Sequence number of multipath.'
                                      ;
                          leaf sequence-number {
                            description 'Sequence number of multipath.'
                                        ;
                            type uint32 {
                              range 2..32 ;
                            }
                            mandatory true ;
                          }
                        }
                      }
                      leaf route-map {
                        description 'Apply route-map to neighbor.'
                                    ;
                        type string {
                          length 1..200 ;
                        }
                      }
                    }
                    container additional-paths-send {
                      description 'Send additional paths to this neighbor.'
                                  ;
                      choice additional-paths-send {
                        description 'Send additional paths to this neighbor.'
                                    ;
                        default send-one-path ;
                        case send-one-path {
                          description 'Send one additional path to this neighbo'
                                    + 'r.'
                                      ;
                          leaf send {
                            description 'Send additional paths to this neighbor.'
                                        ;
                            type empty ;
                          }
                        }
                        case send-multi-paths {
                          description 'Send additional multi-paths to this neig'
                                    + 'hbor.'
                                      ;
                          leaf paths-number {
                            description 'Number of paths for a prefix.'
                                        ;
                            type uint32 {
                              range 2..32 ;
                            }
                            mandatory true ;
                          }
                          leaf prefixlist {
                            description 'Prefixlist of filtering additional paths.'
                                        ;
                            type string {
                              length 1..169 ;
                            }
                          }
                        }
                      }
                    }
                    container withdraw {
                      description 'Withdraw routes when state of track-group is'
                                + ' down.'
                                  ;
                      presence withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                      ncd:revise-date 2016-02-06 ;
                    }
                    container second-withdraw {
                      description 'Withdraw routes when state of the second tra'
                                + 'ck-group is down.'
                                  ;
                      presence second-withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                      ncd:revise-date 2018-07-12 ;
                    }
                  }
                  container advertise-map-uni {
                    description 'Specify route-map for conditional advertisemen'
                              + 't.'
                                ;
                    presence 'Specify route-map for conditional advertisement'
                             ;
                    leaf advertise-map-name {
                      description 'Advertise route-map name.'
                                  ;
                      type string {
                        length 1..200 ;
                      }
                      mandatory true ;
                    }
                    choice advertise-map {
                      description 'Specify route-map for conditional advertisem'
                                + 'ent.'
                                  ;
                      mandatory true ;
                      case exist-map {
                        description 'Advertise prefix only if prefix exists.'
                                    ;
                        leaf exist-map-name {
                          description 'Advertise prefix only if prefix exists.'
                                      ;
                          type string {
                            length 1..200 ;
                          }
                          mandatory true ;
                        }
                      }
                      case nonexist-map {
                        description 'Advertise prefix only if prefix does not e'
                                  + 'xist.'
                                    ;
                        leaf nonexist-map-name {
                          description 'Advertise prefix only if prefix does not'
                                    + ' exist.'
                                      ;
                          type string {
                            length 1..200 ;
                          }
                          mandatory true ;
                        }
                      }
                    }
                    ncd:revise-date 2016-11-15 ;
                  }
                  container route-filter-group {
                    description 'Specify a neighbor to join a route-filter-grou'
                              + 'p.'
                                ;
                    presence route-filter-group ;
                    leaf filter-group {
                      description 'Route filter group name (1-31 characters).'
                                  ;
                      type string {
                        length 1..31 ;
                      }
                      mandatory true ;
                    }
                    leaf next-hop-self {
                      description 'Disable the next hop calculation for this ne'
                                + 'ighbor.'
                                  ;
                      type empty ;
                    }
                    ncd:revise-date 2017-06-12 ;
                  }
                  leaf announce-sid {
                    description 'Enable Prefix-SID attribute for this neighbor.'
                                ;
                    type enumeration {
                      enum enable {
                        value 1 ;
                        description 'Enable Prefix-SID attribute for this neigh'
                                  + 'bor.'
                                    ;
                      }
                    }
                    ncd:revise-date 2018-05-14 ;
                  }
                  leaf send-link-bw {
                    description 'Send link bandwidth to this neighbor.'
                                ;
                    type enumeration {
                      enum disable {
                        value 0 ;
                        description 'Disable peer send link bandwidth'
                                    ;
                      }
                      enum enable {
                        value 1 ;
                        description 'Enable peer send link bandwidth'
                                    ;
                      }
                      enum inherit {
                        value 2 ;
                        description 'If the neighbor joined a group, the status'
                                  + ' inherited from group.'
                                    ;
                      }
                    }
                    ncd:revise-date 2019-10-22 ;
                  }
                  container route-server-client {
                    description 'Set route server client only valid for ebgp pe'
                              + 'er.'
                                ;
                    presence route-server-client ;
                    leaf route-svr-client {
                      description 'Set route server client only valid for ebgp '
                                + 'peer.'
                                  ;
                      type empty ;
                      mandatory true ;
                    }
                    ncd:revise-date 2020-04-07 ;
                  }
                }
              }
              container neighbor-ipv6 {
                description 'Specify a IPv6 neighbor.'
                            ;
                list neighbor {
                  description 'Specify a neighbor.'
                              ;
                  key ipv6-addr ;
                  leaf ipv6-addr {
                    description 'Neighbor IPv6 address.'
                                ;
                    type ncd:ipv6-address ;
                  }
                  leaf joined-group {
                    description 'Only for read operation. The joined group name.'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf monitor {
                    description 'Config BMP monitor for the address family of t'
                              + 'his neighbor.'
                                ;
                    type enumeration {
                      enum disable {
                        value 2 ;
                      }
                      enum enable {
                        value 1 ;
                      }
                      enum inherit-global-config {
                        value 0 ;
                      }
                    }
                    ncd:revise-date 2019-07-29 ;
                  }
                  leaf advertise-maximum-prefix {
                    description 'Maximum number of prefix send to this peer.'
                                ;
                    type uint32 {
                      range 1..4294967295 ;
                    }
                  }
                  leaf allowas-in {
                    description 'Accept as-path with my AS present in it.'
                                ;
                    type uint32 {
                      range 1..10 ;
                    }
                  }
                  leaf as-path-loopcheck {
                    description 'Check as-path sending BGP routing to EBGP neig'
                              + 'hbor.'
                                ;
                    type empty ;
                  }
                  leaf maxas-in {
                    description 'Accept as-path not exceeded maxas-in.'
                                ;
                    type uint32 {
                      range 1..250 ;
                    }
                  }
                  leaf next-hop-self {
                    description 'Disable the next hop calculation for this neig'
                              + 'hbor.'
                                ;
                    type enumeration {
                      enum enable {
                        value 1 ;
                        description 'Apply next-hop-self for EBGP route.'
                                    ;
                      }
                      enum all {
                        value 2 ;
                        description 'Apply next-hop-self for both EBGP and IBGP'
                                  + ' route.'
                                    ;
                      }
                    }
                  }
                  choice nh-unchanged {
                    case next-hop-unchanged {
                      description 'NEXT_HOP of the IBGP path propagated unchang'
                                + 'ed to this neighbor.'
                                  ;
                      leaf next-hop-unchanged {
                        description 'Propagate next hop unchanged for IBGP path'
                                  + 's to this neighbor.'
                                    ;
                        type empty ;
                      }
                      ncd:revise-date 2019-06-04 ;
                    }
                    case next-hop-unchanged-all {
                      description 'NEXT_HOP of either EBGP or IBGP path propaga'
                                + 'ted unchanged to this neighbor.'
                                  ;
                      leaf next-hop-unchanged-all {
                        description 'NEXT_HOP of either EBGP or IBGP path propa'
                                  + 'gated unchanged to this neighbor.'
                                    ;
                        type empty ;
                      }
                      ncd:revise-date 2020-04-07 ;
                    }
                  }
                  leaf remove-private-as {
                    description 'EBGP use to remove private AS number.'
                                ;
                    type enumeration {
                      enum disable {
                        value 0 ;
                      }
                      enum enable {
                        value 1 ;
                      }
                    }
                  }
                  leaf route-reflector-client {
                    description 'Set this neighbor as a client peer.'
                                ;
                    type empty ;
                  }
                  leaf send-community {
                    description 'Send community to this neighbor.'
                                ;
                    type empty ;
                  }
                  leaf send-large-community {
                    description 'Send Large-community to this neighbor.'
                                ;
                    type empty ;
                    ncd:revise-date 2020-04-16 ;
                  }
                  leaf send-label {
                    description 'Send NLRI with MPLS label to this neighbor.'
                                ;
                    type empty ;
                  }
                  leaf send-med {
                    description 'Send metric attribute to this neighbor.'
                                ;
                    type empty ;
                  }
                  leaf inherit-igp-metric {
                    description 'Med attribute inherited from IGP metric before'
                              + ' sending updates.'
                                ;
                    type empty ;
                    ncd:revise-date 2017-07-25 ;
                  }
                  leaf soft-reconfiguration {
                    status obsolete {
                      ncd:revise-date 2018-01-31 ;
                    }
                    description 'Neighbor soft reconfiguration.'
                                ;
                    type empty ;
                  }
                  leaf soft-reconfig {
                    description 'Neighbor soft reconfiguration.'
                                ;
                    type enumeration {
                      enum soft-reconfiguration {
                        value 1 ;
                        description Soft-reconfiguration. ;
                      }
                      enum enforce-soft-reconfiguration {
                        value 2 ;
                        description 'Enforce soft-reconfiguration instead of se'
                                  + 'nding route-refresh.'
                                    ;
                      }
                    }
                    ncd:revise-date 2018-01-31 ;
                  }
                  leaf split-update-group {
                    description 'Split neighbor from update group.'
                                ;
                    type empty ;
                  }
                  leaf weight {
                    description 'Set weight for routes from this neighbor.'
                                ;
                    type uint32 {
                      range 1..65535 ;
                    }
                  }
                  leaf default-originate {
                    description 'Originate default route to this neighbor.'
                                ;
                    type empty ;
                  }
                  leaf default-originate-routemap {
                    description 'Map external entry attributes into routing tab'
                              + 'le.'
                                ;
                    type string {
                      length 1..200 ;
                    }
                    ncd:revise-date 2020-07-28 ;
                  }
                  leaf default-originate-routepolicy {
                    description 'Set external entry attributes into routing tab'
                              + 'le.'
                                ;
                    type string {
                      length 1..200 ;
                    }
                    ncd:revise-date 2020-10-10 ;
                  }
                  leaf aigp {
                    description 'Enable AIGP for this neighbor.'
                                ;
                    type empty ;
                    ncd:revise-date 2017-11-01 ;
                  }
                  container neighbor-extend {
                    description 'Specify a neighbor.'
                                ;
                    leaf additional-paths-receive {
                      description 'Receive additional paths from this neighbor.'
                                  ;
                      type empty ;
                    }
                    leaf prefix-list-in-name {
                      description 'Apply prefix list to incoming routes.'
                                  ;
                      type string {
                        length 1..169 ;
                      }
                    }
                    leaf prefix-list-out-name {
                      description 'Apply prefix list to outbound routes.'
                                  ;
                      type string {
                        length 1..169 ;
                      }
                    }
                    leaf route-map-in-name {
                      description 'Apply route-map to incoming routes.'
                                  ;
                      type string {
                        length 1..200 ;
                      }
                    }
                    leaf route-map-out-name {
                      description 'Apply route-map to outbound routes.'
                                  ;
                      type string {
                        length 1..200 ;
                      }
                    }
                    leaf routepolicy-in-name {
                      description 'Route policy name applied to the inbound rou'
                                + 'tes.'
                                  ;
                      type string {
                        length 1..200 ;
                      }
                    }
                    leaf routepolicy-out-name {
                      description 'Route policy name applied to the outbound ro'
                                + 'utes.'
                                  ;
                      type string {
                        length 1..200 ;
                      }
                    }
                    container maximum-prefix {
                      description 'The action that generated when threshold val'
                                + 'ue reached.'
                                  ;
                      presence 'The action that generated when threshold value '
                             + 'reached'
                               ;
                      leaf maximum-prefix-number {
                        description 'Maximum number of prefix limit.'
                                    ;
                        type uint32 {
                          range 1..4294967295 ;
                        }
                        mandatory true ;
                      }
                      leaf maximum-prefix-threshold {
                        description 'Threshold value(%) at which to generate a '
                                  + 'warning.'
                                    ;
                        type uint32 {
                          range 1..100 ;
                        }
                        mandatory true ;
                      }
                      choice maximum-prefix-action {
                        description 'The action that generated when threshold v'
                                  + 'alue reached.'
                                    ;
                        mandatory true ;
                        case peer-action {
                          description 'The action that generated when threshold'
                                    + ' value reached.'
                                      ;
                          leaf action {
                            description 'The action that generated when threshold value reached.'
                                        ;
                            type enumeration {
                              enum down {
                                value 0 ;
                                description 'Break down BGP connection after limit is exceeded.'
                                            ;
                              }
                              enum warning-only {
                                value 1 ;
                                description 'Only give warning message when limit is exceeded.'
                                            ;
                              }
                              enum drop-routes {
                                value 2 ;
                                description 'Drop routes that exceed the maximum-prefix.'
                                            ;
                              }
                            }
                            mandatory true ;
                          }
                        }
                        case restart {
                          description 'Restart BGP connection after limit is ex'
                                    + 'ceeded.'
                                      ;
                          leaf restart-time {
                            description 'Restart interval in minutes.'
                                        ;
                            type uint32 {
                              range 1..30000 ;
                            }
                            units min ;
                            mandatory true ;
                          }
                        }
                      }
                    }
                    container diverse-path {
                      description 'Advertise diverse path to this neighbor.'
                                  ;
                      presence diverse-path ;
                      choice diverse-path {
                        description 'Advertise diverse path to this neighbor.'
                                    ;
                        mandatory true ;
                        case backup {
                          description 'Advertisement of the backup path.'
                                      ;
                          leaf backup {
                            description 'Advertisement of the backup path.'
                                        ;
                            type empty ;
                            mandatory true ;
                          }
                        }
                        case multipath {
                          description 'Sequence number of multipath.'
                                      ;
                          leaf sequence-number {
                            description 'Sequence number of multipath.'
                                        ;
                            type uint32 {
                              range 2..32 ;
                            }
                            mandatory true ;
                          }
                        }
                      }
                      leaf route-map {
                        description 'Apply route-map to neighbor.'
                                    ;
                        type string {
                          length 1..200 ;
                        }
                      }
                    }
                    container additional-paths-send {
                      description 'Send additional paths to this neighbor.'
                                  ;
                      choice additional-paths-send {
                        description 'Send additional paths to this neighbor.'
                                    ;
                        default send-one-path ;
                        case send-one-path {
                          description 'Send one additional path to this neighbo'
                                    + 'r.'
                                      ;
                          leaf send {
                            description 'Send additional paths to this neighbor.'
                                        ;
                            type empty ;
                          }
                        }
                        case send-multi-paths {
                          description 'Send additional multi-paths to this neig'
                                    + 'hbor.'
                                      ;
                          leaf paths-number {
                            description 'Number of paths for a prefix.'
                                        ;
                            type uint32 {
                              range 2..32 ;
                            }
                            mandatory true ;
                          }
                          leaf prefixlist {
                            description 'prefixlist of Filtering additional paths.'
                                        ;
                            type string {
                              length 1..169 ;
                            }
                          }
                        }
                      }
                    }
                    container withdraw {
                      description 'Withdraw routes when state of track-group is'
                                + ' down.'
                                  ;
                      presence withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                      ncd:revise-date 2016-02-06 ;
                    }
                    container second-withdraw {
                      description 'Withdraw routes when state of the second tra'
                                + 'ck-group is down.'
                                  ;
                      presence second-withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                      ncd:revise-date 2018-07-12 ;
                    }
                  }
                  container advertise-map-uni {
                    description 'Specify route-map for conditional advertisemen'
                              + 't.'
                                ;
                    presence 'Specify route-map for conditional advertisement'
                             ;
                    leaf advertise-map-name {
                      description 'Advertise route-map name.'
                                  ;
                      type string {
                        length 1..200 ;
                      }
                      mandatory true ;
                    }
                    choice advertise-map {
                      description 'Specify route-map for conditional advertisem'
                                + 'ent.'
                                  ;
                      mandatory true ;
                      case exist-map {
                        description 'Advertise prefix only if prefix exists.'
                                    ;
                        leaf exist-map-name {
                          description 'Advertise prefix only if prefix exists.'
                                      ;
                          type string {
                            length 1..200 ;
                          }
                          mandatory true ;
                        }
                      }
                      case nonexist-map {
                        description 'Advertise prefix only if prefix does not e'
                                  + 'xist.'
                                    ;
                        leaf nonexist-map-name {
                          description 'Advertise prefix only if prefix does not'
                                    + ' exist.'
                                      ;
                          type string {
                            length 1..200 ;
                          }
                          mandatory true ;
                        }
                      }
                    }
                    ncd:revise-date 2016-11-15 ;
                  }
                  container route-filter-group {
                    description 'Specify a neighbor to join a route-filter-grou'
                              + 'p.'
                                ;
                    presence route-filter-group ;
                    leaf filter-group {
                      description 'Route filter group name (1-31 characters).'
                                  ;
                      type string {
                        length 1..31 ;
                      }
                      mandatory true ;
                    }
                    leaf next-hop-self {
                      description 'Disable the next hop calculation for this ne'
                                + 'ighbor.'
                                  ;
                      type empty ;
                    }
                    ncd:revise-date 2017-06-12 ;
                  }
                  leaf announce-sid {
                    description 'Enable Prefix-SID attribute for this neighbor.'
                                ;
                    type enumeration {
                      enum enable {
                        value 1 ;
                        description 'Enable Prefix-SID attribute for this neigh'
                                  + 'bor.'
                                    ;
                      }
                    }
                    ncd:revise-date 2018-05-14 ;
                  }
                  leaf send-link-bw {
                    description 'Send link bandwidth to this neighbor.'
                                ;
                    type enumeration {
                      enum disable {
                        value 0 ;
                        description 'Disable peer send link bandwidth'
                                    ;
                      }
                      enum enable {
                        value 1 ;
                        description 'Enable peer send link bandwidth'
                                    ;
                      }
                      enum inherit {
                        value 2 ;
                        description 'If the neighbor joined a group, the status'
                                  + ' inherited from group.'
                                    ;
                      }
                    }
                    ncd:revise-date 2019-10-22 ;
                  }
                  container route-server-client {
                    description 'Set route server client only valid for ebgp pe'
                              + 'er.'
                                ;
                    presence route-server-client ;
                    leaf route-svr-client {
                      description 'Set route server client only valid for ebgp '
                                + 'peer.'
                                  ;
                      type empty ;
                      mandatory true ;
                    }
                    ncd:revise-date 2020-04-07 ;
                  }
                }
              }
            }
            container network-v6-uni {
              description 'Specify a network to announce via BGP.'
                          ;
              presence network-v6-uni ;
              list network {
                description 'Specify a network to announce via BGP.'
                            ;
                key 'ipv6-address ipv6-mask-len'
                    ;
                leaf ipv6-address {
                  description 'Network prefix.'
                              ;
                  type ncd:ipv6-address ;
                }
                leaf ipv6-mask-len {
                  description 'Network mask length.'
                              ;
                  type uint8 {
                    range 0..128 ;
                  }
                }
                leaf route-map {
                  description 'Route-map to modify the attributes.'
                              ;
                  type string {
                    length 1..200 ;
                  }
                }
                leaf route-policy {
                  description 'Route-policy to modify the attributes.'
                              ;
                  type string {
                    length 1..200 ;
                  }
                  ncd:revise-date 2020-10-10 ;
                }
              }
            }
            container redistribute-v6-uni {
              description 'Redistribute information from another routing protoc'
                        + 'ol.'
                          ;
              presence redistribute-v6-uni ;
              container redistribute-v6uni {
                description 'Redistribute information from another routing prot'
                          + 'ocol.'
                            ;
                list redistribute {
                  description 'Redistribute information from another routing pr'
                            + 'otocol.'
                              ;
                  key protocol ;
                  leaf protocol {
                    description 'Routing protocol type.'
                                ;
                    type enumeration {
                      enum connected {
                        value 1 ;
                        description 'Connected routes.'
                                    ;
                      }
                      enum static {
                        value 2 ;
                        description 'Static routes.'
                                    ;
                      }
                      enum rip {
                        value 3 ;
                        description 'Routing information protocol(RIP).'
                                    ;
                      }
                      enum ps-busi-addr {
                        value 10 ;
                        description 'Ps-busi-addr routes.'
                                    ;
                      }
                      enum ps-user-addr {
                        value 11 ;
                        description 'Ps-user-addr routes.'
                                    ;
                      }
                      enum subscriber-host {
                        value 14 ;
                        description "Bras subscriber's host routes."
                                    ;
                      }
                      enum subscriber-aggregation {
                        value 15 ;
                        description "Bras subscriber's aggregation routes."
                                    ;
                      }
                      enum ldp {
                        value 16 ;
                        description 'Label distribution protocol(LDP).'
                                    ;
                      }
                      enum user-special {
                        value 17 ;
                        description 'User-special routes.'
                                    ;
                      }
                      enum sf-nat64 {
                        value 19 ;
                        description 'Stateful NAT64 routes.'
                                    ;
                      }
                      enum sl-nat64-ipv6 {
                        value 20 ;
                        description 'Stateless NAT64 prefix.'
                                    ;
                      }
                      enum aftr {
                        value 21 ;
                        description 'AFTR routes.'
                                    ;
                      }
                      enum nd-host {
                        value 22 ;
                        description 'ND-HOST routes.'
                                    ;
                      }
                      enum dhcp-pd {
                        value 23 ;
                        description 'DHCP-PD routes.'
                                    ;
                      }
                      enum bras-pool {
                        value 24 ;
                        description 'Broadband Remote Access Server pool routes.'
                                    ;
                      }
                      enum hagp {
                        value 26 ;
                        description 'Hybrid access gateway protocol routes.'
                                    ;
                      }
                      enum dyn-leasedline {
                        value 29 ;
                        description 'Dynamic-leased-line routes assigned by AAA.'
                                    ;
                      }
                      enum address {
                        value 9 ;
                        description 'Address routes.'
                                    ;
                      }
                      enum nptv6 {
                        value 30 ;
                        description 'IPv6-to-IPv6 Network Prefix Translation ro'
                                  + 'utes.'
                                    ;
                      }
                      enum srv6-locator {
                        value 31 ;
                        description 'SRv6 locator routes.'
                                    ;
                      }
                    }
                  }
                  leaf route-map {
                    description 'Apply route-map to redistribute.'
                                ;
                    type string {
                      length 1..200 ;
                    }
                  }
                  leaf route-policy {
                    description 'Apply route-policy to redistribute.'
                                ;
                    type string {
                      length 1..200 ;
                    }
                    ncd:revise-date 2020-10-10 ;
                  }
                  container set-metric {
                    description 'Set route metric.'
                                ;
                    leaf metric {
                      description 'Set route metric.'
                                  ;
                      type uint32 {
                        range 0..4294967295 ;
                      }
                    }
                  }
                }
              }
              container redistribute-isis-v6uni {
                description 'Redistribute information from ISIS protocol.'
                            ;
                list redistribute-isis {
                  description 'Redistribute information from ISIS protocol.'
                              ;
                  key 'protocol process-id'
                      ;
                  leaf protocol {
                    description 'Routing protocol type(ISIS-1,ISIS-2 or ISIS-1-'
                              + '2).'
                                ;
                    type enumeration {
                      enum isis-1 {
                        value 4 ;
                        description 'IS-IS level-1 routes only.'
                                    ;
                      }
                      enum isis-2 {
                        value 5 ;
                        description 'IS-IS level-2 routes only.'
                                    ;
                      }
                    }
                  }
                  leaf process-id {
                    description 'ISIS process ID.'
                                ;
                    type uint32 {
                      range 0..65535 ;
                    }
                  }
                  leaf route-map {
                    description 'Apply route-map to redistribute.'
                                ;
                    type string {
                      length 1..200 ;
                    }
                  }
                  leaf route-policy {
                    description 'Apply route-policy to redistribute.'
                                ;
                    type string {
                      length 1..200 ;
                    }
                    ncd:revise-date 2020-10-10 ;
                  }
                  container set-metric {
                    description 'Set route metric.'
                                ;
                    leaf metric {
                      description 'Set route metric.'
                                  ;
                      type uint32 {
                        range 0..4294967295 ;
                      }
                    }
                  }
                }
              }
              container redistribute-ospf-v6uni {
                description 'Redistribute information from OSPF protocol.'
                            ;
                list redistribute-ospf {
                  description 'Redistribute information from OSPF protocol.'
                              ;
                  key 'protocol process-id'
                      ;
                  leaf protocol {
                    description 'Routing protocol type(OSPF-EXT or OSPF-INT).'
                                ;
                    type enumeration {
                      enum ospf-ext {
                        value 7 ;
                        description 'Open shortest path first(OSPF) external ro'
                                  + 'utes.'
                                    ;
                      }
                      enum ospf-int {
                        value 8 ;
                        description 'Open shortest path first(OSPF) internal ro'
                                  + 'utes.'
                                    ;
                      }
                    }
                  }
                  leaf process-id {
                    description 'OSPF process ID.'
                                ;
                    type uint32 {
                      range 1..65535 ;
                    }
                  }
                  leaf route-map {
                    description 'Apply route-map to redistribute.'
                                ;
                    type string {
                      length 1..200 ;
                    }
                  }
                  leaf route-policy {
                    description 'Apply route-policy to redistribute.'
                                ;
                    type string {
                      length 1..200 ;
                    }
                    ncd:revise-date 2020-10-10 ;
                  }
                  container set-metric {
                    description 'Set route metric.'
                                ;
                    leaf metric {
                      description 'Set route metric.'
                                  ;
                      type uint32 {
                        range 0..4294967295 ;
                      }
                    }
                  }
                }
              }
            }
            container rib-only {
              description 'BGP routes are not delivered to the IP routing table.'
                          ;
              presence 'BGP routes are not delivered to the IP routing table'
                       ;
              leaf rib-only-set {
                description 'Enable rib-only.'
                            ;
                type empty ;
                mandatory true ;
              }
              leaf rib-only-routemap {
                description 'Routing policy.'
                            ;
                type string {
                  length 1..200 ;
                }
              }
              leaf rib-only-routepolicy {
                description 'Routing policy.'
                            ;
                type string {
                  length 1..200 ;
                }
                ncd:revise-date 2020-10-10 ;
              }
            }
            container track-v6-uni {
              description 'Event tracking.'
                          ;
              presence track-v6-uni ;
              container track-adjust-type-with-interface {
                description 'Configure adjust-priority of track object with int'
                          + 'erface.'
                            ;
                list track-adjust-with-interface {
                  description 'Configure adjust-priority of track object with i'
                            + 'nterface.'
                              ;
                  key 'track-name track-interface'
                      ;
                  leaf track-name {
                    description 'Name of track object (1-31 characters).'
                                ;
                    type string {
                      length 1..31 ;
                    }
                  }
                  leaf track-interface {
                    description 'Source of track object.'
                                ;
                    type ncd:ifname {
                      length 1..31 ;
                    }
                  }
                  leaf adjust-value {
                    description 'Value of adjust-priority.'
                                ;
                    type uint32 {
                      range 1..100 ;
                    }
                    mandatory true ;
                  }
                }
              }
              container track-adjust-type-without-interface {
                description 'Configure adjust-priority of track object without '
                          + 'interface.'
                            ;
                list track-adjust-without-interface {
                  description 'Configure adjust-priority of track object withou'
                            + 't interface.'
                              ;
                  max-elements 1 ;
                  key track-name ;
                  leaf track-name {
                    description 'Name of track object (1-31 characters).'
                                ;
                    type string {
                      length 1..31 ;
                    }
                  }
                  leaf adjust-value {
                    description 'Value of adjust-priority.'
                                ;
                    type uint32 {
                      range 1..100 ;
                    }
                    mandatory true ;
                  }
                }
              }
            }
            container additional-paths {
              description 'Additional paths in the BGP table.'
                          ;
              leaf selection-route-map {
                description 'Selection criteria to pick the additional paths.'
                            ;
                type string {
                  length 1..200 ;
                }
              }
            }
            container route-scan-time {
              description 'Adjust BGP route scan.'
                          ;
              presence 'The ability of BGP route scan.'
                       ;
              leaf interval-wait {
                description 'The interval of scan waiting. Default value is 500.'
                            ;
                type uint32 {
                  range 1..65535 ;
                }
                units ms ;
                mandatory true ;
              }
              leaf initial {
                description 'The initialization time of scan. Default value is '
                          + '50.'
                            ;
                type uint32 {
                  range 1..65535 ;
                }
                units ms ;
                mandatory true ;
              }
              leaf max-wait {
                description 'The max waiting time of scan. Default value is 500'
                          + '0.'
                            ;
                type uint32 {
                  range 1..65535 ;
                }
                units ms ;
                mandatory true ;
              }
            }
            leaf urpf-id-download {
              if-feature urpf ;
              description 'Download URPF-ID information to RTM.'
                          ;
              type empty ;
              ncd:revise-date 2017-11-16 ;
            }
            leaf bestpath-bgp-lu-nexthop-compare {
              description 'Compare nexthop that rely on BGP-LU path in bestpath'
                        + ' selection'
                          ;
              type enumeration {
                enum enable {
                  value 1 ;
                  description 'Enable this function'
                              ;
                }
                enum disable {
                  value 0 ;
                  description 'Disable this function'
                              ;
                }
              }
              default disable ;
              ncd:revise-date 2018-04-08 ;
            }
            container group-to-group {
              description 'Configure filter group to filter group route reflect'
                        + 'ion.'
                          ;
              presence group-to-group ;
              leaf reflection {
                description 'Reflection of routes is allowed.'
                            ;
                type empty ;
                mandatory true ;
              }
              leaf next-hop-self {
                description 'Disable the next hop calculation.'
                            ;
                type empty ;
              }
              ncd:revise-date 2018-08-04 ;
            }
            leaf entropy-label {
              description 'entropy-label enable or disable'
                          ;
              type enumeration {
                enum disable {
                  value 0 ;
                }
                enum enable {
                  value 1 ;
                }
              }
              ncd:revise-date 2019-02-21 ;
            }
            leaf additional-paths-send-igp-path {
              description 'Send neighbor NLRI with igp-path of additional-paths.'
                          ;
              type empty ;
              ncd:revise-date 2019-07-01 ;
            }
            leaf additional-paths-different-color {
              description 'Set different colors of additional-paths.'
                          ;
              type empty ;
              ncd:revise-date 2019-07-01 ;
            }
            leaf link-bandwidth-download {
              description 'Download link-bandwidth information to RTM.'
                          ;
              type empty ;
              ncd:revise-date 2019-10-22 ;
            }
            leaf sr-lsr {
              description 'Enable or disable BGP segment routing lable switch r'
                        + 'outer'
                          ;
              type enumeration {
                enum disable {
                  value 0 ;
                }
                enum enable {
                  value 1 ;
                }
              }
              default disable ;
              ncd:revise-date 2020-02-13 ;
            }
            leaf slow-peer-detection {
              description 'Set slow peer detection.'
                          ;
              type enumeration {
                enum disable {
                  value 0 ;
                  description 'Disable slow peer detection'
                              ;
                }
                enum enable {
                  value 1 ;
                  description 'Enable slow peer detection'
                              ;
                }
              }
              default disable ;
              ncd:revise-date 2020-09-08 ;
            }
            leaf slow-peer-detection-threshold {
              description 'Set threshold time for slow peer.Default value is 30'
                        + '0.'
                          ;
              type uint32 {
                range 120..3600 {
                  description 'Threshold time range.'
                              ;
                }
              }
              units s ;
              default 300 ;
              ncd:revise-date 2020-09-08 ;
            }
            leaf slow-peer-detection-recover {
              description 'Set recover time for slow peer.Default value is 300.'
                          ;
              type uint32 {
                range 120..3600 {
                  description 'Recover time range.'
                              ;
                }
              }
              units s ;
              default 300 ;
              ncd:revise-date 2020-09-08 ;
            }
            leaf download-community {
              description 'The maximum number of communities for one route.'
                          ;
              type uint8 {
                range 1..255 ;
              }
              ncd:revise-date 2020-10-10 ;
            }
            leaf nexthop-recursive-lookup-srv6-sid {
              description 'Enable or disable bgp nexthop recursive-lookup srv6-'
                        + 'sid'
                          ;
              type enumeration {
                enum disable {
                  value 0 ;
                }
                enum enable {
                  value 1 ;
                }
              }
              default disable ;
              ncd:revise-date 2020-10-28 ;
            }
            leaf bestpath-rpki-validation {
              description 'Compare RPKI state in bestpath selection.'
                          ;
              type empty ;
              ncd:revise-date 2020-12-20 ;
            }
            ncd:revise-date 2016-01-06 ;
          }
          container address-family-ipv6-vrf {
            description 'Specify parameters for IPv6 VRF.'
                        ;
            list address-family-vrf {
              description 'Specify parameters for VRF.'
                          ;
              key vrf-name ;
              leaf vrf-name {
                description 'VPN Routing/Forwarding instance name.'
                            ;
                type string {
                  length 1..32 ;
                }
              }
              leaf maximum-paths-ibgp {
                description 'Set IBGP-multipath.'
                            ;
                type uint32 {
                  range 1..32 ;
                }
                default 1 ;
              }
              leaf maximum-paths-ebgp {
                description 'Set EBGP-multipath.'
                            ;
                type uint32 {
                  range 1..32 ;
                }
                default 1 ;
              }
              leaf maximum-paths-eibgp {
                description 'Set EIBGP-multipath. Mutex with maximum-paths-ibgp'
                          + ' and maximum-paths-ebgp.'
                            ;
                type uint32 {
                  range 1..32 ;
                }
                default 1 ;
              }
              leaf router-id-addr {
                description 'Manually configured router identifier.'
                            ;
                type ncd:ipv4-address {
                  pattern '([1-9][0-9]*\.[1-9][0-9]*\.[1-9][0-9]*\.[1-9][0-9]*)'
                        + '|([1-9][0-9]*\.0\.0\.0)|(0\.[1-9][0-9]*\.0\.0)|(0\.0'
                        + '\.[1-9][0-9]*\.0)|(0\.0\.0\.[1-9][0-9]*)|([1-9][0-9]'
                        + '*\.[1-9][0-9]*\.0\.0)|(0\.[1-9][0-9]*\.[1-9][0-9]*\.'
                        + '0)|(0\.0\.[1-9][0-9]*\.[1-9][0-9]*)|([1-9][0-9]*\.0\.'
                        + '0\.[1-9][0-9]*)|(0\.[1-9][0-9]*\.0\.[1-9][0-9]*)|([1'
                        + '-9][0-9]*\.0\.[1-9][0-9]*\.0)|([1-9][0-9]*\.[1-9][0-'
                        + '9]*\.[1-9][0-9]*\.0)|([1-9][0-9]*\.[1-9][0-9]*\.0\.['
                        + '1-9][0-9]*)|([1-9][0-9]*\.0\.[1-9][0-9]*\.[1-9][0-9]'
                        + '*)|(0\.[1-9][0-9]*\.[1-9][0-9]*\.[1-9][0-9]*)'
                          ;
                }
              }
              leaf default-information-originate {
                description 'Notify default route.'
                            ;
                type empty ;
              }
              leaf default-metric {
                description 'Set metric of BGP routes without MED.'
                            ;
                type uint32 {
                  range 0..4294967295 ;
                }
                default 0 ;
              }
              leaf distance-bgp-external {
                description 'Distance for routes external to the AS.'
                            ;
                type uint32 {
                  range 1..255 ;
                }
                default 20 ;
              }
              leaf distance-bgp-internal {
                description 'Distance for routes internal to the AS.'
                            ;
                type uint32 {
                  range 1..255 ;
                }
                default 200 ;
              }
              leaf distance-bgp-local {
                description 'Distance for BGP local routes.'
                            ;
                type uint32 {
                  range 1..255 ;
                }
                default 254 ;
                ncd:revise-date 2016-05-10 ;
              }
              leaf distance-route-map {
                description 'Define distance by route-map.This node has higher '
                          + 'priority than distance-bgp-internal,distance-bgp-e'
                          + 'xternal and distance-bgp-local.'
                            ;
                type string {
                  length 1..200 ;
                }
                ncd:revise-date 2020-09-08 ;
              }
              leaf distance-route-policy {
                description 'Define distance by route-policy.This node has high'
                          + 'er priority than distance-bgp-internal,distance-bg'
                          + 'p-external and distance-bgp-local.'
                            ;
                type string {
                  length 1..200 ;
                }
                ncd:revise-date 2020-10-10 ;
              }
              leaf import-best-path {
                description 'Maximum number of paths that can be imported into '
                          + 'the VRF.'
                            ;
                type uint32 {
                  range 1..32 ;
                }
              }
              leaf table-map {
                description 'Map external entry attributes into routing table.'
                            ;
                type string {
                  length 1..200 ;
                }
              }
              leaf frr-capability {
                description 'Enable FRR capability.'
                            ;
                type empty ;
              }
              leaf frr-wtr {
                description 'Set the WTR time.'
                            ;
                type int32 {
                  range 1..12 ;
                }
                units min ;
              }
              leaf frr-enhanced {
                description 'If there is no BGP route as a backup route, then c'
                          + 'hoose the default route for FRR.'
                            ;
                type empty ;
              }
              leaf rpki-validation {
                status obsolete {
                  ncd:revise-date 2018-06-11 ;
                }
                description 'Set the BGP origin-AS validation parameters.'
                            ;
                type disable-or-enable-type ;
                default enable ;
              }
              leaf nexthop-recursive-default-route {
                description 'Nexthop recursive lookup default-route.'
                            ;
                type enumeration {
                  enum enable {
                    value 1 ;
                  }
                  enum disable {
                    value 0 ;
                  }
                }
                default enable ;
                ncd:revise-date 2020-07-28 ;
              }
              leaf nexthop-recursive-null1 {
                description 'Nexthop recursive lookup null1.'
                            ;
                type enumeration {
                  enum enable {
                    value 1 ;
                  }
                  enum disable {
                    value 0 ;
                  }
                }
                default enable ;
                ncd:revise-date 2020-12-09 ;
              }
              leaf bgp-attr-set {
                description 'Receive or/and send ATTR-SET attribute.'
                            ;
                type enumeration {
                  enum both {
                    value 1 ;
                    description 'Receive and send ATTR-SET attribute.'
                                ;
                  }
                  enum receive {
                    value 2 ;
                    description 'Receive ATTR-SET attribute.'
                                ;
                  }
                  enum send {
                    value 3 ;
                    description 'Send ATTR-SET attribute.'
                                ;
                  }
                }
                ncd:revise-date 2021-04-21 ;
              }
              container redistribute-v6-vrf {
                description 'Redistribute information from another routing prot'
                          + 'ocol.'
                            ;
                presence redistribute-v6-vrf ;
                container redistribute-vrf {
                  description 'Redistribute information from another routing pr'
                            + 'otocol.'
                              ;
                  list redistribute {
                    description 'Redistribute information from another routing '
                              + 'protocol.'
                                ;
                    key protocol ;
                    leaf protocol {
                      description 'Routing protocol type.'
                                  ;
                      type enumeration {
                        enum connected {
                          value 1 ;
                          description 'Connected routes.'
                                      ;
                        }
                        enum static {
                          value 2 ;
                          description 'Static routes.'
                                      ;
                        }
                        enum rip {
                          value 3 ;
                          description 'Routing information protocol(RIP).'
                                      ;
                        }
                        enum ps-busi-addr {
                          value 10 ;
                          description 'Ps-busi-addr routes.'
                                      ;
                        }
                        enum ps-user-addr {
                          value 11 ;
                          description 'Ps-user-addr routes.'
                                      ;
                        }
                        enum subscriber-host {
                          value 14 ;
                          description "Bras subscriber's host routes."
                                      ;
                        }
                        enum subscriber-aggregation {
                          value 15 ;
                          description "Bras subscriber's aggregation routes."
                                      ;
                        }
                        enum user-special {
                          value 17 ;
                          description 'User-special routes.'
                                      ;
                        }
                        enum sf-nat64 {
                          value 19 ;
                          description 'Stateful NAT64 routes.'
                                      ;
                        }
                        enum sl-nat64-ipv6 {
                          value 20 ;
                          description 'Stateless NAT64 prefix.'
                                      ;
                        }
                        enum aftr {
                          value 21 ;
                          description 'AFTR routes.'
                                      ;
                        }
                        enum nd-host {
                          value 22 ;
                          description 'ND-HOST routes.'
                                      ;
                        }
                        enum dhcp-pd {
                          value 23 ;
                          description 'DHCP-PD routes.'
                                      ;
                        }
                        enum bras-pool {
                          value 24 ;
                          description 'Broadband Remote Access Server pool rout'
                                    + 'es.'
                                      ;
                        }
                        enum hagp {
                          value 26 ;
                          description 'Hybrid access gateway protocol routes.'
                                      ;
                        }
                        enum dyn-leasedline {
                          value 29 ;
                          description 'Dynamic-leased-line routes assigned by A'
                                    + 'AA.'
                                      ;
                        }
                        enum address {
                          value 9 ;
                          description 'Address routes.'
                                      ;
                        }
                        enum nptv6 {
                          value 30 ;
                          description 'IPv6-to-IPv6 Network Prefix Translation '
                                    + 'routes.'
                                      ;
                        }
                      }
                    }
                    leaf route-map {
                      description 'Apply route-map to redistribute.'
                                  ;
                      type string {
                        length 1..200 ;
                      }
                    }
                    leaf route-policy {
                      description 'Apply route-policy to redistribute.'
                                  ;
                      type string {
                        length 1..200 ;
                      }
                      ncd:revise-date 2020-10-10 ;
                    }
                    container set-metric {
                      description 'Set route metric.'
                                  ;
                      leaf metric {
                        description 'Set route metric.'
                                    ;
                        type uint32 {
                          range 0..4294967295 ;
                        }
                      }
                    }
                  }
                }
                container redistribute-isis-vrf {
                  description 'Redistribute information from ISIS protocol.'
                              ;
                  list redistribute-isis {
                    description 'Redistribute information from ISIS protocol.'
                                ;
                    key 'protocol process-id'
                        ;
                    leaf protocol {
                      description 'Routing protocol type(ISIS-1,ISIS-2 or ISIS-'
                                + '1-2).'
                                  ;
                      type enumeration {
                        enum isis-1 {
                          value 4 ;
                          description 'IS-IS level-1 routes only.'
                                      ;
                        }
                        enum isis-2 {
                          value 5 ;
                          description 'IS-IS level-2 routes only.'
                                      ;
                        }
                      }
                    }
                    leaf process-id {
                      description 'ISIS process ID.'
                                  ;
                      type uint32 {
                        range 0..65535 ;
                      }
                    }
                    leaf route-map {
                      description 'Apply route-map to redistribute.'
                                  ;
                      type string {
                        length 1..200 ;
                      }
                    }
                    leaf route-policy {
                      description 'Apply route-policy to redistribute.'
                                  ;
                      type string {
                        length 1..200 ;
                      }
                      ncd:revise-date 2020-10-10 ;
                    }
                    container set-metric {
                      description 'Set route metric.'
                                  ;
                      leaf metric {
                        description 'Set route metric.'
                                    ;
                        type uint32 {
                          range 0..4294967295 ;
                        }
                      }
                    }
                  }
                }
                container redistribute-ospf-vrf {
                  description 'Redistribute information from OSPF protocol.'
                              ;
                  list redistribute-ospf {
                    description 'Redistribute information from OSPF protocol.'
                                ;
                    key 'protocol process-id'
                        ;
                    leaf protocol {
                      description 'Routing protocol type(OSPF-EXT or OSPF-INT).'
                                  ;
                      type enumeration {
                        enum ospf-ext {
                          value 7 ;
                          description 'Open shortest path first(OSPF) external '
                                    + 'routes.'
                                      ;
                        }
                        enum ospf-int {
                          value 8 ;
                          description 'Open shortest path first(OSPF) internal '
                                    + 'routes.'
                                      ;
                        }
                      }
                    }
                    leaf process-id {
                      description 'OSPF process ID.'
                                  ;
                      type uint32 {
                        range 1..65535 ;
                      }
                    }
                    leaf route-map {
                      description 'Apply route-map to redistribute.'
                                  ;
                      type string {
                        length 1..200 ;
                      }
                    }
                    leaf route-policy {
                      description 'Apply route-policy to redistribute.'
                                  ;
                      type string {
                        length 1..200 ;
                      }
                      ncd:revise-date 2020-10-10 ;
                    }
                    container set-metric {
                      description 'Set route metric.'
                                  ;
                      leaf metric {
                        description 'Set route metric.'
                                    ;
                        type uint32 {
                          range 0..4294967295 ;
                        }
                      }
                    }
                  }
                }
              }
              container network-v6-vrf {
                description 'Specify a network to announce via BGP.'
                            ;
                presence network-v6-vrf ;
                list network {
                  description 'Specify a network to announce via BGP.'
                              ;
                  key 'ipv6-address ipv6-mask-len'
                      ;
                  leaf ipv6-address {
                    description 'Network prefix.'
                                ;
                    type ncd:ipv6-address ;
                  }
                  leaf ipv6-mask-len {
                    description 'Network mask length.'
                                ;
                    type uint8 {
                      range 0..128 ;
                    }
                  }
                  leaf route-map {
                    description 'Route-map to modify the attributes.'
                                ;
                    type string {
                      length 1..200 ;
                    }
                  }
                  leaf route-policy {
                    description 'Route-policy to modify the attributes.'
                                ;
                    type string {
                      length 1..200 ;
                    }
                    ncd:revise-date 2020-10-10 ;
                  }
                }
              }
              container damp-v6-vrf {
                description 'Enable BGP route-flap dampening.'
                            ;
                presence damp-v6-vrf ;
                choice dampening {
                  description 'Enable BGP route-flap dampening.'
                              ;
                  case route-map {
                    description 'Route-map to specify criteria for dampening.'
                                ;
                    leaf route-map-name {
                      description 'Route-map to specify criteria for dampening.'
                                  ;
                      type string {
                        length 1..200 ;
                      }
                    }
                    leaf route-policy-name {
                      description 'Route-policy to specify criteria for dampeni'
                                + 'ng.'
                                  ;
                      type string {
                        length 1..200 ;
                      }
                      ncd:revise-date 2020-10-10 ;
                    }
                  }
                  case parameter {
                    description 'Damp parameter.'
                                ;
                    leaf half-time {
                      description 'Half-life time for the penalty.'
                                  ;
                      type uint32 {
                        range 1..45 ;
                      }
                      units min ;
                      mandatory true ;
                    }
                    leaf reuse {
                      description 'Value to start reusing a route.'
                                  ;
                      type uint32 {
                        range 1..20000 ;
                      }
                      mandatory true ;
                    }
                    leaf suppress {
                      description 'Value to start suppressing a route.'
                                  ;
                      type uint32 {
                        range 1..20000 ;
                      }
                      mandatory true ;
                    }
                    leaf max-suppress-time {
                      description 'Maximum duration to suppress a route.'
                                  ;
                      type uint32 {
                        range 1..255 ;
                      }
                      units min ;
                      mandatory true ;
                    }
                  }
                }
              }
              container aggregate-v6-vrf {
                description 'Configure BGP aggregate entries.'
                            ;
                presence aggregate-v6-vrf ;
                list aggregate {
                  description 'Configure BGP aggregate entries.'
                              ;
                  key 'ipv6-address ipv6-mask-len'
                      ;
                  leaf ipv6-address {
                    description 'Aggregate address.'
                                ;
                    type ncd:ipv6-address ;
                  }
                  leaf ipv6-mask-len {
                    description 'Aggregate mask length.'
                                ;
                    type uint8 {
                      range 0..128 ;
                    }
                  }
                  leaf as-set {
                    description 'Generate AS set path information.'
                                ;
                    type empty ;
                  }
                  leaf strict {
                    description 'Strict condition.'
                                ;
                    type empty ;
                  }
                  leaf summary-only {
                    description 'Filter more specific routes from updates.'
                                ;
                    type empty ;
                  }
                  leaf attribute-map {
                    status obsolete {
                      ncd:revise-date 2018-07-21 ;
                    }
                    description 'Attribute map name.'
                                ;
                    type string {
                      length 1..200 ;
                    }
                  }
                  leaf suppress-map {
                    status obsolete {
                      ncd:revise-date 2018-07-21 ;
                    }
                    description 'Suppress map name.'
                                ;
                    type string {
                      length 1..200 ;
                    }
                  }
                  choice agg-policy {
                    description 'Apply policy to aggregate route.'
                                ;
                    case agg-policy-choice-clear {
                      description 'Remove value of any entities which belong to'
                                + ' any case within this choice.'
                                  ;
                      container agg-policy-all-clear {
                        description 'Remove this entitiy means to remove value '
                                  + 'of any entities which belong to any case w'
                                  + 'ithin this choice.'
                                    ;
                        presence clear-agg-policy ;
                      }
                      ncd:revise-date 2020-11-11 ;
                    }
                    case route-map {
                      description 'Apply route map to aggregate route.'
                                  ;
                      leaf attr-map {
                        description 'Attribute map name.'
                                    ;
                        type string {
                          length 1..200 ;
                        }
                      }
                      leaf supp-map {
                        description 'Suppress map name.'
                                    ;
                        type string {
                          length 1..200 ;
                        }
                      }
                      leaf orig-map {
                        description 'Origin map name.'
                                    ;
                        type string {
                          length 1..200 ;
                        }
                        ncd:revise-date 2019-08-19 ;
                      }
                    }
                    case route-policy {
                      description 'Apply route-policy to aggregate route.'
                                  ;
                      leaf policy {
                        description 'Route-policy name.'
                                    ;
                        type string {
                          length 1..200 ;
                        }
                      }
                    }
                    ncd:revise-date 2018-07-21 ;
                  }
                }
              }
              container track-v6-vrf {
                description 'Event tracking.'
                            ;
                presence track-v6-vrf ;
                container track-adjust-type-with-interface {
                  description 'Configure adjust-priority of track object with i'
                            + 'nterface.'
                              ;
                  list track-adjust-with-interface {
                    description 'Configure adjust-priority of track object with'
                              + ' interface.'
                                ;
                    key 'track-name track-interface'
                        ;
                    leaf track-name {
                      description 'Name of track object (1-31 characters).'
                                  ;
                      type string {
                        length 1..31 ;
                      }
                    }
                    leaf track-interface {
                      description 'Source of track object.'
                                  ;
                      type ncd:ifname {
                        length 1..31 ;
                      }
                    }
                    leaf adjust-value {
                      description 'Value of adjust-priority.'
                                  ;
                      type uint32 {
                        range 1..100 ;
                      }
                      mandatory true ;
                    }
                  }
                }
                container track-adjust-type-without-interface {
                  description 'Configure adjust-priority of track object withou'
                            + 't interface.'
                              ;
                  list track-adjust-without-interface {
                    description 'Configure adjust-priority of track object with'
                              + 'out interface.'
                                ;
                    max-elements 1 ;
                    key track-name ;
                    leaf track-name {
                      description 'Name of track object (1-31 characters).'
                                  ;
                      type string {
                        length 1..31 ;
                      }
                    }
                    leaf adjust-value {
                      description 'Value of adjust-priority.'
                                  ;
                      type uint32 {
                        range 1..100 ;
                      }
                      mandatory true ;
                    }
                  }
                }
              }
              container neighbor-v6-vrf {
                description 'Specify a neighbor.'
                            ;
                presence neighbor-v6-vrf ;
                container neighbor-group {
                  description 'Specify a peergroup neighbor.'
                              ;
                  list neighbor-peergroup {
                    description 'Specify a neighbor.'
                                ;
                    key neighbor-group ;
                    leaf neighbor-group {
                      description 'Peer group name (1-31 characters).'
                                  ;
                      type string {
                        length 1..31 ;
                      }
                    }
                    leaf remote-as {
                      description 'Specify a BGP neighbor AS number.'
                                  ;
                      type ncd:asn-dot ;
                    }
                    leaf activate {
                      description 'Enable the address family for this neighbor.'
                                  ;
                      type enumeration {
                        enum disable {
                          value 0 ;
                        }
                        enum enable {
                          value 1 ;
                        }
                      }
                    }
                    leaf monitor {
                      description 'Config BMP monitor for the address family of'
                                + ' this neighbor.'
                                  ;
                      type enumeration {
                        enum disable {
                          value 2 ;
                        }
                        enum enable {
                          value 1 ;
                        }
                        enum inherit-global-config {
                          value 0 ;
                        }
                      }
                      ncd:revise-date 2019-07-29 ;
                    }
                    leaf advertisement-interval {
                      description 'Minimum interval between sending BGP routing'
                                + ' which is not locally originated updates.'
                                  ;
                      type uint32 {
                        range 1..65535 ;
                      }
                      units s ;
                    }
                    leaf advertise-maximum-prefix {
                      description 'Maximum number of prefix send to this peer.'
                                  ;
                      type uint32 {
                        range 1..4294967295 ;
                      }
                    }
                    leaf allowas-in {
                      description 'Accept as-path with my AS present in it.'
                                  ;
                      type uint32 {
                        range 1..10 ;
                      }
                    }
                    leaf as-override {
                      description 'Override matching AS-number while sending up'
                                + 'date.'
                                  ;
                      type empty ;
                    }
                    leaf as-path-loopcheck {
                      description 'Check as-path sending BGP routing to EBGP ne'
                                + 'ighbor.'
                                  ;
                      type empty ;
                    }
                    leaf connect-retry-interval {
                      description 'Set data of connect-retry timer for this nei'
                                + 'ghbor.'
                                  ;
                      type uint32 {
                        range 1..65535 ;
                      }
                      units s ;
                    }
                    leaf default-originate {
                      description 'Originate default route to this neighbor.'
                                  ;
                      type empty ;
                    }
                    leaf default-originate-routemap {
                      description 'Map external entry attributes into routing t'
                                + 'able.'
                                  ;
                      type string {
                        length 1..200 ;
                      }
                      ncd:revise-date 2020-07-28 ;
                    }
                    leaf default-originate-routepolicy {
                      description 'Set external entry attributes into routing t'
                                + 'able.'
                                  ;
                      type string {
                        length 1..200 ;
                      }
                      ncd:revise-date 2020-10-10 ;
                    }
                    leaf description {
                      description 'Neighbor specific description.'
                                  ;
                      type ncd:string-with-blank {
                        length 1..80 ;
                      }
                    }
                    leaf dscp {
                      description 'Set DSCP value.'
                                  ;
                      type uint8 {
                        range 0..63 ;
                      }
                    }
                    container fall-over {
                      description 'Set BFD supporting for fallover.'
                                  ;
                      presence 'Enable BFD support for fallover'
                               ;
                      leaf bfd {
                        description 'Enable BFD support for fallover.'
                                    ;
                        type empty ;
                        mandatory true ;
                      }
                      container bfd-parameters {
                        description 'The parameters of BFD.'
                                    ;
                        presence bfd-parameters ;
                        choice bfd-parameters {
                          description 'Config bfd parameters'
                                      ;
                          case template-name {
                            description 'Template name'
                                        ;
                            leaf template {
                              description 'BFD template name'
                                          ;
                              type string {
                                length 1..31 ;
                              }
                            }
                            ncd:revise-date 2020-03-31 ;
                          }
                          case parameters {
                            description Parameters ;
                            leaf interval {
                              description 'Minimum send interval.'
                                          ;
                              type uint32 {
                                range 10..990 ;
                              }
                              units ms ;
                              mandatory true ;
                            }
                            leaf min-rx {
                              description 'Minimum receive interval.'
                                          ;
                              type uint32 {
                                range 10..990 ;
                              }
                              units ms ;
                              mandatory true ;
                            }
                            leaf multiplier {
                              description Multiplier. ;
                              type uint8 {
                                range 3..50 ;
                              }
                              mandatory true ;
                            }
                          }
                        }
                      }
                      leaf bfd-hop {
                        description 'bfd optional hop'
                                    ;
                        type enumeration {
                          enum single-hop {
                            value 1 ;
                            description 'Set single-hop bfd'
                                        ;
                          }
                          enum multi-hop {
                            value 2 ;
                            description 'Set multi-hop bfd'
                                        ;
                          }
                        }
                        ncd:revise-date 2019-04-23 ;
                      }
                    }
                    leaf maxas-in {
                      description 'Accept as-path not exceeded maxas-in.'
                                  ;
                      type uint32 {
                        range 1..250 ;
                      }
                    }
                    leaf next-hop-self {
                      description 'Disable the next hop calculation for this ne'
                                + 'ighbor.'
                                  ;
                      type enumeration {
                        enum enable {
                          value 1 ;
                          description 'Apply next-hop-self for EBGP route.'
                                      ;
                        }
                        enum all {
                          value 2 ;
                          description 'Apply next-hop-self for both EBGP and IB'
                                    + 'GP route.'
                                      ;
                        }
                      }
                    }
                    leaf originate-interval {
                      description 'Minimum interval between sending BGP routing'
                                + ' which is locally originated updates.'
                                  ;
                      type uint32 {
                        range 1..65535 ;
                      }
                      units s ;
                    }
                    leaf passive {
                      description "Don't send open messages to this neighbor ac"
                                + "tively."
                                  ;
                      type empty ;
                    }
                    leaf remove-private-as {
                      description 'EBGP use to remove private AS number.'
                                  ;
                      type enumeration {
                        enum disable {
                          value 0 ;
                        }
                        enum enable {
                          value 1 ;
                        }
                      }
                    }
                    leaf send-community {
                      description 'Send community to this neighbor.'
                                  ;
                      type empty ;
                    }
                    leaf send-large-community {
                      description 'Send Large-community to this neighbor.'
                                  ;
                      type empty ;
                      ncd:revise-date 2020-04-16 ;
                    }
                    leaf route-reflector-client {
                      description 'Set this neighbor as a client peer.'
                                  ;
                      type empty ;
                      ncd:revise-date 2019-08-19 ;
                    }
                    leaf send-med {
                      description 'Send metric attribute to this neighbor.'
                                  ;
                      type empty ;
                    }
                    leaf inherit-igp-metric {
                      description 'Med attribute inherited from IGP metric befo'
                                + 're sending updates.'
                                  ;
                      type empty ;
                      ncd:revise-date 2017-07-25 ;
                    }
                    leaf shut-down {
                      status obsolete {
                        ncd:revise-date 2016-06-12 ;
                      }
                      description 'Administratively shut down this neighbor.'
                                  ;
                      type empty ;
                    }
                    leaf soft-reconfiguration {
                      status obsolete {
                        ncd:revise-date 2018-01-31 ;
                      }
                      description 'Neighbor soft reconfiguration.'
                                  ;
                      type empty ;
                    }
                    leaf soft-reconfig {
                      description 'Neighbor soft reconfiguration.'
                                  ;
                      type enumeration {
                        enum soft-reconfiguration {
                          value 1 ;
                          description Soft-reconfiguration. ;
                        }
                        enum enforce-soft-reconfiguration {
                          value 2 ;
                          description 'Enforce soft-reconfiguration instead of '
                                    + 'sending route-refresh.'
                                      ;
                        }
                      }
                      ncd:revise-date 2018-01-31 ;
                    }
                    leaf soo {
                      description 'Site-of-Origin extended community.'
                                  ;
                      type union {
                        type ncd:asn-nn ;
                        type ncd:asnd-nn ;
                        type ncd:ipadd-nn ;
                      }
                    }
                    leaf split-update-group {
                      description 'Split neighbor from update group.'
                                  ;
                      type empty ;
                    }
                    leaf update-source {
                      status obsolete {
                        ncd:revise-date 2018-11-27 ;
                      }
                      description 'Source of routing updates.'
                                  ;
                      type ncd:ifname {
                        length 1..31 ;
                      }
                    }
                    leaf weight {
                      description 'Set weight for routes from this neighbor.'
                                  ;
                      type uint32 {
                        range 1..65535 ;
                      }
                    }
                    leaf aigp {
                      description 'Enable AIGP for this neighbor.'
                                  ;
                      type empty ;
                      ncd:revise-date 2017-11-01 ;
                    }
                    leaf send-label {
                      description 'Send NLRI with MPLS label to this neighbor.'
                                  ;
                      type empty ;
                      ncd:revise-date 2018-11-06 ;
                    }
                    container set-ttl {
                      description 'ebgp-multihop-ttl and ttl-security-hops are '
                                + 'mutex.'
                                  ;
                      choice set-ttl {
                        description 'ebgp-multihop-ttl and ttl-security-hops ar'
                                  + 'e mutex.'
                                    ;
                        case ebgp-multihop-ttl {
                          description 'Allow EBGP neighbors not on directly con'
                                    + 'nected net.'
                                      ;
                          leaf ebgp-multihop {
                            description 'Allow EBGP neighbors not on directly connected net.'
                                        ;
                            type uint8 {
                              range 1..255 ;
                            }
                          }
                        }
                        case ttl-security-hops {
                          description 'Enable EBGP TTL security check.'
                                      ;
                          leaf ttl-security-hops {
                            description 'Enable EBGP TTL security check.'
                                        ;
                            type uint8 {
                              range 1..254 ;
                            }
                          }
                        }
                      }
                    }
                    container neighbor-extend {
                      description 'Specify a neighbor.'
                                  ;
                      container local-as {
                        description 'Specify a local-as number.'
                                    ;
                        presence local-as ;
                        leaf as-number {
                          description 'Autonomous system number (normal or 4 Oc'
                                    + 'tets).'
                                      ;
                          type ncd:asn-dot {
                            pattern '-?([1-9]+(\.(\d*)|0)?)|(0(\.\d+){1})'
                                    ;
                          }
                          mandatory true ;
                        }
                        leaf no-prepend {
                          description 'Do not prepend local-as to updates from '
                                    + 'EBGP peer.'
                                      ;
                          type empty ;
                        }
                        leaf replace-as {
                          description 'Replace real AS with local AS in the EBG'
                                    + 'P updates.'
                                      ;
                          type empty ;
                        }
                        leaf dual-as {
                          description 'Accept real AS or local AS from the EBGP'
                                    + ' peer.'
                                      ;
                          type empty ;
                        }
                      }
                      container password {
                        description 'Set a password of the neighbor.'
                                    ;
                        choice password {
                          description 'Set a password of the neighbor.'
                                      ;
                          case clear-words {
                            description 'Specify the clear password (1-80 characters).'
                                        ;
                            leaf clear-words {
                              description 'The clear password (1-80 characters).'
                                          ;
                              type string {
                                length 1..80 ;
                              }
                            }
                          }
                          case encrypt-words {
                            description 'Specify the encrypted password.'
                                        ;
                            leaf encrypt-words {
                              description 'Specify the encrypted password.'
                                          ;
                              type string {
                                length 64..172 ;
                              }
                            }
                          }
                        }
                      }
                      leaf prefix-list-in-name {
                        description 'Apply prefix list to incoming routes.'
                                    ;
                        type string {
                          length 1..169 ;
                        }
                      }
                      leaf prefix-list-out-name {
                        description 'Apply  prefix list to outbound routes.'
                                    ;
                        type string {
                          length 1..169 ;
                        }
                      }
                      leaf route-map-in-name {
                        description 'Apply route-map to incoming routes.'
                                    ;
                        type string {
                          length 1..200 ;
                        }
                      }
                      leaf route-map-out-name {
                        description 'Apply route-map to outbound routes.'
                                    ;
                        type string {
                          length 1..200 ;
                        }
                      }
                      container maximum-prefix {
                        description 'The action that generated when threshold v'
                                  + 'alue reached.'
                                    ;
                        presence 'The action that generated when threshold valu'
                               + 'e reached'
                                 ;
                        leaf maximum-prefix-number {
                          description 'Maximum number of prefix limit.'
                                      ;
                          type uint32 {
                            range 1..4294967295 ;
                          }
                          mandatory true ;
                        }
                        leaf maximum-prefix-threshold {
                          description 'Threshold value(%) at which to generate '
                                    + 'a warning.'
                                      ;
                          type uint32 {
                            range 1..100 ;
                          }
                          mandatory true ;
                        }
                        choice maximum-prefix-action {
                          description 'The action that generated when threshold'
                                    + ' value reached.'
                                      ;
                          mandatory true ;
                          case peer-action {
                            description 'The action that generated when threshold value reached.'
                                        ;
                            leaf action {
                              description 'The action that generated when threshold value reached.'
                                          ;
                              type enumeration {
                                enum down {
                                  value 0 ;
                                  description 'Break down BGP connection after limit is exceeded.'
                                              ;
                                }
                                enum warning-only {
                                  value 1 ;
                                  description 'Only give warning message when limit is exceeded.'
                                              ;
                                }
                                enum drop-routes {
                                  value 2 ;
                                  description 'Drop routes that exceed the maximum-prefix.'
                                              ;
                                }
                              }
                              mandatory true ;
                            }
                          }
                          case restart {
                            description 'Restart BGP connection after limit is exceeded.'
                                        ;
                            leaf restart-time {
                              description 'Restart interval in minutes.'
                                          ;
                              type uint32 {
                                range 1..30000 ;
                              }
                              units min ;
                              mandatory true ;
                            }
                          }
                        }
                      }
                      container timers {
                        description 'BGP per neighbor timers.'
                                    ;
                        presence timers ;
                        leaf keepalive {
                          description 'Adjust keepalive interval.'
                                      ;
                          type uint32 {
                            range 0..65535 ;
                          }
                          units s ;
                          mandatory true ;
                        }
                        leaf holdtime {
                          description 'Adjust holdtime.'
                                      ;
                          type uint32 {
                            range '0 | 3..65535'
                                  ;
                          }
                          units s ;
                          mandatory true ;
                        }
                      }
                      leaf routepolicy-in-name {
                        description 'Route policy name applied to the inbound r'
                                  + 'outes.'
                                    ;
                        type string {
                          length 1..200 ;
                        }
                      }
                      leaf routepolicy-out-name {
                        description 'Route policy name applied to the outbound '
                                  + 'routes.'
                                    ;
                        type string {
                          length 1..200 ;
                        }
                      }
                      leaf keychain-name {
                        description 'Keychain name associated to peer for authe'
                                  + 'ntication.'
                                    ;
                        type string {
                          length 1..31 ;
                        }
                      }
                      container withdraw {
                        description 'Withdraw routes when state of track-group '
                                  + 'is down.'
                                    ;
                        presence withdraw ;
                        leaf track-group {
                          description 'Track-group name.'
                                      ;
                          type string {
                            length 1..31 ;
                          }
                          mandatory true ;
                        }
                        leaf route-map {
                          description 'Route-map name.'
                                      ;
                          type string {
                            length 1..200 ;
                          }
                        }
                        ncd:revise-date 2016-02-06 ;
                      }
                      container second-withdraw {
                        description 'Withdraw routes when state of the second t'
                                  + 'rack-group is down.'
                                    ;
                        presence second-withdraw ;
                        leaf track-group {
                          description 'Track-group name.'
                                      ;
                          type string {
                            length 1..31 ;
                          }
                          mandatory true ;
                        }
                        leaf route-map {
                          description 'Route-map name.'
                                      ;
                          type string {
                            length 1..200 ;
                          }
                        }
                        ncd:revise-date 2018-07-12 ;
                      }
                      container idle-hold-time {
                        description 'Specifiy the length of time the peer is he'
                                  + 'ld in the idle state.'
                                    ;
                        presence idle-hold-time ;
                        leaf hold-time {
                          description 'Idle hold time.'
                                      ;
                          type uint32 {
                            range 1..3000 ;
                          }
                          units s ;
                          mandatory true ;
                        }
                        leaf increase {
                          description 'Increase idle hold time doubly to maximu'
                                    + 'm 3000.'
                                      ;
                          type empty ;
                        }
                        ncd:revise-date 2016-03-23 ;
                      }
                      container tracking {
                        description 'Enable peer tracking.'
                                    ;
                        presence tracking ;
                        leaf tracking {
                          status obsolete {
                            ncd:revise-date 2019-01-15 ;
                          }
                          description 'Enable peer tracking.'
                                      ;
                          type empty ;
                          mandatory true ;
                        }
                        leaf tracking-ex {
                          description 'Peer tracking.'
                                      ;
                          type enumeration {
                            enum enable {
                              value 1 ;
                              description 'Enable peer tracking.'
                                          ;
                            }
                            enum disable {
                              value 0 ;
                              description 'Disable peer tracking.'
                                          ;
                            }
                          }
                          ncd:revise-date 2019-01-15 ;
                        }
                        leaf delay {
                          description 'Delay time to reset the session.'
                                      ;
                          type uint32 {
                            range 1..65535 ;
                          }
                          units s ;
                        }
                        ncd:revise-date 2018-08-29 ;
                      }
                      container transport {
                        description 'Specify TCP path MTU discovery or TCP MSS '
                                  + 'to this neighbor.'
                                    ;
                        choice transport {
                          description 'Specify TCP path MTU discovery or TCP MS'
                                    + 'S to this neighbor.'
                                      ;
                          case path-mtu-discovery {
                            description 'Use transport path MTU discovery.'
                                        ;
                            leaf path-mtu-discovery {
                              description 'Use transport path MTU discovery.'
                                          ;
                              type empty ;
                            }
                          }
                          case mss {
                            description 'Specify TCP MSS to this neighbor.'
                                        ;
                            leaf mss {
                              description 'Set TCP initial maximum segment size.'
                                          ;
                              type uint32 {
                                range 68..10000 ;
                              }
                            }
                          }
                        }
                        ncd:revise-date 2020-08-18 ;
                      }
                      leaf neighbor-stalepath-time {
                        description "Set the max time to hold on to restarting "
                                  + "peer's stale paths."
                                    ;
                        type uint32 {
                          range 1..604800 {
                            description 'Delay value.'
                                        ;
                          }
                        }
                        units s ;
                        ncd:revise-date 2021-02-01 ;
                      }
                      leaf neighbor-stalepath-time-permanent {
                        description 'Hold on stale paths permanently.'
                                    ;
                        type empty ;
                        ncd:revise-date 2021-02-01 ;
                      }
                    }
                    leaf open-delay {
                      description 'Delay to send open message.'
                                  ;
                      type uint32 {
                        range 1..240 ;
                      }
                      units s ;
                    }
                    container shutdown {
                      description 'Shut down this neighbor administratively or '
                                + 'when state of track-group is down.'
                                  ;
                      presence shut-down ;
                      leaf shut-down {
                        description 'Administratively shut down this neighbor.'
                                    ;
                        type empty ;
                        mandatory true ;
                      }
                      leaf track-group {
                        description 'Shut down this neighbor when state of trac'
                                  + 'k-group is down.'
                                    ;
                        type string {
                          length 1..31 ;
                        }
                      }
                      ncd:revise-date 2016-06-12 ;
                    }
                    container advertise-map-uni {
                      description 'Specify route-map for conditional advertisem'
                                + 'ent.'
                                  ;
                      presence 'Specify route-map for conditional advertisement'
                               ;
                      leaf advertise-map-name {
                        description 'Advertise route-map name.'
                                    ;
                        type string {
                          length 1..200 ;
                        }
                        mandatory true ;
                      }
                      choice advertise-map {
                        description 'Specify route-map for conditional advertis'
                                  + 'ement.'
                                    ;
                        mandatory true ;
                        case exist-map {
                          description 'Advertise prefix only if prefix exists.'
                                      ;
                          leaf exist-map-name {
                            description 'Advertise prefix only if prefix exists.'
                                        ;
                            type string {
                              length 1..200 ;
                            }
                            mandatory true ;
                          }
                        }
                        case nonexist-map {
                          description 'Advertise prefix only if prefix does not'
                                    + ' exist.'
                                      ;
                          leaf nonexist-map-name {
                            description 'Advertise prefix only if prefix does not exist.'
                                        ;
                            type string {
                              length 1..200 ;
                            }
                            mandatory true ;
                          }
                        }
                      }
                      ncd:revise-date 2016-11-15 ;
                    }
                    container route-filter-group {
                      description 'Specify a neighbor to join a route-filter-gr'
                                + 'oup.'
                                  ;
                      presence route-filter-group ;
                      leaf filter-group {
                        description 'Route filter group name (1-31 characters).'
                                    ;
                        type string {
                          length 1..31 ;
                        }
                        mandatory true ;
                      }
                      leaf next-hop-self {
                        description 'Disable the next hop calculation for this '
                                  + 'neighbor.'
                                    ;
                        type empty ;
                      }
                      ncd:revise-date 2017-06-12 ;
                    }
                    leaf enforce-first-as-disable {
                      description 'Not enforce the first AS for EBGP neighbor r'
                                + 'outes'
                                  ;
                      type empty ;
                      ncd:revise-date 2018-01-10 ;
                    }
                    leaf announce-sid {
                      description 'Enable Prefix-SID attribute for this neighbo'
                                + 'r.'
                                  ;
                      type enumeration {
                        enum enable {
                          value 1 ;
                          description 'Enable Prefix-SID attribute for this nei'
                                    + 'ghbor.'
                                      ;
                        }
                      }
                      ncd:revise-date 2018-05-14 ;
                    }
                    leaf enhanced-route-refresh-disable {
                      description 'Enhanced route refresh capability.'
                                  ;
                      type empty ;
                      ncd:revise-date 2018-10-23 ;
                    }
                    container update-source-ex {
                      description 'Specify the update-source configuration of t'
                                + 'he neighbor.'
                                  ;
                      presence 'Specify the update-source configuration of the '
                             + 'neighbor.'
                               ;
                      choice update-source {
                        description 'Specify the update-source configuration of'
                                  + ' the neighbor.'
                                    ;
                        case update-source-if {
                          description 'Specify the update-source interface name'
                                    + ' of the neighbor.'
                                      ;
                          leaf update-source-ifname {
                            description 'Specify the update-source interface name of the neighbor.'
                                        ;
                            type ncd:ifname ;
                          }
                        }
                        case update-source-ipv6 {
                          description 'Specify the update-source IPv6 address o'
                                    + 'f the neighbor.'
                                      ;
                          leaf update-source-addrv6 {
                            description 'Specify the update-source IPv6 address of the neighbor.'
                                        ;
                            type ncd:ipv6-address-none-zero ;
                          }
                          ncd:revise-date 2019-07-07 ;
                        }
                      }
                      ncd:revise-date 2018-11-27 ;
                    }
                    leaf four-byte-as-disable {
                      description 'Disable 4-byte AS capability.'
                                  ;
                      type empty ;
                      ncd:revise-date 2019-01-15 ;
                    }
                    leaf receive-single-label {
                      description 'Receive single label only for label unicast '
                                + 'route.'
                                  ;
                      type enumeration {
                        enum disable {
                          value 0 ;
                          description 'Disable receive single label only for la'
                                    + 'bel unicast route'
                                      ;
                        }
                        enum enable {
                          value 1 ;
                          description 'Enable receive single label only for lab'
                                    + 'el unicast route'
                                      ;
                        }
                      }
                      ncd:revise-date 2019-11-29 ;
                    }
                    leaf receive-single-label-compatible {
                      description 'Receive single label only for label unicast '
                                + 'route.The function is the same as receive-si'
                                + 'ngle-label node.'
                                  ;
                      type enumeration {
                        enum disable {
                          value 0 ;
                          description 'Disable receive single label only for la'
                                    + 'bel unicast route'
                                      ;
                        }
                        enum enable {
                          value 1 ;
                          description 'Enable receive single label only for lab'
                                    + 'el unicast route'
                                      ;
                        }
                      }
                      ncd:revise-date 2020-07-28 ;
                    }
                    leaf ignore-error-packet {
                      description 'Ignore error packet for this neighbor.'
                                  ;
                      type enumeration {
                        enum disable {
                          value 0 ;
                          description 'Disable peer ignore error packet'
                                      ;
                        }
                        enum enable {
                          value 1 ;
                          description 'Enable peer ignore error packet'
                                      ;
                        }
                      }
                      default disable ;
                      ncd:revise-date 2020-01-13 ;
                    }
                  }
                }
                container neighbor-ipv6 {
                  description 'Specify a IPv6 neighbor.'
                              ;
                  list neighbor {
                    description 'Specify a neighbor.'
                                ;
                    key ipv6-address ;
                    leaf ipv6-address {
                      description 'Neighbor IPv6 address.'
                                  ;
                      type ncd:ipv6-address ;
                    }
                    leaf remote-as {
                      description 'Specify a BGP neighbor AS number.'
                                  ;
                      type ncd:asn-dot ;
                    }
                    leaf join-peergroup {
                      description 'Create/Join a peer group(1-31 characters).'
                                  ;
                      type string {
                        length 1..31 ;
                      }
                    }
                    leaf activate {
                      description 'Enable the address family for this neighbor.'
                                  ;
                      type enumeration {
                        enum disable {
                          value 0 ;
                        }
                        enum enable {
                          value 1 ;
                        }
                      }
                    }
                    leaf monitor {
                      description 'Config BMP monitor for the address family of'
                                + ' this neighbor.'
                                  ;
                      type enumeration {
                        enum disable {
                          value 2 ;
                        }
                        enum enable {
                          value 1 ;
                        }
                        enum inherit-global-config {
                          value 0 ;
                        }
                      }
                      ncd:revise-date 2019-07-29 ;
                    }
                    leaf advertisement-interval {
                      description 'Minimum interval between sending BGP routing'
                                + ' which is not locally originated updates.'
                                  ;
                      type uint32 {
                        range 1..65535 ;
                      }
                      units s ;
                    }
                    leaf advertise-maximum-prefix {
                      description 'Maximum number of prefix send to this peer.'
                                  ;
                      type uint32 {
                        range 1..4294967295 ;
                      }
                    }
                    leaf allowas-in {
                      description 'Accept as-path with my AS present in it.'
                                  ;
                      type uint32 {
                        range 1..10 ;
                      }
                    }
                    leaf as-override {
                      description 'Override matching AS-number while sending up'
                                + 'date.'
                                  ;
                      type empty ;
                    }
                    leaf as-path-loopcheck {
                      description 'Check as-path sending BGP routing to EBGP ne'
                                + 'ighbor.'
                                  ;
                      type empty ;
                    }
                    leaf connect-retry-interval {
                      description 'Set data of connect-retry timer for this nei'
                                + 'ghbor.'
                                  ;
                      type uint32 {
                        range 1..65535 ;
                      }
                      units s ;
                    }
                    leaf default-originate {
                      description 'Originate default route to this neighbor.'
                                  ;
                      type empty ;
                    }
                    leaf default-originate-routemap {
                      description 'Map external entry attributes into routing t'
                                + 'able.'
                                  ;
                      type string {
                        length 1..200 ;
                      }
                      ncd:revise-date 2020-07-28 ;
                    }
                    leaf default-originate-routepolicy {
                      description 'Set external entry attributes into routing t'
                                + 'able.'
                                  ;
                      type string {
                        length 1..200 ;
                      }
                      ncd:revise-date 2020-10-10 ;
                    }
                    leaf description {
                      description 'Neighbor specific description.'
                                  ;
                      type ncd:string-with-blank {
                        length 1..80 ;
                      }
                    }
                    leaf dscp {
                      description 'Set DSCP value.'
                                  ;
                      type uint8 {
                        range 0..63 ;
                      }
                    }
                    container fall-over {
                      description 'Set BFD supporting for fallover.'
                                  ;
                      presence 'Set BFD supporting for fallover'
                               ;
                      leaf bfd {
                        description 'Enable BFD support for fallover.'
                                    ;
                        type empty ;
                        mandatory true ;
                      }
                      container bfd-parameters {
                        description 'The parameters of BFD.'
                                    ;
                        presence bfd-parameters ;
                        choice bfd-parameters {
                          description 'Config bfd parameters'
                                      ;
                          case template-name {
                            description 'Template name'
                                        ;
                            leaf template {
                              description 'BFD template name'
                                          ;
                              type string {
                                length 1..31 ;
                              }
                            }
                            ncd:revise-date 2020-03-31 ;
                          }
                          case parameters {
                            description Parameters ;
                            leaf interval {
                              description 'Minimum send interval.'
                                          ;
                              type uint32 {
                                range 10..990 ;
                              }
                              units ms ;
                              mandatory true ;
                            }
                            leaf min-rx {
                              description 'Minimum receive interval.'
                                          ;
                              type uint32 {
                                range 10..990 ;
                              }
                              units ms ;
                              mandatory true ;
                            }
                            leaf multiplier {
                              description Multiplier. ;
                              type uint8 {
                                range 3..50 ;
                              }
                              mandatory true ;
                            }
                          }
                        }
                      }
                      leaf bfd-hop {
                        description 'bfd optional hop'
                                    ;
                        type enumeration {
                          enum single-hop {
                            value 1 ;
                            description 'Set single-hop bfd'
                                        ;
                          }
                          enum multi-hop {
                            value 2 ;
                            description 'Set multi-hop bfd'
                                        ;
                          }
                        }
                        ncd:revise-date 2019-04-23 ;
                      }
                    }
                    leaf maxas-in {
                      description 'Accept as-path not exceeded maxas-in.'
                                  ;
                      type uint32 {
                        range 1..250 ;
                      }
                    }
                    leaf next-hop-self {
                      description 'Disable the next hop calculation for this ne'
                                + 'ighbor.'
                                  ;
                      type enumeration {
                        enum enable {
                          value 1 ;
                          description 'Apply next-hop-self for EBGP route.'
                                      ;
                        }
                        enum all {
                          value 2 ;
                          description 'Apply next-hop-self for both EBGP and IB'
                                    + 'GP route.'
                                      ;
                        }
                      }
                    }
                    leaf originate-interval {
                      description 'Minimum interval between sending BGP routing'
                                + ' which is locally originated updates.'
                                  ;
                      type uint32 {
                        range 1..65535 ;
                      }
                      units s ;
                    }
                    leaf passive {
                      description "Don't send open messages to this neighbor ac"
                                + "tively."
                                  ;
                      type empty ;
                    }
                    leaf remove-private-as {
                      description 'EBGP use to remove private AS number.'
                                  ;
                      type enumeration {
                        enum disable {
                          value 0 ;
                        }
                        enum enable {
                          value 1 ;
                        }
                      }
                    }
                    leaf send-community {
                      description 'Send community to this neighbor.'
                                  ;
                      type empty ;
                    }
                    leaf send-large-community {
                      description 'Send Large-community to this neighbor.'
                                  ;
                      type empty ;
                      ncd:revise-date 2020-04-16 ;
                    }
                    leaf route-reflector-client {
                      description 'Set this neighbor as a client peer.'
                                  ;
                      type empty ;
                      ncd:revise-date 2019-08-19 ;
                    }
                    leaf send-label {
                      description 'Send NLRI with MPLS label to this neighbor.'
                                  ;
                      type empty ;
                    }
                    leaf send-med {
                      description 'Send metric attribute to this neighbor.'
                                  ;
                      type empty ;
                    }
                    leaf inherit-igp-metric {
                      description 'Med attribute inherited from IGP metric befo'
                                + 're sending updates.'
                                  ;
                      type empty ;
                      ncd:revise-date 2017-07-25 ;
                    }
                    leaf shut-down {
                      status obsolete {
                        ncd:revise-date 2016-06-12 ;
                      }
                      description 'Administratively shut down this neighbor.'
                                  ;
                      type empty ;
                    }
                    leaf soft-reconfiguration {
                      status obsolete {
                        ncd:revise-date 2018-01-31 ;
                      }
                      description 'Neighbor soft reconfiguration.'
                                  ;
                      type empty ;
                    }
                    leaf soft-reconfig {
                      description 'Neighbor soft reconfiguration.'
                                  ;
                      type enumeration {
                        enum soft-reconfiguration {
                          value 1 ;
                          description Soft-reconfiguration. ;
                        }
                        enum enforce-soft-reconfiguration {
                          value 2 ;
                          description 'Enforce soft-reconfiguration instead of '
                                    + 'sending route-refresh.'
                                      ;
                        }
                      }
                      ncd:revise-date 2018-01-31 ;
                    }
                    leaf soo {
                      description 'Site-of-Origin extended community.'
                                  ;
                      type union {
                        type ncd:asn-nn ;
                        type ncd:asnd-nn ;
                        type ncd:ipadd-nn ;
                      }
                    }
                    leaf split-update-group {
                      description 'Split neighbor from update group.'
                                  ;
                      type empty ;
                    }
                    leaf update-source {
                      status obsolete {
                        ncd:revise-date 2018-11-27 ;
                      }
                      description 'Source of routing updates.'
                                  ;
                      type ncd:ifname {
                        length 1..31 ;
                      }
                    }
                    leaf weight {
                      description 'Set weight for routes from this neighbor.'
                                  ;
                      type uint32 {
                        range 1..65535 ;
                      }
                    }
                    leaf aigp {
                      description 'Enable AIGP for this neighbor.'
                                  ;
                      type empty ;
                      ncd:revise-date 2017-11-01 ;
                    }
                    container set-ttl {
                      description 'ebgp-multihop-ttl and ttl-security-hops are '
                                + 'mutex.'
                                  ;
                      choice set-ttl {
                        description 'ebgp-multihop-ttl and ttl-security-hops ar'
                                  + 'e mutex.'
                                    ;
                        case ebgp-multihop-ttl {
                          description 'Allow EBGP neighbors not on directly con'
                                    + 'nected net.'
                                      ;
                          leaf ebgp-multihop {
                            description 'Allow EBGP neighbors not on directly connected net.'
                                        ;
                            type uint8 {
                              range 1..255 ;
                            }
                          }
                        }
                        case ttl-security-hops {
                          description 'Enable EBGP TTL security check.'
                                      ;
                          leaf ttl-security-hops {
                            description 'Enable EBGP TTL security check.'
                                        ;
                            type uint8 {
                              range 1..254 ;
                            }
                          }
                        }
                      }
                    }
                    container neighbor-extend {
                      description 'Specify a neighbor.'
                                  ;
                      container local-as {
                        description 'Specify a local-as number.'
                                    ;
                        presence local-as ;
                        leaf as-number {
                          description 'Autonomous system number (normal or 4 Oc'
                                    + 'tets).'
                                      ;
                          type ncd:asn-dot {
                            pattern '-?([1-9]+(\.(\d*)|0)?)|(0(\.\d+){1})'
                                    ;
                          }
                          mandatory true ;
                        }
                        leaf replace-as {
                          description 'Replace real AS with local AS in the EBG'
                                    + 'P updates.'
                                      ;
                          type empty ;
                        }
                        leaf no-prepend {
                          description 'Do not prepend local-as to updates from '
                                    + 'EBGP peer.'
                                      ;
                          type empty ;
                        }
                        leaf dual-as {
                          description 'Accept real AS or local AS from the EBGP'
                                    + ' peer.'
                                      ;
                          type empty ;
                        }
                      }
                      container password {
                        description 'Set a password of the neighbor.'
                                    ;
                        choice password {
                          description 'Set a password of the neighbor.'
                                      ;
                          case clear-words {
                            description 'Specify the clear password (1-80 characters).'
                                        ;
                            leaf clear-words {
                              description 'The clear password (1-80 characters).'
                                          ;
                              type string {
                                length 1..80 ;
                              }
                            }
                          }
                          case encrypt-words {
                            description 'Specify the encrypted password.'
                                        ;
                            leaf encrypt-words {
                              description 'Specify the encrypted password.'
                                          ;
                              type string {
                                length 64..172 ;
                              }
                            }
                          }
                        }
                      }
                      leaf prefix-list-in-name {
                        description 'Apply prefix list to incoming routes.'
                                    ;
                        type string {
                          length 1..169 ;
                        }
                      }
                      leaf prefix-list-out-name {
                        description 'Apply prefix list to outbound routes.'
                                    ;
                        type string {
                          length 1..169 ;
                        }
                      }
                      leaf route-map-in-name {
                        description 'Apply route-map to incoming routes.'
                                    ;
                        type string {
                          length 1..200 ;
                        }
                      }
                      leaf route-map-out-name {
                        description 'Apply route-map to outbound routes.'
                                    ;
                        type string {
                          length 1..200 ;
                        }
                      }
                      container maximum-prefix {
                        description 'The action that generated when threshold v'
                                  + 'alue reached.'
                                    ;
                        presence 'The action that generated when threshold valu'
                               + 'e reached'
                                 ;
                        leaf maximum-prefix-number {
                          description 'Maximum number of prefix limit.'
                                      ;
                          type uint32 {
                            range 1..4294967295 ;
                          }
                          mandatory true ;
                        }
                        leaf maximum-prefix-threshold {
                          description 'Threshold value(%) at which to generate '
                                    + 'a warning.'
                                      ;
                          type uint32 {
                            range 1..100 ;
                          }
                          mandatory true ;
                        }
                        choice maximum-prefix-action {
                          description 'The action that generated when threshold'
                                    + ' value reached.'
                                      ;
                          mandatory true ;
                          case peer-action {
                            description 'The action that generated when threshold value reached.'
                                        ;
                            leaf action {
                              description 'The action that generated when threshold value reached.'
                                          ;
                              type enumeration {
                                enum down {
                                  value 0 ;
                                  description 'Break down BGP connection after limit is exceeded.'
                                              ;
                                }
                                enum warning-only {
                                  value 1 ;
                                  description 'Only give warning message when limit is exceeded.'
                                              ;
                                }
                                enum drop-routes {
                                  value 2 ;
                                  description 'Drop routes that exceed the maximum-prefix.'
                                              ;
                                }
                              }
                              mandatory true ;
                            }
                          }
                          case restart {
                            description 'Restart BGP connection after limit is exceeded.'
                                        ;
                            leaf restart-time {
                              description 'Restart interval in minutes.'
                                          ;
                              type uint32 {
                                range 1..30000 ;
                              }
                              units min ;
                              mandatory true ;
                            }
                          }
                        }
                      }
                      container timers {
                        description 'BGP per neighbor timers.'
                                    ;
                        presence timers ;
                        leaf keepalive {
                          description 'Adjust keepalive interval.'
                                      ;
                          type uint32 {
                            range 0..65535 ;
                          }
                          units s ;
                          mandatory true ;
                        }
                        leaf holdtime {
                          description 'Adjust holdtime.'
                                      ;
                          type uint32 {
                            range '0 | 3..65535'
                                  ;
                          }
                          units s ;
                          mandatory true ;
                        }
                      }
                      leaf routepolicy-in-name {
                        description 'Route policy name applied to the inbound r'
                                  + 'outes.'
                                    ;
                        type string {
                          length 1..200 ;
                        }
                      }
                      leaf routepolicy-out-name {
                        description 'Route policy name applied to the outbound '
                                  + 'routes.'
                                    ;
                        type string {
                          length 1..200 ;
                        }
                      }
                      leaf keychain-name {
                        description 'Keychain name associated to peer for authe'
                                  + 'ntication.'
                                    ;
                        type string {
                          length 1..31 ;
                        }
                      }
                      container withdraw {
                        description 'Withdraw routes when state of track-group '
                                  + 'is down.'
                                    ;
                        presence withdraw ;
                        leaf track-group {
                          description 'Track-group name.'
                                      ;
                          type string {
                            length 1..31 ;
                          }
                          mandatory true ;
                        }
                        leaf route-map {
                          description 'Route-map name.'
                                      ;
                          type string {
                            length 1..200 ;
                          }
                        }
                        ncd:revise-date 2016-02-06 ;
                      }
                      container second-withdraw {
                        description 'Withdraw routes when state of the second t'
                                  + 'rack-group is down.'
                                    ;
                        presence second-withdraw ;
                        leaf track-group {
                          description 'Track-group name.'
                                      ;
                          type string {
                            length 1..31 ;
                          }
                          mandatory true ;
                        }
                        leaf route-map {
                          description 'Route-map name.'
                                      ;
                          type string {
                            length 1..200 ;
                          }
                        }
                        ncd:revise-date 2018-07-12 ;
                      }
                      container idle-hold-time {
                        description 'Specifiy the length of time the peer is he'
                                  + 'ld in the idle state.'
                                    ;
                        presence idle-hold-time ;
                        leaf hold-time {
                          description 'Idle hold time.'
                                      ;
                          type uint32 {
                            range 1..3000 ;
                          }
                          units s ;
                          mandatory true ;
                        }
                        leaf increase {
                          description 'Increase idle hold time doubly to maximu'
                                    + 'm 3000.'
                                      ;
                          type empty ;
                        }
                        ncd:revise-date 2016-03-23 ;
                      }
                      container tracking {
                        description 'Enable peer tracking.'
                                    ;
                        presence tracking ;
                        leaf tracking {
                          status obsolete {
                            ncd:revise-date 2019-01-15 ;
                          }
                          description 'Enable peer tracking.'
                                      ;
                          type empty ;
                          mandatory true ;
                        }
                        leaf tracking-ex {
                          description 'Peer tracking.'
                                      ;
                          type enumeration {
                            enum enable {
                              value 1 ;
                              description 'Enable peer tracking.'
                                          ;
                            }
                            enum disable {
                              value 0 ;
                              description 'Disable peer tracking.'
                                          ;
                            }
                            enum inherit {
                              value 2 ;
                              description 'If the neighbor joined a group, the status of tracking inherited from group.'
                                          ;
                            }
                          }
                          ncd:revise-date 2019-01-15 ;
                        }
                        leaf delay {
                          description 'Delay time to reset the session.'
                                      ;
                          type uint32 {
                            range 1..65535 ;
                          }
                          units s ;
                        }
                        ncd:revise-date 2018-08-29 ;
                      }
                      container transport {
                        description 'Specify TCP path MTU discovery or TCP MSS '
                                  + 'to this neighbor.'
                                    ;
                        choice transport {
                          description 'Specify TCP path MTU discovery or TCP MS'
                                    + 'S to this neighbor.'
                                      ;
                          case path-mtu-discovery {
                            description 'Use transport path MTU discovery.'
                                        ;
                            leaf path-mtu-discovery {
                              description 'Use transport path MTU discovery.'
                                          ;
                              type empty ;
                            }
                          }
                          case mss {
                            description 'Specify TCP MSS to this neighbor.'
                                        ;
                            leaf mss {
                              description 'Set TCP initial maximum segment size.'
                                          ;
                              type uint32 {
                                range 68..10000 ;
                              }
                            }
                          }
                        }
                        ncd:revise-date 2020-08-18 ;
                      }
                      leaf neighbor-stalepath-time {
                        description "Set the max time to hold on to restarting "
                                  + "peer's stale paths."
                                    ;
                        type uint32 {
                          range 1..604800 {
                            description 'Delay value.'
                                        ;
                          }
                        }
                        units s ;
                        ncd:revise-date 2021-02-01 ;
                      }
                      leaf neighbor-stalepath-time-permanent {
                        description 'Hold on stale paths permanently.'
                                    ;
                        type empty ;
                        ncd:revise-date 2021-02-01 ;
                      }
                    }
                    leaf nouse-peergroup-config {
                      description 'Peer do not use group config set.Only for ge'
                                + 't operation.'
                                  ;
                      type empty ;
                    }
                    leaf open-delay {
                      description 'Delay to send open message.'
                                  ;
                      type uint32 {
                        range 1..240 ;
                      }
                      units s ;
                    }
                    container shutdown {
                      description 'Shut down this neighbor administratively or '
                                + 'when state of track-group is down.'
                                  ;
                      presence shut-down ;
                      leaf shut-down {
                        description 'Administratively shut down this neighbor.'
                                    ;
                        type empty ;
                        mandatory true ;
                      }
                      leaf track-group {
                        description 'Shut down this neighbor when state of trac'
                                  + 'k-group is down.'
                                    ;
                        type string {
                          length 1..31 ;
                        }
                      }
                      ncd:revise-date 2016-06-12 ;
                    }
                    container advertise-map-uni {
                      description 'Specify route-map for conditional advertisem'
                                + 'ent.'
                                  ;
                      presence 'Specify route-map for conditional advertisement'
                               ;
                      leaf advertise-map-name {
                        description 'Advertise route-map name.'
                                    ;
                        type string {
                          length 1..200 ;
                        }
                        mandatory true ;
                      }
                      choice advertise-map {
                        description 'Specify route-map for conditional advertis'
                                  + 'ement.'
                                    ;
                        mandatory true ;
                        case exist-map {
                          description 'Advertise prefix only if prefix exists.'
                                      ;
                          leaf exist-map-name {
                            description 'Advertise prefix only if prefix exists.'
                                        ;
                            type string {
                              length 1..200 ;
                            }
                            mandatory true ;
                          }
                        }
                        case nonexist-map {
                          description 'Advertise prefix only if prefix does not'
                                    + ' exist.'
                                      ;
                          leaf nonexist-map-name {
                            description 'Advertise prefix only if prefix does not exist.'
                                        ;
                            type string {
                              length 1..200 ;
                            }
                            mandatory true ;
                          }
                        }
                      }
                      ncd:revise-date 2016-11-15 ;
                    }
                    container route-filter-group {
                      description 'Specify a neighbor to join a route-filter-gr'
                                + 'oup.'
                                  ;
                      presence route-filter-group ;
                      leaf filter-group {
                        description 'Route filter group name (1-31 characters).'
                                    ;
                        type string {
                          length 1..31 ;
                        }
                        mandatory true ;
                      }
                      leaf next-hop-self {
                        description 'Disable the next hop calculation for this '
                                  + 'neighbor.'
                                    ;
                        type empty ;
                      }
                      ncd:revise-date 2017-06-12 ;
                    }
                    leaf enforce-first-as-disable {
                      description 'Not enforce the first AS for EBGP neighbor r'
                                + 'outes'
                                  ;
                      type empty ;
                      ncd:revise-date 2018-01-10 ;
                    }
                    leaf announce-sid {
                      description 'Enable Prefix-SID attribute for this neighbo'
                                + 'r.'
                                  ;
                      type enumeration {
                        enum enable {
                          value 1 ;
                          description 'Enable Prefix-SID attribute for this nei'
                                    + 'ghbor.'
                                      ;
                        }
                      }
                      ncd:revise-date 2018-05-14 ;
                    }
                    leaf enhanced-route-refresh-disable {
                      description 'Enhanced route refresh capability.'
                                  ;
                      type empty ;
                      ncd:revise-date 2018-10-23 ;
                    }
                    container update-source-ex {
                      description 'Specify the update-source configuration of t'
                                + 'he neighbor.'
                                  ;
                      presence 'Specify the update-source configuration of the '
                             + 'neighbor.'
                               ;
                      choice update-source {
                        description 'Specify the update-source configuration of'
                                  + ' the neighbor.'
                                    ;
                        case update-source-if {
                          description 'Specify the update-source interface name'
                                    + ' of the neighbor.'
                                      ;
                          leaf update-source-ifname {
                            description 'Specify the update-source interface name of the neighbor.'
                                        ;
                            type ncd:ifname ;
                          }
                        }
                        case update-source-ipv6 {
                          description 'Specify the update-source IPv6 address o'
                                    + 'f the neighbor.'
                                      ;
                          leaf update-source-addrv6 {
                            description 'Specify the update-source IPv6 address of the neighbor.'
                                        ;
                            type ncd:ipv6-address-none-zero ;
                          }
                          ncd:revise-date 2019-07-07 ;
                        }
                      }
                      ncd:revise-date 2018-11-27 ;
                    }
                    leaf four-byte-as-disable {
                      description 'Disable 4-byte AS capability.'
                                  ;
                      type empty ;
                      ncd:revise-date 2019-01-15 ;
                    }
                    leaf receive-single-label {
                      description 'Receive single label only for label unicast '
                                + 'route.'
                                  ;
                      type enumeration {
                        enum disable {
                          value 0 ;
                          description 'Disable receive single label only for la'
                                    + 'bel unicast route'
                                      ;
                        }
                        enum enable {
                          value 1 ;
                          description 'Enable receive single label only for lab'
                                    + 'el unicast route'
                                      ;
                        }
                        enum inherit {
                          value 2 ;
                          description 'If the neighbor joined a group, the stat'
                                    + 'us inherited from group'
                                      ;
                        }
                      }
                      ncd:revise-date 2019-11-29 ;
                    }
                    leaf receive-single-label-compatible {
                      description 'Receive single label only for label unicast '
                                + 'route.The function is the same as receive-si'
                                + 'ngle-label node.'
                                  ;
                      type enumeration {
                        enum disable {
                          value 0 ;
                          description 'Disable receive single label only for la'
                                    + 'bel unicast route'
                                      ;
                        }
                        enum enable {
                          value 1 ;
                          description 'Enable receive single label only for lab'
                                    + 'el unicast route'
                                      ;
                        }
                        enum inherit {
                          value 2 ;
                          description 'If the neighbor joined a group, the stat'
                                    + 'us inherited from group'
                                      ;
                        }
                      }
                      ncd:revise-date 2020-07-28 ;
                    }
                    leaf ignore-error-packet {
                      description 'Ignore error packet for this neighbor.'
                                  ;
                      type enumeration {
                        enum disable {
                          value 0 ;
                          description 'Disable peer ignore error packet'
                                      ;
                        }
                        enum enable {
                          value 1 ;
                          description 'Enable peer ignore error packet'
                                      ;
                        }
                        enum inherit {
                          value 2 ;
                          description 'If the neighbor joined a group, the stat'
                                    + 'us inherited from group.'
                                      ;
                        }
                      }
                      ncd:revise-date 2020-01-13 ;
                    }
                  }
                }
              }
              leaf table-policy {
                description 'Set external entry attributes into routing table.'
                            ;
                type string {
                  length 1..200 ;
                }
              }
              container multicast {
                description 'Specify parameters for IPv6 multicast VRF.'
                            ;
                presence 'IPv6 multicast VRF address family.'
                         ;
                container neighbor-ipv6 {
                  description 'Specify a IPv6 neighbor.'
                              ;
                  list neighbor {
                    description 'Specify a neighbor.'
                                ;
                    key ipv6-address ;
                    leaf ipv6-address {
                      description 'Neighbor IPv6 address.'
                                  ;
                      type ncd:ipv6-address ;
                    }
                    leaf activate {
                      description 'Enable the address family for this neighbor.'
                                  ;
                      type enumeration {
                        enum disable {
                          value 0 ;
                        }
                        enum enable {
                          value 1 ;
                        }
                      }
                    }
                    leaf as-path-loopcheck {
                      description 'Check as-path sending BGP routing to EBGP ne'
                                + 'ighbor.'
                                  ;
                      type empty ;
                    }
                    leaf split-update-group {
                      description 'Split neighbor from update group.'
                                  ;
                      type empty ;
                    }
                  }
                }
                container network {
                  description 'Specify a network to announce via BGP.'
                              ;
                  presence network ;
                  list network {
                    description 'Specify a network to announce via BGP.'
                                ;
                    key 'ipv6-address ipv6-mask-len'
                        ;
                    leaf ipv6-address {
                      description 'Network prefix.'
                                  ;
                      type ncd:ipv6-address ;
                    }
                    leaf ipv6-mask-len {
                      description 'Network mask length.'
                                  ;
                      type uint8 {
                        range 0..128 ;
                      }
                    }
                    leaf route-map {
                      description 'Route-map to modify the attributes.'
                                  ;
                      type string {
                        length 1..200 ;
                      }
                    }
                    leaf route-policy {
                      description 'Route-policy to modify the attributes.'
                                  ;
                      type string {
                        length 1..200 ;
                      }
                      ncd:revise-date 2020-10-10 ;
                    }
                  }
                }
                container redistribute {
                  description 'Redistribute information from another routing pr'
                            + 'otocol.'
                              ;
                  presence redistribute ;
                  container redistribute {
                    description 'Redistribute information from another routing '
                              + 'protocol.'
                                ;
                    list redistribute {
                      description 'Redistribute information from another routin'
                                + 'g protocol.'
                                  ;
                      key protocol ;
                      leaf protocol {
                        description 'Routing protocol type.'
                                    ;
                        type enumeration {
                          enum connected {
                            value 1 ;
                            description 'Connected routes.'
                                        ;
                          }
                          enum static {
                            value 2 ;
                            description 'Static routes.'
                                        ;
                          }
                          enum rip {
                            value 3 ;
                            description 'Routing information protocol(RIP).'
                                        ;
                          }
                          enum bras-pool {
                            value 24 ;
                            description 'Broadband Remote Access Server pool routes.'
                                        ;
                          }
                          enum hagp {
                            value 26 ;
                            description 'Hybrid access gateway protocol routes.'
                                        ;
                          }
                          enum dyn-leasedline {
                            value 29 ;
                            description 'Dynamic-leased-line routes assigned by AAA.'
                                        ;
                          }
                          enum address {
                            value 9 ;
                            description 'Address routes.'
                                        ;
                          }
                        }
                      }
                      leaf route-map {
                        description 'Apply route-map to redistribute.'
                                    ;
                        type string {
                          length 1..200 ;
                        }
                      }
                      leaf route-policy {
                        description 'Apply route-policy to redistribute.'
                                    ;
                        type string {
                          length 1..200 ;
                        }
                        ncd:revise-date 2020-10-10 ;
                      }
                      container set-metric {
                        description 'Set route metric.'
                                    ;
                        leaf metric {
                          description 'Set route metric.'
                                      ;
                          type uint32 {
                            range 0..4294967295 ;
                          }
                        }
                      }
                    }
                  }
                  container redistribute-isis {
                    description 'Redistribute information from ISIS protocol.'
                                ;
                    list redistribute-isis {
                      description 'Redistribute information from ISIS protocol.'
                                  ;
                      key 'protocol process-id'
                          ;
                      leaf protocol {
                        description 'Routing protocol type(ISIS-1,ISIS-2 or ISI'
                                  + 'S-1-2).'
                                    ;
                        type enumeration {
                          enum isis-1 {
                            value 4 ;
                            description 'IS-IS level-1 routes only.'
                                        ;
                          }
                          enum isis-2 {
                            value 5 ;
                            description 'IS-IS level-2 routes only.'
                                        ;
                          }
                        }
                      }
                      leaf process-id {
                        description 'ISIS process ID.'
                                    ;
                        type uint32 {
                          range 0..65535 ;
                        }
                      }
                      leaf route-map {
                        description 'Apply route-map to redistribute.'
                                    ;
                        type string {
                          length 1..200 ;
                        }
                      }
                      leaf route-policy {
                        description 'Apply route-policy to redistribute.'
                                    ;
                        type string {
                          length 1..200 ;
                        }
                        ncd:revise-date 2020-10-10 ;
                      }
                      container set-metric {
                        description 'Set route metric.'
                                    ;
                        leaf metric {
                          description 'Set route metric.'
                                      ;
                          type uint32 {
                            range 0..4294967295 ;
                          }
                        }
                      }
                    }
                  }
                  container redistribute-ospf {
                    description 'Redistribute information from OSPF protocol.'
                                ;
                    list redistribute-ospf {
                      description 'Redistribute information from OSPF protocol.'
                                  ;
                      key 'protocol process-id'
                          ;
                      leaf protocol {
                        description 'Routing protocol type(OSPF-EXT or OSPF-INT'
                                  + ').'
                                    ;
                        type enumeration {
                          enum ospf-ext {
                            value 7 ;
                            description 'Open shortest path first(OSPF) external routes.'
                                        ;
                          }
                          enum ospf-int {
                            value 8 ;
                            description 'Open shortest path first(OSPF) internal routes.'
                                        ;
                          }
                        }
                      }
                      leaf process-id {
                        description 'OSPF process ID.'
                                    ;
                        type uint32 {
                          range 1..65535 ;
                        }
                      }
                      leaf route-map {
                        description 'Apply route-map to redistribute.'
                                    ;
                        type string {
                          length 1..200 ;
                        }
                      }
                      leaf route-policy {
                        description 'Apply route-policy to redistribute.'
                                    ;
                        type string {
                          length 1..200 ;
                        }
                        ncd:revise-date 2020-10-10 ;
                      }
                      container set-metric {
                        description 'Set route metric.'
                                    ;
                        leaf metric {
                          description 'Set route metric.'
                                      ;
                          type uint32 {
                            range 0..4294967295 ;
                          }
                        }
                      }
                    }
                  }
                }
                leaf default-metric {
                  description 'Set metric of BGP routes without MED.'
                              ;
                  type uint32 {
                    range 0..4294967295 ;
                  }
                  default 0 ;
                  ncd:revise-date 2019-04-10 ;
                }
                ncd:revise-date 2016-01-29 ;
              }
              container additional-paths {
                description 'Additional paths in the BGP table.'
                            ;
                leaf selection-route-map {
                  description 'Selection criteria to pick the additional paths.'
                              ;
                  type string {
                    length 1..200 ;
                  }
                }
              }
              container route-scan-time {
                description 'Adjust BGP route scan.'
                            ;
                presence 'The ability of BGP route scan.'
                         ;
                leaf interval-wait {
                  description 'The interval of scan waiting. Default value is 5'
                            + '00.'
                              ;
                  type uint32 {
                    range 1..65535 ;
                  }
                  units ms ;
                  mandatory true ;
                }
                leaf initial {
                  description 'The initialization time of scan. Default value i'
                            + 's 50.'
                              ;
                  type uint32 {
                    range 1..65535 ;
                  }
                  units ms ;
                  mandatory true ;
                }
                leaf max-wait {
                  description 'The max waiting time of scan. Default value is 5'
                            + '000.'
                              ;
                  type uint32 {
                    range 1..65535 ;
                  }
                  units ms ;
                  mandatory true ;
                }
              }
              leaf urpf-id-download {
                if-feature urpf ;
                description 'Download URPF-ID information to RTM.'
                            ;
                type empty ;
                ncd:revise-date 2017-11-16 ;
              }
              container group-to-group {
                description 'Configure filter group to filter group route refle'
                          + 'ction.'
                            ;
                presence group-to-group ;
                leaf reflection {
                  description 'Reflection of routes is allowed.'
                              ;
                  type empty ;
                  mandatory true ;
                }
                leaf next-hop-self {
                  description 'Disable the next hop calculation.'
                              ;
                  type empty ;
                }
                ncd:revise-date 2018-08-04 ;
              }
              leaf ebgp-interface-sensitive {
                description 'Enable or disable interface sensitive for EBGP nei'
                          + 'ghbor.'
                            ;
                type enumeration {
                  enum disable {
                    value 0 ;
                  }
                  enum enable {
                    value 1 ;
                  }
                }
                default enable ;
                ncd:revise-date 2018-12-11 ;
              }
              leaf entropy-label {
                description 'entropy-label enable or disable'
                            ;
                type enumeration {
                  enum disable {
                    value 0 ;
                  }
                  enum enable {
                    value 1 ;
                  }
                }
                ncd:revise-date 2019-02-21 ;
              }
              leaf bgp-bestpath-origin {
                description 'bgp bestpath origin-from L3VPN neighbor or EVPN ne'
                          + 'ighbor.'
                            ;
                type enumeration {
                  enum l3vpn {
                    value 1 ;
                    description 'bgp bestpath origin-from L3VPN neighbor'
                                ;
                  }
                  enum evpn {
                    value 2 ;
                    description 'bgp bestpath origin-from EVPN neighbor'
                                ;
                  }
                }
                ncd:revise-date 2019-08-08 ;
              }
              leaf link-bandwidth-download {
                description 'Download link-bandwidth information to RTM.'
                            ;
                type empty ;
                ncd:revise-date 2019-10-22 ;
              }
              leaf bgp-bestpath-nexthop-priority {
                description 'Set BGP bestpath nexthop priority.'
                            ;
                type enumeration {
                  enum ipv4 {
                    value 1 ;
                    description 'BGP bestpath nexthop priority is ipv4'
                                ;
                  }
                  enum ipv6 {
                    value 2 ;
                    description 'BGP bestpath nexthop priority is ipv6'
                                ;
                  }
                }
                ncd:revise-date 2020-08-29 ;
              }
              container rib-only {
                description 'BGP routes are not delivered to the IP routing tab'
                          + 'le.'
                            ;
                presence 'BGP routes are not delivered to the IP routing table'
                         ;
                leaf rib-only-set {
                  description 'Enable rib-only.'
                              ;
                  type empty ;
                  mandatory true ;
                }
                leaf rib-only-routemap {
                  description 'Routing policy.'
                              ;
                  type string {
                    length 1..200 ;
                  }
                }
                leaf rib-only-routepolicy {
                  description 'Routing policy.'
                              ;
                  type string {
                    length 1..200 ;
                  }
                  ncd:revise-date 2020-10-10 ;
                }
                ncd:revise-date 2020-03-02 ;
              }
              leaf slow-peer-detection {
                description 'Set slow peer detection.'
                            ;
                type enumeration {
                  enum disable {
                    value 0 ;
                    description 'Disable slow peer detection'
                                ;
                  }
                  enum enable {
                    value 1 ;
                    description 'Enable slow peer detection'
                                ;
                  }
                }
                default disable ;
                ncd:revise-date 2020-09-08 ;
              }
              leaf slow-peer-detection-threshold {
                description 'Set threshold time for slow peer.Default value is '
                          + '300.'
                            ;
                type uint32 {
                  range 120..3600 {
                    description 'Threshold time range.'
                                ;
                  }
                }
                units s ;
                default 300 ;
                ncd:revise-date 2020-09-08 ;
              }
              leaf slow-peer-detection-recover {
                description 'Set recover time for slow peer.Default value is 30'
                          + '0.'
                            ;
                type uint32 {
                  range 120..3600 {
                    description 'Recover time range.'
                                ;
                  }
                }
                units s ;
                default 300 ;
                ncd:revise-date 2020-09-08 ;
              }
              leaf download-community {
                description 'The maximum number of communities for one route.'
                            ;
                type uint8 {
                  range 1..255 ;
                }
                ncd:revise-date 2020-10-10 ;
              }
              leaf bestpath-external {
                description 'Routes from external peer or RR client are preferr'
                          + 'ed in bestpath selection.'
                            ;
                type enumeration {
                  enum inherit {
                    value 0 ;
                    description 'Inherit from address family VPNv6 or L2VPN EVPN'
                                ;
                  }
                  enum enable {
                    value 1 ;
                  }
                  enum disable {
                    value 2 ;
                  }
                }
                default inherit ;
                ncd:revise-date 2020-11-23 ;
              }
              leaf bestpath-igp-metric-compare {
                description 'Compare IGP metric in maximum-paths.'
                            ;
                type enumeration {
                  enum inherit {
                    value 0 ;
                    description 'Inherit from address family VPNv6 or L2VPN EVPN'
                                ;
                  }
                  enum enable {
                    value 1 ;
                  }
                  enum disable {
                    value 2 ;
                  }
                }
                default inherit ;
                ncd:revise-date 2020-11-23 ;
              }
              leaf bestpath-igp-metric-ignore {
                description 'Ignore IGP metric in bestpath selection.'
                            ;
                type enumeration {
                  enum inherit {
                    value 0 ;
                    description 'Inherit from address family VPNv6 or L2VPN EVPN'
                                ;
                  }
                  enum enable {
                    value 1 ;
                  }
                  enum disable {
                    value 2 ;
                  }
                }
                default inherit ;
                ncd:revise-date 2020-11-23 ;
              }
            }
            ncd:revise-date 2016-01-06 ;
          }
          container address-family-ipv6-multi {
            description 'Configuration in address family IPv6 multicast mode.'
                        ;
            presence 'IPv6 multicast address family.'
                     ;
            leaf defaults-set-flag {
              status obsolete {
                ncd:revise-date 2020-07-28 ;
              }
              description 'Flag of defaults.Only for get operation.When this va'
                        + 'lue expressed as a binary,The lowest bit indicate di'
                        + 'stance-ibgp,the next bit distance-ebgp,then maxpaths'
                        + '-ebgp,then default-metric,then wait-for-end-of-rib,t'
                        + 'hen constrain-rt-filter.'
                          ;
              type uint32 {
                range 0..4294967295 ;
              }
              default 0 ;
            }
            leaf default-information-originate {
              description 'Notify default route.'
                          ;
              type empty ;
            }
            leaf default-metric {
              description 'Set the metric of BGP routes without MED.'
                          ;
              type uint32 {
                range 0..4294967295 ;
              }
              default 0 ;
            }
            leaf distance-bgp-external {
              description 'Distance for routes external to the AS.'
                          ;
              type uint32 {
                range 1..255 ;
              }
              default 20 ;
            }
            leaf distance-bgp-internal {
              description 'Distance for routes internal to the AS.'
                          ;
              type uint32 {
                range 1..255 ;
              }
              default 200 ;
            }
            leaf distance-route-map {
              description 'Define distance by route-map.This node has higher pr'
                        + 'iority than distance-bgp-internal and distance-bgp-e'
                        + 'xternal.'
                          ;
              type string {
                length 1..200 ;
              }
              ncd:revise-date 2020-09-08 ;
            }
            leaf distance-route-policy {
              description 'Define distance by route-policy.This node has higher'
                        + ' priority than distance-bgp-internal and distance-bg'
                        + 'p-external.'
                          ;
              type string {
                length 1..200 ;
              }
              ncd:revise-date 2020-10-10 ;
            }
            container redistribute-ipv6-multi {
              description 'Redistribute information from another routing protoc'
                        + 'ol.'
                          ;
              presence redistribute-ipv6-multi ;
              container redistribute-multi {
                description 'Redistribute information from another routing prot'
                          + 'ocol.'
                            ;
                list redistribute {
                  description 'Redistribute information from another routing pr'
                            + 'otocol.'
                              ;
                  key protocol ;
                  leaf protocol {
                    description 'Routing protocol type.'
                                ;
                    type enumeration {
                      enum connected {
                        value 1 ;
                        description 'Connected routes.'
                                    ;
                      }
                      enum static {
                        value 2 ;
                        description 'Static routes.'
                                    ;
                      }
                      enum rip {
                        value 3 ;
                        description 'Routing information protocol(RIP).'
                                    ;
                      }
                      enum bras-pool {
                        value 24 ;
                        description 'Broadband Remote Access Server pool routes.'
                                    ;
                      }
                      enum hagp {
                        value 26 ;
                        description 'Hybrid access gateway protocol routes.'
                                    ;
                      }
                      enum dyn-leasedline {
                        value 29 ;
                        description 'Dynamic-leased-line routes assigned by AAA.'
                                    ;
                      }
                      enum address {
                        value 9 ;
                        description 'Address routes.'
                                    ;
                      }
                      enum srv6-locator {
                        value 31 ;
                        description 'SRv6 locator routes.'
                                    ;
                      }
                    }
                  }
                  leaf route-map {
                    description 'Apply route-map to redistribute.'
                                ;
                    type string {
                      length 1..200 ;
                    }
                  }
                  leaf route-policy {
                    description 'Apply route-policy to redistribute.'
                                ;
                    type string {
                      length 1..200 ;
                    }
                    ncd:revise-date 2020-10-10 ;
                  }
                  container set-metric {
                    description 'Set route metric.'
                                ;
                    leaf metric {
                      description 'Set route metric.'
                                  ;
                      type uint32 {
                        range 0..4294967295 ;
                      }
                    }
                  }
                }
              }
              container redistribute-isis-multi {
                description 'Redistribute information from ISIS protocol.'
                            ;
                list redistribute-isis {
                  description 'Redistribute information from ISIS protocol.'
                              ;
                  key 'protocol process-id'
                      ;
                  leaf protocol {
                    description 'Routing protocol type(ISIS-1,ISIS-2 or ISIS-1-'
                              + '2).'
                                ;
                    type enumeration {
                      enum isis-1 {
                        value 4 ;
                        description 'IS-IS level-1 routes only.'
                                    ;
                      }
                      enum isis-2 {
                        value 5 ;
                        description 'IS-IS level-2 routes only.'
                                    ;
                      }
                    }
                  }
                  leaf process-id {
                    description 'ISIS process ID.'
                                ;
                    type uint32 {
                      range 0..65535 ;
                    }
                  }
                  leaf route-map {
                    description 'Apply route-map to redistribute.'
                                ;
                    type string {
                      length 1..200 ;
                    }
                  }
                  leaf route-policy {
                    description 'Apply route-policy to redistribute.'
                                ;
                    type string {
                      length 1..200 ;
                    }
                    ncd:revise-date 2020-10-10 ;
                  }
                  container set-metric {
                    description 'Set route metric.'
                                ;
                    leaf metric {
                      description 'Set route metric.'
                                  ;
                      type uint32 {
                        range 0..4294967295 ;
                      }
                    }
                  }
                }
              }
              container redistribute-ospf-multi {
                description 'Redistribute information from OSPF protocol.'
                            ;
                list redistribute-ospf {
                  description 'Redistribute information from OSPF protocol.'
                              ;
                  key 'protocol process-id'
                      ;
                  leaf protocol {
                    description 'Routing protocol type(OSPF-EXT or OSPF-INT).'
                                ;
                    type enumeration {
                      enum ospf-ext {
                        value 7 ;
                        description 'Open shortest path first(OSPF) external ro'
                                  + 'utes.'
                                    ;
                      }
                      enum ospf-int {
                        value 8 ;
                        description 'Open shortest path first(OSPF) internal ro'
                                  + 'utes.'
                                    ;
                      }
                    }
                  }
                  leaf process-id {
                    description 'OSPF process ID.'
                                ;
                    type uint32 {
                      range 1..65535 ;
                    }
                  }
                  leaf route-map {
                    description 'Apply route-map to redistribute.'
                                ;
                    type string {
                      length 1..200 ;
                    }
                  }
                  leaf route-policy {
                    description 'Apply route-policy to redistribute.'
                                ;
                    type string {
                      length 1..200 ;
                    }
                    ncd:revise-date 2020-10-10 ;
                  }
                  container set-metric {
                    description 'Set route metric.'
                                ;
                    leaf metric {
                      description 'Set route metric.'
                                  ;
                      type uint32 {
                        range 0..4294967295 ;
                      }
                    }
                  }
                }
              }
            }
            container network-ipv6-multi {
              description 'Specify a network to announce via BGP.'
                          ;
              presence network-ipv6-multi ;
              list network {
                description 'Specify a network to announce via BGP.'
                            ;
                key 'ipv6-address ipv6-mask-len'
                    ;
                leaf ipv6-address {
                  description 'Network prefix.'
                              ;
                  type ncd:ipv6-address ;
                }
                leaf ipv6-mask-len {
                  description 'Network mask length.'
                              ;
                  type uint8 {
                    range 0..128 ;
                  }
                }
                leaf route-map {
                  description 'Route-map to modify the attributes.'
                              ;
                  type string {
                    length 1..200 ;
                  }
                }
                leaf route-policy {
                  description 'Route-policy to modify the attributes.'
                              ;
                  type string {
                    length 1..200 ;
                  }
                  ncd:revise-date 2020-10-10 ;
                }
              }
            }
            container neighbor-v6-multi {
              description 'Specify a neighbor.'
                          ;
              presence neighbor-v6-multi ;
              container neighbor-group {
                description 'Specify a peergroup neighbor.'
                            ;
                list neighbor-peergroup {
                  description 'Specify a neighbor.'
                              ;
                  key neighbor-group ;
                  leaf neighbor-group {
                    description 'Peer group name (1-31 characters).'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf allowas-in {
                    description 'Accept as-path with my AS present in it.'
                                ;
                    type uint32 {
                      range 1..10 ;
                    }
                  }
                  leaf as-path-loopcheck {
                    description 'Check as-path sending BGP routing to EBGP neig'
                              + 'hbor.'
                                ;
                    type empty ;
                  }
                  leaf change-unicast-multicast {
                    description 'Add unicast routes to multicast.'
                                ;
                    type empty ;
                  }
                  leaf default-originate {
                    description 'Originate default route to this neighbor.'
                                ;
                    type empty ;
                  }
                  leaf default-originate-routemap {
                    description 'Map external entry attributes into routing tab'
                              + 'le.'
                                ;
                    type string {
                      length 1..200 ;
                    }
                    ncd:revise-date 2020-07-28 ;
                  }
                  leaf default-originate-routepolicy {
                    description 'Set external entry attributes into routing tab'
                              + 'le.'
                                ;
                    type string {
                      length 1..200 ;
                    }
                    ncd:revise-date 2020-10-10 ;
                  }
                  leaf maxas-in {
                    description 'Accept as-path not exceeded maxas-in.'
                                ;
                    type uint32 {
                      range 1..250 ;
                    }
                  }
                  leaf next-hop-self {
                    description 'Disable the next hop calculation for this neig'
                              + 'hbor.'
                                ;
                    type enumeration {
                      enum enable {
                        value 1 ;
                        description 'Apply next-hop-self for EBGP route.'
                                    ;
                      }
                      enum all {
                        value 2 ;
                        description 'Apply next-hop-self for both EBGP and IBGP'
                                  + ' route.'
                                    ;
                      }
                    }
                  }
                  leaf remove-private-as {
                    description 'EBGP use to remove private AS number.'
                                ;
                    type enumeration {
                      enum disable {
                        value 0 ;
                      }
                      enum enable {
                        value 1 ;
                      }
                    }
                  }
                  leaf route-reflector-client {
                    description 'Set this neighbor as a client peer.'
                                ;
                    type empty ;
                  }
                  leaf send-community {
                    description 'Send community to this neighbor.'
                                ;
                    type empty ;
                  }
                  leaf send-large-community {
                    description 'Send Large-community to this neighbor.'
                                ;
                    type empty ;
                    ncd:revise-date 2020-04-16 ;
                  }
                  leaf send-med {
                    description 'Send metric attribute to this neighbor.'
                                ;
                    type empty ;
                  }
                  leaf split-update-group {
                    description 'Split neighbor from update group.'
                                ;
                    type empty ;
                  }
                  leaf weight {
                    description 'Set weight for routes from this neighbor.'
                                ;
                    type uint32 {
                      range 1..65535 ;
                    }
                  }
                  container neighbor-extend {
                    description 'Specify a neighbor.'
                                ;
                    leaf prefix-list-in-name {
                      description 'Apply prefix list to incoming routes.'
                                  ;
                      type string {
                        length 1..169 ;
                      }
                    }
                    leaf prefix-list-out-name {
                      description 'Apply prefix list to outbound routes.'
                                  ;
                      type string {
                        length 1..169 ;
                      }
                    }
                    leaf route-map-in-name {
                      description 'Apply route-map to incoming routes.'
                                  ;
                      type string {
                        length 1..200 ;
                      }
                    }
                    leaf route-map-out-name {
                      description 'Apply route-map to outbound routes.'
                                  ;
                      type string {
                        length 1..200 ;
                      }
                    }
                    container maximum-prefix {
                      description 'The action that generated when threshold val'
                                + 'ue reached.'
                                  ;
                      presence 'The action that generated when threshold value '
                             + 'reached'
                               ;
                      leaf maximum-prefix-number {
                        description 'Maximum number of prefix limit.'
                                    ;
                        type uint32 {
                          range 1..4294967295 ;
                        }
                        mandatory true ;
                      }
                      leaf maximum-prefix-threshold {
                        description 'Threshold value(%) at which to generate a '
                                  + 'warning.'
                                    ;
                        type uint32 {
                          range 1..100 ;
                        }
                        mandatory true ;
                      }
                      choice maximum-prefix-action {
                        description 'The action that generated when threshold v'
                                  + 'alue reached.'
                                    ;
                        mandatory true ;
                        case peer-action {
                          description 'The action that generated when threshold'
                                    + ' value reached.'
                                      ;
                          leaf action {
                            description 'The action that generated when threshold value reached.'
                                        ;
                            type enumeration {
                              enum down {
                                value 0 ;
                                description 'Break down BGP connection after limit is exceeded.'
                                            ;
                              }
                              enum warning-only {
                                value 1 ;
                                description 'Only give warning message when limit is exceeded.'
                                            ;
                              }
                              enum drop-routes {
                                value 2 ;
                                description 'Drop routes that exceed the maximum-prefix.'
                                            ;
                              }
                            }
                            mandatory true ;
                          }
                        }
                        case restart {
                          description 'Restart BGP connection after limit is ex'
                                    + 'ceeded.'
                                      ;
                          leaf restart-time {
                            description 'Restart interval in minutes.'
                                        ;
                            type uint32 {
                              range 1..30000 ;
                            }
                            units min ;
                            mandatory true ;
                          }
                        }
                      }
                    }
                    leaf routepolicy-in-name {
                      description 'Route policy name applied to the inbound rou'
                                + 'tes.'
                                  ;
                      type string {
                        length 1..200 ;
                      }
                    }
                    leaf routepolicy-out-name {
                      description 'Route policy name applied to the outbound ro'
                                + 'utes.'
                                  ;
                      type string {
                        length 1..200 ;
                      }
                    }
                  }
                  container route-server-client {
                    description 'Set route server client only valid for ebgp pe'
                              + 'er.'
                                ;
                    presence route-server-client ;
                    leaf route-svr-client {
                      description 'Set route server client only valid for ebgp '
                                + 'peer.'
                                  ;
                      type empty ;
                      mandatory true ;
                    }
                    ncd:revise-date 2020-04-07 ;
                  }
                }
              }
              container neighbor-ipv6 {
                description 'Specify a IPv6 neighbor.'
                            ;
                list neighbor {
                  description 'Specify a neighbor.'
                              ;
                  key ipv6-address ;
                  leaf ipv6-address {
                    description 'Neighbor IPv6 address.'
                                ;
                    type ncd:ipv6-address ;
                  }
                  leaf joined-group {
                    description 'Only for read operation. The joined group name.'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf allowas-in {
                    description 'Accept as-path with my AS present in it.'
                                ;
                    type uint32 {
                      range 1..10 ;
                    }
                  }
                  leaf as-path-loopcheck {
                    description 'Check as-path sending BGP routing to EBGP neig'
                              + 'hbor.'
                                ;
                    type empty ;
                  }
                  leaf change-unicast-multicast {
                    description 'Add unicast routes to multicast.'
                                ;
                    type empty ;
                  }
                  leaf default-originate {
                    description 'Originate default route to this neighbor.'
                                ;
                    type empty ;
                  }
                  leaf default-originate-routemap {
                    description 'Map external entry attributes into routing tab'
                              + 'le.'
                                ;
                    type string {
                      length 1..200 ;
                    }
                    ncd:revise-date 2020-07-28 ;
                  }
                  leaf default-originate-routepolicy {
                    description 'Set external entry attributes into routing tab'
                              + 'le.'
                                ;
                    type string {
                      length 1..200 ;
                    }
                    ncd:revise-date 2020-10-10 ;
                  }
                  leaf maxas-in {
                    description 'Accept as-path not exceeded maxas-in.'
                                ;
                    type uint32 {
                      range 1..250 ;
                    }
                  }
                  leaf next-hop-self {
                    description 'Disable the next hop calculation for this neig'
                              + 'hbor.'
                                ;
                    type enumeration {
                      enum enable {
                        value 1 ;
                        description 'Apply next-hop-self for EBGP route.'
                                    ;
                      }
                      enum all {
                        value 2 ;
                        description 'Apply next-hop-self for both EBGP and IBGP'
                                  + ' route.'
                                    ;
                      }
                    }
                  }
                  leaf remove-private-as {
                    description 'EBGP use to remove private AS number.'
                                ;
                    type enumeration {
                      enum disable {
                        value 0 ;
                      }
                      enum enable {
                        value 1 ;
                      }
                    }
                  }
                  leaf route-reflector-client {
                    description 'Set this neighbor as a client peer.'
                                ;
                    type empty ;
                  }
                  leaf send-community {
                    description 'Send community to this neighbor.'
                                ;
                    type empty ;
                  }
                  leaf send-large-community {
                    description 'Send Large-community to this neighbor.'
                                ;
                    type empty ;
                    ncd:revise-date 2020-04-16 ;
                  }
                  leaf send-med {
                    description 'Send metric attribute to this neighbor.'
                                ;
                    type empty ;
                  }
                  leaf split-update-group {
                    description 'Split neighbor from update group.'
                                ;
                    type empty ;
                  }
                  leaf weight {
                    description 'Set weight for routes from this neighbor.'
                                ;
                    type uint32 {
                      range 1..65535 ;
                    }
                  }
                  container neighbor-extend {
                    description 'Specify a neighbor.'
                                ;
                    leaf prefix-list-in-name {
                      description 'Apply prefix list to incoming routes.'
                                  ;
                      type string {
                        length 1..169 ;
                      }
                    }
                    leaf prefix-list-out-name {
                      description 'Apply prefix list to outbound routes.'
                                  ;
                      type string {
                        length 1..169 ;
                      }
                    }
                    leaf route-map-in-name {
                      description 'Apply route-map to incoming routes.'
                                  ;
                      type string {
                        length 1..200 ;
                      }
                    }
                    leaf route-map-out-name {
                      description 'Apply route-map to outbound routes.'
                                  ;
                      type string {
                        length 1..200 ;
                      }
                    }
                    container maximum-prefix {
                      description 'The action that generated when threshold val'
                                + 'ue reached.'
                                  ;
                      presence 'The action that generated when threshold value '
                             + 'reached'
                               ;
                      leaf maximum-prefix-number {
                        description 'Maximum number of prefix limit.'
                                    ;
                        type uint32 {
                          range 1..4294967295 ;
                        }
                        mandatory true ;
                      }
                      leaf maximum-prefix-threshold {
                        description 'Threshold value(%) at which to generate a '
                                  + 'warning.'
                                    ;
                        type uint32 {
                          range 1..100 ;
                        }
                        mandatory true ;
                      }
                      choice maximum-prefix-action {
                        description 'The action that generated when threshold v'
                                  + 'alue reached.'
                                    ;
                        mandatory true ;
                        case peer-action {
                          description 'The action that generated when threshold'
                                    + ' value reached.'
                                      ;
                          leaf action {
                            description 'The action that generated when threshold value reached.'
                                        ;
                            type enumeration {
                              enum down {
                                value 0 ;
                                description 'Break down BGP connection after limit is exceeded.'
                                            ;
                              }
                              enum warning-only {
                                value 1 ;
                                description 'Only give warning message when limit is exceeded.'
                                            ;
                              }
                              enum drop-routes {
                                value 2 ;
                                description 'Drop routes that exceed the maximum-prefix.'
                                            ;
                              }
                            }
                            mandatory true ;
                          }
                        }
                        case restart {
                          description 'Restart BGP connection after limit is ex'
                                    + 'ceeded.'
                                      ;
                          leaf restart-time {
                            description 'Restart interval in minutes.'
                                        ;
                            type uint32 {
                              range 1..30000 ;
                            }
                            units min ;
                            mandatory true ;
                          }
                        }
                      }
                    }
                    leaf routepolicy-in-name {
                      description 'Route policy name applied to the inbound rou'
                                + 'tes.'
                                  ;
                      type string {
                        length 1..200 ;
                      }
                    }
                    leaf routepolicy-out-name {
                      description 'Route policy name applied to the outbound ro'
                                + 'utes.'
                                  ;
                      type string {
                        length 1..200 ;
                      }
                    }
                  }
                  container route-server-client {
                    description 'Set route server client only valid for ebgp pe'
                              + 'er.'
                                ;
                    presence route-server-client ;
                    leaf route-svr-client {
                      description 'Set route server client only valid for ebgp '
                                + 'peer.'
                                  ;
                      type empty ;
                      mandatory true ;
                    }
                    ncd:revise-date 2020-04-07 ;
                  }
                }
              }
              container neighbor-ipv4 {
                description 'Specify a IPv4 neighbor.'
                            ;
                list neighbor {
                  description 'Specify a neighbor.'
                              ;
                  key ipv4-address ;
                  leaf ipv4-address {
                    description 'Neighbor IPv4 address.'
                                ;
                    type ncd:ipv4-address ;
                  }
                  leaf joined-group {
                    description 'Only for read operation. The joined group name.'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf allowas-in {
                    description 'Accept as-path with my AS present in it.'
                                ;
                    type uint32 {
                      range 1..10 ;
                    }
                  }
                  leaf as-path-loopcheck {
                    description 'Check as-path sending BGP routing to EBGP neig'
                              + 'hbor.'
                                ;
                    type empty ;
                  }
                  leaf change-unicast-multicast {
                    description 'Add unicast routes to multicast.'
                                ;
                    type empty ;
                  }
                  leaf default-originate {
                    description 'Originate default route to this neighbor.'
                                ;
                    type empty ;
                  }
                  leaf default-originate-routemap {
                    description 'Map external entry attributes into routing tab'
                              + 'le.'
                                ;
                    type string {
                      length 1..200 ;
                    }
                  }
                  leaf default-originate-routepolicy {
                    description 'Set external entry attributes into routing tab'
                              + 'le.'
                                ;
                    type string {
                      length 1..200 ;
                    }
                    ncd:revise-date 2020-10-10 ;
                  }
                  leaf maxas-in {
                    description 'Accept as-path not exceeded maxas-in.'
                                ;
                    type uint32 {
                      range 1..250 ;
                    }
                  }
                  leaf next-hop-self {
                    description 'Disable the next hop calculation for this neig'
                              + 'hbor.'
                                ;
                    type enumeration {
                      enum enable {
                        value 1 ;
                        description 'Apply next-hop-self for EBGP route.'
                                    ;
                      }
                      enum all {
                        value 2 ;
                        description 'Apply next-hop-self for both EBGP and IBGP'
                                  + ' route.'
                                    ;
                      }
                    }
                  }
                  leaf remove-private-as {
                    description 'EBGP use to remove private AS number.'
                                ;
                    type enumeration {
                      enum disable {
                        value 0 ;
                      }
                      enum enable {
                        value 1 ;
                      }
                    }
                  }
                  leaf route-reflector-client {
                    description 'Set this neighbor as a client peer.'
                                ;
                    type empty ;
                  }
                  leaf send-community {
                    description 'Send community to this neighbor.'
                                ;
                    type empty ;
                  }
                  leaf send-large-community {
                    description 'Send Large-community to this neighbor.'
                                ;
                    type empty ;
                  }
                  leaf send-med {
                    description 'Send metric attribute to this neighbor.'
                                ;
                    type empty ;
                  }
                  leaf split-update-group {
                    description 'Split neighbor from update group.'
                                ;
                    type empty ;
                  }
                  leaf weight {
                    description 'Set weight for routes from this neighbor.'
                                ;
                    type uint32 {
                      range 1..65535 ;
                    }
                  }
                  container route-server-client {
                    description 'Set route server client for bgp peer.'
                                ;
                    presence route-server-client ;
                    leaf route-svr-client {
                      description 'Set route server client for bgp peer.'
                                  ;
                      type empty ;
                      mandatory true ;
                    }
                  }
                  container neighbor-extend {
                    description 'Specify a neighbor.'
                                ;
                    leaf prefix-list-in-name {
                      description 'Apply prefix list to incoming routes.'
                                  ;
                      type string {
                        length 1..169 ;
                      }
                    }
                    leaf prefix-list-out-name {
                      description 'Apply prefix list to outbound routes.'
                                  ;
                      type string {
                        length 1..169 ;
                      }
                    }
                    leaf route-map-in-name {
                      description 'Apply route-map to incoming routes.'
                                  ;
                      type string {
                        length 1..200 ;
                      }
                    }
                    leaf route-map-out-name {
                      description 'Apply route-map to outbound routes.'
                                  ;
                      type string {
                        length 1..200 ;
                      }
                    }
                    container maximum-prefix {
                      description 'The action that generated when threshold val'
                                + 'ue reached.'
                                  ;
                      presence 'The action that generated when threshold value '
                             + 'reached'
                               ;
                      leaf maximum-prefix-number {
                        description 'Maximum number of prefix limit.'
                                    ;
                        type uint32 {
                          range 1..4294967295 ;
                        }
                        mandatory true ;
                      }
                      leaf maximum-prefix-threshold {
                        description 'Threshold value(%) at which to generate a '
                                  + 'warning.'
                                    ;
                        type uint32 {
                          range 1..100 ;
                        }
                        mandatory true ;
                      }
                      choice maximum-prefix-action {
                        description 'The action that generated when threshold v'
                                  + 'alue reached.'
                                    ;
                        mandatory true ;
                        case peer-action {
                          description 'The action that generated when threshold'
                                    + ' value reached.'
                                      ;
                          leaf action {
                            description 'The action that generated when threshold value reached.'
                                        ;
                            type enumeration {
                              enum down {
                                value 0 ;
                                description 'Break down BGP connection after limit is exceeded.'
                                            ;
                              }
                              enum warning-only {
                                value 1 ;
                                description 'Only give warning message when limit is exceeded.'
                                            ;
                              }
                              enum drop-routes {
                                value 2 ;
                                description 'Drop routes that exceed the maximum-prefix.'
                                            ;
                              }
                            }
                            mandatory true ;
                          }
                        }
                        case restart {
                          description 'Restart BGP connection after limit is ex'
                                    + 'ceeded.'
                                      ;
                          leaf restart-time {
                            description 'Restart interval in minutes.'
                                        ;
                            type uint32 {
                              range 1..30000 ;
                            }
                            units min ;
                            mandatory true ;
                          }
                        }
                      }
                    }
                    leaf routepolicy-in-name {
                      description 'Route policy name applied to the inbound rou'
                                + 'tes.'
                                  ;
                      type string {
                        length 1..200 ;
                      }
                    }
                    leaf routepolicy-out-name {
                      description 'Route policy name applied to the outbound ro'
                                + 'utes.'
                                  ;
                      type string {
                        length 1..200 ;
                      }
                    }
                  }
                }
                ncd:revise-date 2020-07-28 ;
              }
            }
            ncd:revise-date 2016-01-06 ;
          }
          container address-family-vpnv6 {
            description 'Configuration in address family VPNv6 mode.'
                        ;
            presence 'VPNv6 address family.'
                     ;
            leaf defaults-set-flag {
              status obsolete {
                ncd:revise-date 2020-07-28 ;
              }
              description 'Flag of defaults.Only for get operation.When this va'
                        + 'lue expressed as a binary,The lowest bit indicate di'
                        + 'stance-ibgp,the next bit distance-ebgp,then maxpaths'
                        + '-ebgp,then default-metric,then wait-for-end-of-rib,t'
                        + 'hen constrain-rt-filter.'
                          ;
              type uint32 {
                range 0..4294967295 ;
              }
              default 0 ;
            }
            leaf bestpath-external {
              description 'Routes from external peer or RR client are preferred'
                        + ' in bestpath selection.'
                          ;
              type empty ;
            }
            leaf bestpath-igp-metric-ignore {
              description 'Ignore IGP metric in bestpath selection.'
                          ;
              type empty ;
            }
            leaf default-metric {
              description 'Set the metric of BGP routes without MED.'
                          ;
              type uint32 {
                range 0..4294967295 ;
              }
              default 0 ;
            }
            leaf bestpath-igp-metric-compare {
              description 'Compare IGP metric in maximum-paths.'
                          ;
              type empty ;
              ncd:revise-date 2017-07-05 ;
            }
            leaf nexthop-recursive-default-route {
              description 'Nexthop recursive lookup default-route.'
                          ;
              type enumeration {
                enum enable {
                  value 1 ;
                }
                enum disable {
                  value 0 ;
                }
              }
              default enable ;
              ncd:revise-date 2020-07-28 ;
            }
            leaf nexthop-recursive-null1 {
              description 'Nexthop recursive lookup null1.'
                          ;
              type enumeration {
                enum enable {
                  value 1 ;
                }
                enum disable {
                  value 0 ;
                }
              }
              default enable ;
              ncd:revise-date 2020-12-09 ;
            }
            container damp-vpnv6 {
              description 'Enable route-flap dampening.'
                          ;
              presence damp-vpnv6 ;
              choice damp {
                description 'Enable route-flap dampening.'
                            ;
                case route-map {
                  description 'Route-map to specify criteria for dampening.'
                              ;
                  leaf route-map-name {
                    description 'Route-map to specify criteria for dampening.'
                                ;
                    type string {
                      length 1..200 ;
                    }
                  }
                  leaf route-policy-name {
                    description 'Route-policy to specify criteria for dampening.'
                                ;
                    type string {
                      length 1..200 ;
                    }
                    ncd:revise-date 2020-10-10 ;
                  }
                }
                case parameter {
                  description 'Damp parameter.'
                              ;
                  leaf half-time {
                    description 'Half-life time for the penalty.'
                                ;
                    type uint32 {
                      range 1..45 ;
                    }
                    units min ;
                    mandatory true ;
                  }
                  leaf reuse {
                    description 'Value to start reusing a route.'
                                ;
                    type uint32 {
                      range 1..20000 ;
                    }
                    mandatory true ;
                  }
                  leaf suppress {
                    description 'Value to start suppressing a route.'
                                ;
                    type uint32 {
                      range 1..20000 ;
                    }
                    mandatory true ;
                  }
                  leaf max-suppress-time {
                    description 'Maximum duration to suppress a route.'
                                ;
                    type uint32 {
                      range 1..255 ;
                    }
                    mandatory true ;
                  }
                }
              }
            }
            container neighbor-vpnv6 {
              description 'Specify a neighbor.'
                          ;
              presence neighbor-vpnv6 ;
              container neighbor-group {
                description 'Specify a peergroup neighbor.'
                            ;
                list neighbor-peergroup {
                  description 'Specify a neighbor.'
                              ;
                  key neighbor-group ;
                  leaf neighbor-group {
                    description 'Peer group name (1-31 characters).'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf monitor {
                    description 'Config BMP monitor for the address family of t'
                              + 'his neighbor.'
                                ;
                    type enumeration {
                      enum disable {
                        value 2 ;
                      }
                      enum enable {
                        value 1 ;
                      }
                      enum inherit-global-config {
                        value 0 ;
                      }
                    }
                    ncd:revise-date 2019-07-29 ;
                  }
                  leaf advertise-maximum-prefix {
                    description 'Maximum number of prefix send to this peer.'
                                ;
                    type uint32 {
                      range 1..4294967295 ;
                    }
                  }
                  leaf allowas-in {
                    description 'Accept as-path with my AS present in it.'
                                ;
                    type uint32 {
                      range 1..10 ;
                    }
                  }
                  leaf as-path-loopcheck {
                    description 'Check as-path sending BGP routing to EBGP neig'
                              + 'hbor.'
                                ;
                    type empty ;
                  }
                  leaf maxas-in {
                    description 'Accept as-path not exceeded maxas-in.'
                                ;
                    type uint32 {
                      range 1..250 ;
                    }
                  }
                  leaf next-hop-self {
                    description 'Disable the next hop calculation for this neig'
                              + 'hbor.'
                                ;
                    type enumeration {
                      enum enable {
                        value 1 ;
                        description 'Apply next-hop-self for EBGP route.'
                                    ;
                      }
                      enum all {
                        value 2 ;
                        description 'Apply next-hop-self for both EBGP and IBGP'
                                  + ' route.'
                                    ;
                      }
                    }
                  }
                  choice nh-unchanged {
                    case next-hop-unchanged {
                      description 'NEXT_HOP of the IBGP path propagated unchang'
                                + 'ed to this neighbor.'
                                  ;
                      leaf next-hop-unchanged {
                        description 'Propagate next hop unchanged for IBGP path'
                                  + 's to this neighbor.'
                                    ;
                        type empty ;
                      }
                    }
                    case next-hop-unchanged-all {
                      description 'NEXT_HOP of either EBGP or IBGP path propaga'
                                + 'ted unchanged to this neighbor.'
                                  ;
                      leaf next-hop-unchanged-all {
                        description 'NEXT_HOP of either EBGP or IBGP path propa'
                                  + 'gated unchanged to this neighbor.'
                                    ;
                        type empty ;
                      }
                      ncd:revise-date 2020-04-07 ;
                    }
                  }
                  leaf remove-private-as {
                    description 'EBGP use to remove private AS number.'
                                ;
                    type enumeration {
                      enum disable {
                        value 0 ;
                      }
                      enum enable {
                        value 1 ;
                      }
                    }
                  }
                  leaf route-reflector-client {
                    description 'Set this neighbor as a client peer.'
                                ;
                    type empty ;
                  }
                  leaf send-community {
                    description 'Send community to this neighbor.'
                                ;
                    type empty ;
                  }
                  leaf send-large-community {
                    description 'Send Large-community to this neighbor.'
                                ;
                    type empty ;
                    ncd:revise-date 2020-04-16 ;
                  }
                  leaf send-med {
                    description 'Send metric attribute to this neighbor.'
                                ;
                    type empty ;
                  }
                  leaf inherit-igp-metric {
                    description 'Med attribute inherited from IGP metric before'
                              + ' sending updates.'
                                ;
                    type empty ;
                    ncd:revise-date 2017-07-25 ;
                  }
                  leaf split-update-group {
                    description 'Split neighbor from update group.'
                                ;
                    type empty ;
                  }
                  leaf weight {
                    description 'Set weight for routes from this neighbor.'
                                ;
                    type uint32 {
                      range 1..65535 ;
                    }
                  }
                  leaf default-originate-all {
                    description 'Notify all VPN default route.'
                                ;
                    type empty ;
                    ncd:revise-date 2016-05-30 ;
                  }
                  leaf default-originate-routemap {
                    description 'Map external entry attributes into routing tab'
                              + 'le.'
                                ;
                    type string {
                      length 1..200 ;
                    }
                    ncd:revise-date 2020-07-28 ;
                  }
                  leaf default-originate-routepolicy {
                    description 'Set external entry attributes into routing tab'
                              + 'le.'
                                ;
                    type string {
                      length 1..200 ;
                    }
                    ncd:revise-date 2020-10-10 ;
                  }
                  leaf aigp {
                    description 'Enable AIGP for this neighbor.'
                                ;
                    type empty ;
                    ncd:revise-date 2017-11-01 ;
                  }
                  container default-originate-vrf {
                    description 'Originate default route to this neighbor for c'
                              + 'ertain VRF.'
                                ;
                    list default-originate-vrf {
                      description 'Originate default route to this neighbor for'
                                + ' certain VRF.'
                                  ;
                      key vrf-name ;
                      leaf vrf-name {
                        description 'VPN Routing/Forwarding instance.'
                                    ;
                        type string {
                          length 1..32 ;
                        }
                      }
                      choice prefix-list {
                        description 'Prefix list name.'
                                    ;
                        case peer-list {
                          description 'Prefix list name of peer list.'
                                      ;
                          leaf peer-list-name {
                            description 'Prefix list name of peer list.'
                                        ;
                            type string {
                              length 1..169 ;
                            }
                          }
                          ncd:revise-date 2019-01-10 ;
                        }
                        case vrf-peer-list {
                          description 'Prefix list name of VRF routes list.'
                                      ;
                          leaf vrf-peer-list-name {
                            description 'Prefix list name of VRF routes list.'
                                        ;
                            type string {
                              length 1..169 ;
                            }
                          }
                          ncd:revise-date 2019-09-04 ;
                        }
                        ncd:revise-date 2019-01-10 ;
                      }
                    }
                    ncd:revise-date 2016-05-30 ;
                  }
                  leaf adv-tunnel-encap {
                    description 'Advertise tunnel encapsulation type'
                                ;
                    type enumeration {
                      enum mpls {
                        value 2 ;
                      }
                      enum srv6 {
                        value 4 ;
                      }
                    }
                    ncd:revise-date 2020-08-18 ;
                  }
                  container virtual {
                    description 'Set spoke PE.'
                                ;
                    presence virtual ;
                    leaf virtual-spoke {
                      description 'Enable spoke PE.'
                                  ;
                      type empty ;
                      mandatory true ;
                    }
                    leaf reflect-nexthop-self {
                      description 'Set nexthop self when reflection.'
                                  ;
                      type empty ;
                    }
                    leaf check-upstream-pe {
                      description 'Check upstream PE when advertising default r'
                                + 'oute.'
                                  ;
                      type empty ;
                      ncd:revise-date 2018-05-14 ;
                    }
                    leaf by-vrf {
                      description 'Send specific route by default-originate con'
                                + 'fig.'
                                  ;
                      type empty ;
                      ncd:revise-date 2019-12-31 ;
                    }
                    ncd:revise-date 2016-05-30 ;
                  }
                  container neighbor-extend {
                    description 'Specify a neighbor.'
                                ;
                    leaf additional-paths-receive {
                      description 'Receive additional paths from this neighbor.'
                                  ;
                      type empty ;
                    }
                    container maximum-prefix {
                      description 'The action that generated when threshold val'
                                + 'ue reached.'
                                  ;
                      presence 'The action that generated when threshold value '
                             + 'reached'
                               ;
                      leaf maximum-prefix-number {
                        description 'Maximum number of prefix limit.'
                                    ;
                        type uint32 {
                          range 1..4294967295 ;
                        }
                        mandatory true ;
                      }
                      leaf maximum-prefix-threshold {
                        description 'Threshold value(%) at which to generate a '
                                  + 'warning.'
                                    ;
                        type uint32 {
                          range 1..100 ;
                        }
                        mandatory true ;
                      }
                      choice maximum-prefix-action {
                        description 'The action that generated when threshold v'
                                  + 'alue reached.'
                                    ;
                        mandatory true ;
                        case peer-action {
                          description 'The action that generated when threshold'
                                    + ' value reached.'
                                      ;
                          leaf action {
                            description 'The action that generated when threshold value reached.'
                                        ;
                            type enumeration {
                              enum down {
                                value 0 ;
                                description 'Break down BGP connection after limit is exceeded.'
                                            ;
                              }
                              enum warning-only {
                                value 1 ;
                                description 'Only give warning message when limit is exceeded.'
                                            ;
                              }
                              enum drop-routes {
                                value 2 ;
                                description 'Drop routes that exceed the maximum-prefix.'
                                            ;
                              }
                            }
                            mandatory true ;
                          }
                        }
                        case restart {
                          description 'Restart BGP connection after limit is ex'
                                    + 'ceeded.'
                                      ;
                          leaf restart-time {
                            description 'Restart interval in minutes.'
                                        ;
                            type uint32 {
                              range 1..30000 ;
                            }
                            units min ;
                            mandatory true ;
                          }
                        }
                      }
                    }
                    leaf prefix-list-in-name {
                      description 'Apply prefix list to incoming routes.'
                                  ;
                      type string {
                        length 1..169 ;
                      }
                    }
                    leaf prefix-list-out-name {
                      description 'Apply  prefix list to outbound routes.'
                                  ;
                      type string {
                        length 1..169 ;
                      }
                    }
                    leaf route-map-in-name {
                      description 'Apply route-map to incoming routes.'
                                  ;
                      type string {
                        length 1..200 ;
                      }
                    }
                    leaf route-map-out-name {
                      description 'Apply route-map to outbound routes.'
                                  ;
                      type string {
                        length 1..200 ;
                      }
                    }
                    container diverse-path {
                      description 'Advertise diverse path to this neighbor.'
                                  ;
                      presence diverse-path ;
                      choice diverse-path {
                        description 'Advertise diverse path to this neighbor.'
                                    ;
                        mandatory true ;
                        case backup {
                          description 'Advertisement of the backup path.'
                                      ;
                          leaf backup {
                            description 'Advertisement of the backup path.'
                                        ;
                            type empty ;
                            mandatory true ;
                          }
                        }
                        case multipath {
                          description 'Sequence number of multipath.'
                                      ;
                          leaf sequence-number {
                            description 'Sequence number of multipath.'
                                        ;
                            type uint32 {
                              range 2..32 ;
                            }
                            mandatory true ;
                          }
                        }
                      }
                      leaf route-map {
                        description 'Apply route-map to neighbor.'
                                    ;
                        type string {
                          length 1..200 ;
                        }
                      }
                    }
                    container additional-paths-send {
                      description 'Send additional paths to this neighbor.'
                                  ;
                      choice additional-paths-send {
                        description 'Send additional paths to this neighbor.'
                                    ;
                        default send-one-path ;
                        case send-one-path {
                          description 'Send one additional path to this neighbo'
                                    + 'r.'
                                      ;
                          leaf send {
                            description 'Send additional paths to this neighbor.'
                                        ;
                            type empty ;
                          }
                        }
                        case send-multi-paths {
                          description 'Send additional multi-paths to this neig'
                                    + 'hbor.'
                                      ;
                          leaf paths-number {
                            description 'Number of paths for a prefix.'
                                        ;
                            type uint32 {
                              range 2..32 ;
                            }
                            mandatory true ;
                          }
                          leaf prefixlist {
                            description 'Prefixlist of filtering additional paths.'
                                        ;
                            type string {
                              length 1..169 ;
                            }
                          }
                        }
                      }
                    }
                    leaf routepolicy-in-name {
                      description 'Route policy name applied to the inbound rou'
                                + 'tes.'
                                  ;
                      type string {
                        length 1..200 ;
                      }
                    }
                    leaf routepolicy-out-name {
                      description 'Route policy name applied to the outbound ro'
                                + 'utes.'
                                  ;
                      type string {
                        length 1..200 ;
                      }
                    }
                    container withdraw {
                      description 'Withdraw routes when state of track-group is'
                                + ' down.'
                                  ;
                      presence withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                      ncd:revise-date 2016-02-06 ;
                    }
                    container second-withdraw {
                      description 'Withdraw routes when state of the second tra'
                                + 'ck-group is down.'
                                  ;
                      presence second-withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                      ncd:revise-date 2018-07-12 ;
                    }
                  }
                  container advertise-map-uni {
                    description 'Specify route-map for conditional advertisemen'
                              + 't.'
                                ;
                    presence 'Specify route-map for conditional advertisement'
                             ;
                    leaf advertise-map-name {
                      description 'Advertise route-map name.'
                                  ;
                      type string {
                        length 1..200 ;
                      }
                      mandatory true ;
                    }
                    choice advertise-map {
                      description 'Specify route-map for conditional advertisem'
                                + 'ent.'
                                  ;
                      mandatory true ;
                      case exist-map {
                        description 'Advertise prefix only if prefix exists.'
                                    ;
                        leaf exist-map-name {
                          description 'Advertise prefix only if prefix exists.'
                                      ;
                          type string {
                            length 1..200 ;
                          }
                          mandatory true ;
                        }
                      }
                      case nonexist-map {
                        description 'Advertise prefix only if prefix does not e'
                                  + 'xist.'
                                    ;
                        leaf nonexist-map-name {
                          description 'Advertise prefix only if prefix does not'
                                    + ' exist.'
                                      ;
                          type string {
                            length 1..200 ;
                          }
                          mandatory true ;
                        }
                      }
                    }
                    ncd:revise-date 2016-11-15 ;
                  }
                  container route-filter-group {
                    description 'Specify a neighbor to join a route-filter-grou'
                              + 'p.'
                                ;
                    presence route-filter-group ;
                    leaf filter-group {
                      description 'Route filter group name (1-31 characters).'
                                  ;
                      type string {
                        length 1..31 ;
                      }
                      mandatory true ;
                    }
                    leaf next-hop-self {
                      description 'Disable the next hop calculation for this ne'
                                + 'ighbor.'
                                  ;
                      type empty ;
                    }
                    ncd:revise-date 2017-06-12 ;
                  }
                  leaf announce-sid {
                    description 'Enable Prefix-SID attribute for this neighbor.'
                                ;
                    type enumeration {
                      enum enable {
                        value 1 ;
                        description 'Enable Prefix-SID attribute for this neigh'
                                  + 'bor.'
                                    ;
                      }
                    }
                    ncd:revise-date 2018-05-14 ;
                  }
                  leaf soft-reconfig {
                    description 'Neighbor soft reconfiguration.'
                                ;
                    type enumeration {
                      enum soft-reconfiguration {
                        value 1 ;
                        description Soft-reconfiguration. ;
                      }
                      enum enforce-soft-reconfiguration {
                        value 2 ;
                        description 'Enforce soft-reconfiguration instead of se'
                                  + 'nding route-refresh.'
                                    ;
                      }
                    }
                    ncd:revise-date 2019-08-08 ;
                  }
                  leaf vpn-orf {
                    description 'Peer route-target ORF capability'
                                ;
                    type enumeration {
                      enum disable {
                        value 0 ;
                        description 'Disable peer route-target ORF capability'
                                    ;
                      }
                      enum enable {
                        value 1 ;
                        description 'Enable peer route-target ORF capability'
                                    ;
                      }
                    }
                    ncd:revise-date 2020-02-08 ;
                  }
                  leaf send-link-bw {
                    description 'Send link bandwidth to this neighbor.'
                                ;
                    type enumeration {
                      enum disable {
                        value 0 ;
                        description 'Disable peer send link bandwidth'
                                    ;
                      }
                      enum enable {
                        value 1 ;
                        description 'Enable peer send link bandwidth'
                                    ;
                      }
                    }
                    ncd:revise-date 2019-10-22 ;
                  }
                  container route-server-client {
                    description 'Set route server client only valid for ebgp pe'
                              + 'er.'
                                ;
                    presence route-server-client ;
                    leaf route-svr-client {
                      description 'Set route server client only valid for ebgp '
                                + 'peer.'
                                  ;
                      type empty ;
                      mandatory true ;
                    }
                    ncd:revise-date 2020-04-07 ;
                  }
                }
              }
              container neighbor-ipv4 {
                description 'Specify a IPv4 neighbor.'
                            ;
                list neighbor {
                  description 'Specify a neighbor.'
                              ;
                  key ipv4-addr ;
                  leaf ipv4-addr {
                    description 'Neighbor IPv4 address.'
                                ;
                    type ncd:ipv4-address ;
                  }
                  leaf joined-group {
                    description 'Only for read operation. The joined group name.'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf monitor {
                    description 'Config BMP monitor for the address family of t'
                              + 'his neighbor.'
                                ;
                    type enumeration {
                      enum disable {
                        value 2 ;
                      }
                      enum enable {
                        value 1 ;
                      }
                      enum inherit-global-config {
                        value 0 ;
                      }
                    }
                    ncd:revise-date 2019-07-29 ;
                  }
                  leaf advertise-maximum-prefix {
                    description 'Maximum number of prefix send to this peer.'
                                ;
                    type uint32 {
                      range 1..4294967295 ;
                    }
                  }
                  leaf allowas-in {
                    description 'Accept as-path with my AS present in it.'
                                ;
                    type uint32 {
                      range 1..10 ;
                    }
                  }
                  leaf as-path-loopcheck {
                    description 'Check as-path sending BGP routing to EBGP neig'
                              + 'hbor.'
                                ;
                    type empty ;
                  }
                  leaf maxas-in {
                    description 'Accept as-path not exceeded maxas-in.'
                                ;
                    type uint32 {
                      range 1..250 ;
                    }
                  }
                  leaf next-hop-self {
                    description 'Disable the next hop calculation for this neig'
                              + 'hbor.'
                                ;
                    type enumeration {
                      enum enable {
                        value 1 ;
                        description 'Apply next-hop-self for EBGP route.'
                                    ;
                      }
                      enum all {
                        value 2 ;
                        description 'Apply next-hop-self for both EBGP and IBGP'
                                  + ' route.'
                                    ;
                      }
                    }
                  }
                  choice nh-unchanged {
                    case next-hop-unchanged {
                      description 'NEXT_HOP of the IBGP path propagated unchang'
                                + 'ed to this neighbor.'
                                  ;
                      leaf next-hop-unchanged {
                        description 'Propagate next hop unchanged for IBGP path'
                                  + 's to this neighbor.'
                                    ;
                        type empty ;
                      }
                    }
                    case next-hop-unchanged-all {
                      description 'NEXT_HOP of either EBGP or IBGP path propaga'
                                + 'ted unchanged to this neighbor.'
                                  ;
                      leaf next-hop-unchanged-all {
                        description 'NEXT_HOP of either EBGP or IBGP path propa'
                                  + 'gated unchanged to this neighbor.'
                                    ;
                        type empty ;
                      }
                      ncd:revise-date 2020-04-07 ;
                    }
                  }
                  leaf remove-private-as {
                    description 'EBGP use to remove private AS number.'
                                ;
                    type enumeration {
                      enum disable {
                        value 0 ;
                      }
                      enum enable {
                        value 1 ;
                      }
                    }
                  }
                  leaf route-reflector-client {
                    description 'Set this neighbor as a client peer.'
                                ;
                    type empty ;
                  }
                  leaf send-community {
                    description 'Send community to this neighbor.'
                                ;
                    type empty ;
                  }
                  leaf send-large-community {
                    description 'Send Large-community to this neighbor.'
                                ;
                    type empty ;
                    ncd:revise-date 2020-04-16 ;
                  }
                  leaf send-med {
                    description 'Send metric attribute to this neighbor.'
                                ;
                    type empty ;
                  }
                  leaf inherit-igp-metric {
                    description 'Med attribute inherited from IGP metric before'
                              + ' sending updates.'
                                ;
                    type empty ;
                    ncd:revise-date 2017-07-25 ;
                  }
                  leaf split-update-group {
                    description 'Split neighbor from update group.'
                                ;
                    type empty ;
                  }
                  leaf weight {
                    description 'Set weight for routes from this neighbor.'
                                ;
                    type uint32 {
                      range 1..65535 ;
                    }
                  }
                  leaf default-originate-all {
                    description 'Notify all VPN default route.'
                                ;
                    type empty ;
                    ncd:revise-date 2016-05-30 ;
                  }
                  leaf default-originate-routemap {
                    description 'Map external entry attributes into routing tab'
                              + 'le.'
                                ;
                    type string {
                      length 1..200 ;
                    }
                    ncd:revise-date 2020-07-28 ;
                  }
                  leaf default-originate-routepolicy {
                    description 'Set external entry attributes into routing tab'
                              + 'le.'
                                ;
                    type string {
                      length 1..200 ;
                    }
                    ncd:revise-date 2020-10-10 ;
                  }
                  leaf aigp {
                    description 'Enable AIGP for this neighbor.'
                                ;
                    type empty ;
                    ncd:revise-date 2017-11-01 ;
                  }
                  container default-originate-vrf {
                    description 'Originate default route to this neighbor for c'
                              + 'ertain VRF.'
                                ;
                    list default-originate-vrf {
                      description 'Originate default route to this neighbor for'
                                + ' certain VRF.'
                                  ;
                      key vrf-name ;
                      leaf vrf-name {
                        description 'VPN Routing/Forwarding instance.'
                                    ;
                        type string {
                          length 1..32 ;
                        }
                      }
                      choice prefix-list {
                        description 'Prefix list name.'
                                    ;
                        case peer-list {
                          description 'Prefix list name of peer list.'
                                      ;
                          leaf peer-list-name {
                            description 'Prefix list name of peer list.'
                                        ;
                            type string {
                              length 1..169 ;
                            }
                          }
                          ncd:revise-date 2019-01-10 ;
                        }
                        case vrf-peer-list {
                          description 'Prefix list name of VRF routes list.'
                                      ;
                          leaf vrf-peer-list-name {
                            description 'Prefix list name of VRF routes list.'
                                        ;
                            type string {
                              length 1..169 ;
                            }
                          }
                          ncd:revise-date 2019-09-04 ;
                        }
                        ncd:revise-date 2019-01-10 ;
                      }
                    }
                    ncd:revise-date 2016-05-30 ;
                  }
                  container virtual {
                    description 'Set spoke PE.'
                                ;
                    presence virtual ;
                    leaf virtual-spoke {
                      description 'Enable spoke PE.'
                                  ;
                      type empty ;
                      mandatory true ;
                    }
                    leaf reflect-nexthop-self {
                      description 'Set nexthop self when reflection.'
                                  ;
                      type empty ;
                    }
                    leaf check-upstream-pe {
                      description 'Check upstream PE when advertising default r'
                                + 'oute.'
                                  ;
                      type empty ;
                      ncd:revise-date 2018-05-14 ;
                    }
                    leaf by-vrf {
                      description 'Send specific route by default-originate con'
                                + 'fig.'
                                  ;
                      type empty ;
                      ncd:revise-date 2019-12-31 ;
                    }
                    ncd:revise-date 2016-05-30 ;
                  }
                  leaf adv-tunnel-encap {
                    description 'Advertise tunnel encapsulation type'
                                ;
                    type enumeration {
                      enum mpls {
                        value 2 ;
                      }
                      enum srv6 {
                        value 4 ;
                      }
                    }
                    ncd:revise-date 2020-08-18 ;
                  }
                  container neighbor-extend {
                    description 'Specify a neighbor.'
                                ;
                    leaf additional-paths-receive {
                      description 'Receive additional paths from this neighbor.'
                                  ;
                      type empty ;
                    }
                    container maximum-prefix {
                      description 'The action that generated when threshold val'
                                + 'ue reached.'
                                  ;
                      presence 'The action that generated when threshold value '
                             + 'reached'
                               ;
                      leaf maximum-prefix-number {
                        description 'Maximum number of prefix limit.'
                                    ;
                        type uint32 {
                          range 1..4294967295 ;
                        }
                        mandatory true ;
                      }
                      leaf maximum-prefix-threshold {
                        description 'Threshold value(%) at which to generate a '
                                  + 'warning.'
                                    ;
                        type uint32 {
                          range 1..100 ;
                        }
                        mandatory true ;
                      }
                      choice maximum-prefix-action {
                        description 'The action that generated when threshold v'
                                  + 'alue reached.'
                                    ;
                        mandatory true ;
                        case peer-action {
                          description 'The action that generated when threshold'
                                    + ' value reached.'
                                      ;
                          leaf action {
                            description 'The action that generated when threshold value reached.'
                                        ;
                            type enumeration {
                              enum down {
                                value 0 ;
                                description 'Break down BGP connection after limit is exceeded.'
                                            ;
                              }
                              enum warning-only {
                                value 1 ;
                                description 'Only give warning message when limit is exceeded.'
                                            ;
                              }
                              enum drop-routes {
                                value 2 ;
                                description 'Drop routes that exceed the maximum-prefix.'
                                            ;
                              }
                            }
                            mandatory true ;
                          }
                        }
                        case restart {
                          description 'Restart BGP connection after limit is ex'
                                    + 'ceeded.'
                                      ;
                          leaf restart-time {
                            description 'Restart interval in minutes.'
                                        ;
                            type uint32 {
                              range 1..30000 ;
                            }
                            units min ;
                            mandatory true ;
                          }
                        }
                      }
                    }
                    leaf prefix-list-in-name {
                      description 'Apply prefix list to incoming routes.'
                                  ;
                      type string {
                        length 1..169 ;
                      }
                    }
                    leaf prefix-list-out-name {
                      description 'Apply  prefix list to outbound routes.'
                                  ;
                      type string {
                        length 1..169 ;
                      }
                    }
                    leaf route-map-in-name {
                      description 'Apply route-map to incoming routes.'
                                  ;
                      type string {
                        length 1..200 ;
                      }
                    }
                    leaf route-map-out-name {
                      description 'Apply route-map to outbound routes.'
                                  ;
                      type string {
                        length 1..200 ;
                      }
                    }
                    container diverse-path {
                      description 'Advertise diverse path to this neighbor.'
                                  ;
                      presence diverse-path ;
                      choice diverse-path {
                        description 'Advertise diverse path to this neighbor.'
                                    ;
                        mandatory true ;
                        case backup {
                          description 'Advertisement of the backup path.'
                                      ;
                          leaf backup {
                            description 'Advertisement of the backup path.'
                                        ;
                            type empty ;
                            mandatory true ;
                          }
                        }
                        case multipath {
                          description 'Sequence number of multipath.'
                                      ;
                          leaf sequence-number {
                            description 'Sequence number of multipath.'
                                        ;
                            type uint32 {
                              range 2..32 ;
                            }
                            mandatory true ;
                          }
                        }
                      }
                      leaf route-map {
                        description 'Apply route-map to neighbor.'
                                    ;
                        type string {
                          length 1..200 ;
                        }
                      }
                    }
                    container additional-paths-send {
                      description 'Send additional paths to this neighbor.'
                                  ;
                      choice additional-paths-send {
                        description 'Send additional paths to this neighbor.'
                                    ;
                        default send-one-path ;
                        case send-one-path {
                          description 'Send one additional path to this neighbo'
                                    + 'r.'
                                      ;
                          leaf send {
                            description 'Send additional paths to this neighbor.'
                                        ;
                            type empty ;
                          }
                        }
                        case send-multi-paths {
                          description 'Send additional multi-paths to this neig'
                                    + 'hbor.'
                                      ;
                          leaf paths-number {
                            description 'Number of paths for a prefix.'
                                        ;
                            type uint32 {
                              range 2..32 ;
                            }
                            mandatory true ;
                          }
                          leaf prefixlist {
                            description 'Prefixlist of filtering additional paths.'
                                        ;
                            type string {
                              length 1..169 ;
                            }
                          }
                        }
                      }
                    }
                    leaf routepolicy-in-name {
                      description 'Route policy name applied to the inbound rou'
                                + 'tes.'
                                  ;
                      type string {
                        length 1..200 ;
                      }
                    }
                    leaf routepolicy-out-name {
                      description 'Route policy name applied to the outbound ro'
                                + 'utes.'
                                  ;
                      type string {
                        length 1..200 ;
                      }
                    }
                    container withdraw {
                      description 'Withdraw routes when state of track-group is'
                                + ' down.'
                                  ;
                      presence withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                      ncd:revise-date 2016-02-06 ;
                    }
                    container second-withdraw {
                      description 'Withdraw routes when state of the second tra'
                                + 'ck-group is down.'
                                  ;
                      presence second-withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                      ncd:revise-date 2018-07-12 ;
                    }
                  }
                  container advertise-map-uni {
                    description 'Specify route-map for conditional advertisemen'
                              + 't.'
                                ;
                    presence 'Specify route-map for conditional advertisement'
                             ;
                    leaf advertise-map-name {
                      description 'Advertise route-map name.'
                                  ;
                      type string {
                        length 1..200 ;
                      }
                      mandatory true ;
                    }
                    choice advertise-map {
                      description 'Specify route-map for conditional advertisem'
                                + 'ent.'
                                  ;
                      mandatory true ;
                      case exist-map {
                        description 'Advertise prefix only if prefix exists.'
                                    ;
                        leaf exist-map-name {
                          description 'Advertise prefix only if prefix exists.'
                                      ;
                          type string {
                            length 1..200 ;
                          }
                          mandatory true ;
                        }
                      }
                      case nonexist-map {
                        description 'Advertise prefix only if prefix does not e'
                                  + 'xist.'
                                    ;
                        leaf nonexist-map-name {
                          description 'Advertise prefix only if prefix does not'
                                    + ' exist.'
                                      ;
                          type string {
                            length 1..200 ;
                          }
                          mandatory true ;
                        }
                      }
                    }
                    ncd:revise-date 2016-11-15 ;
                  }
                  container route-filter-group {
                    description 'Specify a neighbor to join a route-filter-grou'
                              + 'p.'
                                ;
                    presence route-filter-group ;
                    leaf filter-group {
                      description 'Route filter group name (1-31 characters).'
                                  ;
                      type string {
                        length 1..31 ;
                      }
                      mandatory true ;
                    }
                    leaf next-hop-self {
                      description 'Disable the next hop calculation for this ne'
                                + 'ighbor.'
                                  ;
                      type empty ;
                    }
                    ncd:revise-date 2017-06-12 ;
                  }
                  leaf announce-sid {
                    description 'Enable Prefix-SID attribute for this neighbor.'
                                ;
                    type enumeration {
                      enum enable {
                        value 1 ;
                        description 'Enable Prefix-SID attribute for this neigh'
                                  + 'bor.'
                                    ;
                      }
                    }
                    ncd:revise-date 2018-05-14 ;
                  }
                  leaf soft-reconfig {
                    description 'Neighbor soft reconfiguration.'
                                ;
                    type enumeration {
                      enum soft-reconfiguration {
                        value 1 ;
                        description Soft-reconfiguration. ;
                      }
                      enum enforce-soft-reconfiguration {
                        value 2 ;
                        description 'Enforce soft-reconfiguration instead of se'
                                  + 'nding route-refresh.'
                                    ;
                      }
                    }
                    ncd:revise-date 2019-08-08 ;
                  }
                  leaf vpn-orf {
                    description 'Peer route-target ORF capability'
                                ;
                    type enumeration {
                      enum disable {
                        value 0 ;
                        description 'Disable peer route-target ORF capability'
                                    ;
                      }
                      enum enable {
                        value 1 ;
                        description 'Enable peer route-target ORF capability'
                                    ;
                      }
                      enum inherit {
                        value 2 ;
                        description 'If the neighbor joined a group, the status'
                                  + ' inherited from group.'
                                    ;
                      }
                    }
                    ncd:revise-date 2020-02-08 ;
                  }
                  leaf send-link-bw {
                    description 'Send link bandwidth to this neighbor.'
                                ;
                    type enumeration {
                      enum disable {
                        value 0 ;
                        description 'Disable peer send link bandwidth'
                                    ;
                      }
                      enum enable {
                        value 1 ;
                        description 'Enable peer send link bandwidth'
                                    ;
                      }
                      enum inherit {
                        value 2 ;
                        description 'If the neighbor joined a group, the status'
                                  + ' inherited from group.'
                                    ;
                      }
                    }
                    ncd:revise-date 2019-10-22 ;
                  }
                  container route-server-client {
                    description 'Set route server client only valid for ebgp pe'
                              + 'er.'
                                ;
                    presence route-server-client ;
                    leaf route-svr-client {
                      description 'Set route server client only valid for ebgp '
                                + 'peer.'
                                  ;
                      type empty ;
                      mandatory true ;
                    }
                    ncd:revise-date 2020-04-07 ;
                  }
                }
              }
              container neighbor-ipv6 {
                description 'Specify a IPv6 neighbor.'
                            ;
                list neighbor {
                  description 'Specify a neighbor.'
                              ;
                  key ipv6-addr ;
                  leaf ipv6-addr {
                    description 'Neighbor IPv6 address.'
                                ;
                    type ncd:ipv6-address ;
                  }
                  leaf joined-group {
                    description 'Only for read operation. The joined group name.'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf monitor {
                    description 'Config BMP monitor for the address family of t'
                              + 'his neighbor.'
                                ;
                    type enumeration {
                      enum disable {
                        value 2 ;
                      }
                      enum enable {
                        value 1 ;
                      }
                      enum inherit-global-config {
                        value 0 ;
                      }
                    }
                    ncd:revise-date 2019-07-29 ;
                  }
                  leaf advertise-maximum-prefix {
                    description 'Maximum number of prefix send to this peer.'
                                ;
                    type uint32 {
                      range 1..4294967295 ;
                    }
                  }
                  leaf allowas-in {
                    description 'Accept as-path with my AS present in it.'
                                ;
                    type uint32 {
                      range 1..10 ;
                    }
                  }
                  leaf as-path-loopcheck {
                    description 'Check as-path sending BGP routing to EBGP neig'
                              + 'hbor.'
                                ;
                    type empty ;
                  }
                  leaf maxas-in {
                    description 'Accept as-path not exceeded maxas-in.'
                                ;
                    type uint32 {
                      range 1..250 ;
                    }
                  }
                  leaf next-hop-self {
                    description 'Disable the next hop calculation for this neig'
                              + 'hbor.'
                                ;
                    type enumeration {
                      enum enable {
                        value 1 ;
                        description 'Apply next-hop-self for EBGP route.'
                                    ;
                      }
                      enum all {
                        value 2 ;
                        description 'Apply next-hop-self for both EBGP and IBGP'
                                  + ' route.'
                                    ;
                      }
                    }
                  }
                  choice nh-unchanged {
                    case next-hop-unchanged {
                      description 'NEXT_HOP of the IBGP path propagated unchang'
                                + 'ed to this neighbor.'
                                  ;
                      leaf next-hop-unchanged {
                        description 'Propagate next hop unchanged for IBGP path'
                                  + 's to this neighbor.'
                                    ;
                        type empty ;
                      }
                    }
                    case next-hop-unchanged-all {
                      description 'NEXT_HOP of either EBGP or IBGP path propaga'
                                + 'ted unchanged to this neighbor.'
                                  ;
                      leaf next-hop-unchanged-all {
                        description 'NEXT_HOP of either EBGP or IBGP path propa'
                                  + 'gated unchanged to this neighbor.'
                                    ;
                        type empty ;
                      }
                      ncd:revise-date 2020-04-07 ;
                    }
                  }
                  leaf remove-private-as {
                    description 'EBGP use to remove private AS number.'
                                ;
                    type enumeration {
                      enum disable {
                        value 0 ;
                      }
                      enum enable {
                        value 1 ;
                      }
                    }
                  }
                  leaf route-reflector-client {
                    description 'Set this neighbor as a client peer.'
                                ;
                    type empty ;
                  }
                  leaf send-community {
                    description 'Send community to this neighbor.'
                                ;
                    type empty ;
                  }
                  leaf send-large-community {
                    description 'Send Large-community to this neighbor.'
                                ;
                    type empty ;
                    ncd:revise-date 2020-04-16 ;
                  }
                  leaf send-med {
                    description 'Send metric attribute to this neighbor.'
                                ;
                    type empty ;
                  }
                  leaf inherit-igp-metric {
                    description 'Med attribute inherited from IGP metric before'
                              + ' sending updates.'
                                ;
                    type empty ;
                    ncd:revise-date 2017-07-25 ;
                  }
                  leaf split-update-group {
                    description 'Split neighbor from update group.'
                                ;
                    type empty ;
                  }
                  leaf weight {
                    description 'Set weight for routes from this neighbor.'
                                ;
                    type uint32 {
                      range 1..65535 ;
                    }
                  }
                  leaf aigp {
                    description 'Enable AIGP for this neighbor.'
                                ;
                    type empty ;
                    ncd:revise-date 2017-11-01 ;
                  }
                  leaf adv-tunnel-encap {
                    description 'Advertise tunnel encapsulation type'
                                ;
                    type enumeration {
                      enum mpls {
                        value 2 ;
                      }
                      enum srv6 {
                        value 4 ;
                      }
                    }
                    ncd:revise-date 2020-08-18 ;
                  }
                  container neighbor-extend {
                    description 'Specify a neighbor.'
                                ;
                    leaf additional-paths-receive {
                      description 'Receive additional paths from this neighbor.'
                                  ;
                      type empty ;
                    }
                    container maximum-prefix {
                      description 'The action that generated when threshold val'
                                + 'ue reached.'
                                  ;
                      presence 'The action that generated when threshold value '
                             + 'reached'
                               ;
                      leaf maximum-prefix-number {
                        description 'Maximum number of prefix limit.'
                                    ;
                        type uint32 {
                          range 1..4294967295 ;
                        }
                        mandatory true ;
                      }
                      leaf maximum-prefix-threshold {
                        description 'Threshold value(%) at which to generate a '
                                  + 'warning.'
                                    ;
                        type uint32 {
                          range 1..100 ;
                        }
                        mandatory true ;
                      }
                      choice maximum-prefix-action {
                        description 'The action that generated when threshold v'
                                  + 'alue reached.'
                                    ;
                        mandatory true ;
                        case peer-action {
                          description 'The action that generated when threshold'
                                    + ' value reached.'
                                      ;
                          leaf action {
                            description 'The action that generated when threshold value reached.'
                                        ;
                            type enumeration {
                              enum down {
                                value 0 ;
                                description 'Break down BGP connection after limit is exceeded.'
                                            ;
                              }
                              enum warning-only {
                                value 1 ;
                                description 'Only give warning message when limit is exceeded.'
                                            ;
                              }
                              enum drop-routes {
                                value 2 ;
                                description 'Drop routes that exceed the maximum-prefix.'
                                            ;
                              }
                            }
                            mandatory true ;
                          }
                        }
                        case restart {
                          description 'Restart BGP connection after limit is ex'
                                    + 'ceeded.'
                                      ;
                          leaf restart-time {
                            description 'Restart interval in minutes.'
                                        ;
                            type uint32 {
                              range 1..30000 ;
                            }
                            units min ;
                            mandatory true ;
                          }
                        }
                      }
                    }
                    leaf prefix-list-in-name {
                      description 'Apply prefix list to incoming routes.'
                                  ;
                      type string {
                        length 1..169 ;
                      }
                    }
                    leaf prefix-list-out-name {
                      description 'Apply  prefix list to outbound routes.'
                                  ;
                      type string {
                        length 1..169 ;
                      }
                    }
                    leaf route-map-in-name {
                      description 'Apply route-map to incoming routes.'
                                  ;
                      type string {
                        length 1..200 ;
                      }
                    }
                    leaf route-map-out-name {
                      description 'Apply route-map to outbound routes.'
                                  ;
                      type string {
                        length 1..200 ;
                      }
                    }
                    container diverse-path {
                      description 'Advertise diverse path to this neighbor.'
                                  ;
                      presence diverse-path ;
                      choice diverse-path {
                        description 'Advertise diverse path to this neighbor.'
                                    ;
                        mandatory true ;
                        case backup {
                          description 'Advertisement of the backup path.'
                                      ;
                          leaf backup {
                            description 'Advertisement of the backup path.'
                                        ;
                            type empty ;
                            mandatory true ;
                          }
                        }
                        case multipath {
                          description 'Sequence number of multipath.'
                                      ;
                          leaf sequence-number {
                            description 'Sequence number of multipath.'
                                        ;
                            type uint32 {
                              range 2..32 ;
                            }
                            mandatory true ;
                          }
                        }
                      }
                      leaf route-map {
                        description 'Apply route-map to neighbor.'
                                    ;
                        type string {
                          length 1..200 ;
                        }
                      }
                    }
                    container additional-paths-send {
                      description 'Send additional paths to this neighbor.'
                                  ;
                      choice additional-paths-send {
                        description 'Send additional paths to this neighbor.'
                                    ;
                        default send-one-path ;
                        case send-one-path {
                          description 'Send one additional path to this neighbo'
                                    + 'r.'
                                      ;
                          leaf send {
                            description 'Send additional paths to this neighbor.'
                                        ;
                            type empty ;
                          }
                        }
                        case send-multi-paths {
                          description 'Send additional multi-paths to this neig'
                                    + 'hbor.'
                                      ;
                          leaf paths-number {
                            description 'Number of paths for a prefix.'
                                        ;
                            type uint32 {
                              range 2..32 ;
                            }
                            mandatory true ;
                          }
                          leaf prefixlist {
                            description 'Prefixlist of filtering additional paths.'
                                        ;
                            type string {
                              length 1..169 ;
                            }
                          }
                        }
                      }
                    }
                    leaf routepolicy-in-name {
                      description 'Route policy name applied to the inbound rou'
                                + 'tes.'
                                  ;
                      type string {
                        length 1..200 ;
                      }
                    }
                    leaf routepolicy-out-name {
                      description 'Route policy name applied to the outbound ro'
                                + 'utes.'
                                  ;
                      type string {
                        length 1..200 ;
                      }
                    }
                    container withdraw {
                      description 'Withdraw routes when state of track-group is'
                                + ' down.'
                                  ;
                      presence withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                    }
                    container second-withdraw {
                      description 'Withdraw routes when state of the second tra'
                                + 'ck-group is down.'
                                  ;
                      presence second-withdraw ;
                      leaf track-group {
                        description 'Track-group name.'
                                    ;
                        type string {
                          length 1..31 ;
                        }
                        mandatory true ;
                      }
                      leaf route-map {
                        description 'Route-map name.'
                                    ;
                        type string {
                          length 1..200 ;
                        }
                      }
                      ncd:revise-date 2018-07-12 ;
                    }
                    ncd:revise-date 2016-07-07 ;
                  }
                  leaf label-per-nexthop {
                    status obsolete {
                      ncd:revise-date 2017-07-05 ;
                    }
                    description 'Allocate label  according to nexthop.'
                                ;
                    type empty ;
                    ncd:revise-date 2016-07-07 ;
                  }
                  leaf default-originate-all {
                    description 'Notify all VPN default route.'
                                ;
                    type empty ;
                    ncd:revise-date 2016-05-30 ;
                  }
                  leaf default-originate-routemap {
                    description 'Map external entry attributes into routing tab'
                              + 'le.'
                                ;
                    type string {
                      length 1..200 ;
                    }
                    ncd:revise-date 2020-07-28 ;
                  }
                  leaf default-originate-routepolicy {
                    description 'Set external entry attributes into routing tab'
                              + 'le.'
                                ;
                    type string {
                      length 1..200 ;
                    }
                    ncd:revise-date 2020-10-10 ;
                  }
                  container default-originate-vrf {
                    description 'Originate default route to this neighbor for c'
                              + 'ertain VRF.'
                                ;
                    list default-originate-vrf {
                      description 'Originate default route to this neighbor for'
                                + ' certain VRF.'
                                  ;
                      key vrf-name ;
                      leaf vrf-name {
                        description 'VPN Routing/Forwarding instance.'
                                    ;
                        type string {
                          length 1..32 ;
                        }
                      }
                      choice prefix-list {
                        description 'Prefix list name.'
                                    ;
                        case peer-list {
                          description 'Prefix list name of peer list.'
                                      ;
                          leaf peer-list-name {
                            description 'Prefix list name of peer list.'
                                        ;
                            type string {
                              length 1..169 ;
                            }
                          }
                          ncd:revise-date 2019-01-10 ;
                        }
                        case vrf-peer-list {
                          description 'Prefix list name of VRF routes list.'
                                      ;
                          leaf vrf-peer-list-name {
                            description 'Prefix list name of VRF routes list.'
                                        ;
                            type string {
                              length 1..169 ;
                            }
                          }
                          ncd:revise-date 2019-09-04 ;
                        }
                        ncd:revise-date 2019-01-10 ;
                      }
                    }
                    ncd:revise-date 2016-05-30 ;
                  }
                  container virtual {
                    description 'Set spoke PE.'
                                ;
                    presence virtual ;
                    leaf virtual-spoke {
                      description 'Enable spoke PE.'
                                  ;
                      type empty ;
                      mandatory true ;
                    }
                    leaf reflect-nexthop-self {
                      description 'Set nexthop self when reflection.'
                                  ;
                      type empty ;
                    }
                    leaf check-upstream-pe {
                      description 'Check upstream PE when advertising default r'
                                + 'oute.'
                                  ;
                      type empty ;
                      ncd:revise-date 2018-05-14 ;
                    }
                    leaf by-vrf {
                      description 'Send specific route by default-originate con'
                                + 'fig.'
                                  ;
                      type empty ;
                      ncd:revise-date 2019-12-31 ;
                    }
                    ncd:revise-date 2016-05-30 ;
                  }
                  container advertise-map-uni {
                    description 'Specify route-map for conditional advertisemen'
                              + 't.'
                                ;
                    presence 'Specify route-map for conditional advertisement'
                             ;
                    leaf advertise-map-name {
                      description 'Advertise route-map name.'
                                  ;
                      type string {
                        length 1..200 ;
                      }
                      mandatory true ;
                    }
                    choice advertise-map {
                      description 'Specify route-map for conditional advertisem'
                                + 'ent.'
                                  ;
                      mandatory true ;
                      case exist-map {
                        description 'Advertise prefix only if prefix exists.'
                                    ;
                        leaf exist-map-name {
                          description 'Advertise prefix only if prefix exists.'
                                      ;
                          type string {
                            length 1..200 ;
                          }
                          mandatory true ;
                        }
                      }
                      case nonexist-map {
                        description 'Advertise prefix only if prefix does not e'
                                  + 'xist.'
                                    ;
                        leaf nonexist-map-name {
                          description 'Advertise prefix only if prefix does not'
                                    + ' exist.'
                                      ;
                          type string {
                            length 1..200 ;
                          }
                          mandatory true ;
                        }
                      }
                    }
                    ncd:revise-date 2016-11-15 ;
                  }
                  container route-filter-group {
                    description 'Specify a neighbor to join a route-filter-grou'
                              + 'p.'
                                ;
                    presence route-filter-group ;
                    leaf filter-group {
                      description 'Route filter group name (1-31 characters).'
                                  ;
                      type string {
                        length 1..31 ;
                      }
                      mandatory true ;
                    }
                    leaf next-hop-self {
                      description 'Disable the next hop calculation for this ne'
                                + 'ighbor.'
                                  ;
                      type empty ;
                    }
                    ncd:revise-date 2017-06-12 ;
                  }
                  leaf announce-sid {
                    description 'Enable Prefix-SID attribute for this neighbor.'
                                ;
                    type enumeration {
                      enum enable {
                        value 1 ;
                        description 'Enable Prefix-SID attribute for this neigh'
                                  + 'bor.'
                                    ;
                      }
                    }
                    ncd:revise-date 2018-05-14 ;
                  }
                  leaf soft-reconfig {
                    description 'Neighbor soft reconfiguration.'
                                ;
                    type enumeration {
                      enum soft-reconfiguration {
                        value 1 ;
                        description Soft-reconfiguration. ;
                      }
                      enum enforce-soft-reconfiguration {
                        value 2 ;
                        description 'Enforce soft-reconfiguration instead of se'
                                  + 'nding route-refresh.'
                                    ;
                      }
                    }
                    ncd:revise-date 2019-08-08 ;
                  }
                  leaf vpn-orf {
                    description 'Peer route-target ORF capability'
                                ;
                    type enumeration {
                      enum disable {
                        value 0 ;
                        description 'Disable peer route-target ORF capability'
                                    ;
                      }
                      enum enable {
                        value 1 ;
                        description 'Enable peer route-target ORF capability'
                                    ;
                      }
                      enum inherit {
                        value 2 ;
                        description 'If the neighbor joined a group, the status'
                                  + ' inherited from group.'
                                    ;
                      }
                    }
                    ncd:revise-date 2020-02-08 ;
                  }
                  leaf send-link-bw {
                    description 'Send link bandwidth to this neighbor.'
                                ;
                    type enumeration {
                      enum disable {
                        value 0 ;
                        description 'Disable peer send link bandwidth'
                                    ;
                      }
                      enum enable {
                        value 1 ;
                        description 'Enable peer send link bandwidth'
                                    ;
                      }
                      enum inherit {
                        value 2 ;
                        description 'If the neighbor joined a group, the status'
                                  + ' inherited from group.'
                                    ;
                      }
                    }
                    ncd:revise-date 2019-10-22 ;
                  }
                  container route-server-client {
                    description 'Set route server client only valid for ebgp pe'
                              + 'er.'
                                ;
                    presence route-server-client ;
                    leaf route-svr-client {
                      description 'Set route server client only valid for ebgp '
                                + 'peer.'
                                  ;
                      type empty ;
                      mandatory true ;
                    }
                    ncd:revise-date 2020-04-07 ;
                  }
                }
              }
            }
            container additional-paths {
              description 'Additional paths in the BGP table.'
                          ;
              leaf selection-route-map {
                description 'Selection criteria to pick the additional paths.'
                            ;
                type string {
                  length 1..200 ;
                }
              }
              ncd:revise-date 2016-07-07 ;
            }
            container route-scan-time {
              description 'Adjust BGP route scan.'
                          ;
              presence 'The ability of BGP route scan.'
                       ;
              leaf interval-wait {
                description 'The interval of scan waiting. Default value is 500.'
                            ;
                type uint32 {
                  range 1..65535 ;
                }
                units ms ;
                mandatory true ;
              }
              leaf initial {
                description 'The initialization time of scan. Default value is '
                          + '50.'
                            ;
                type uint32 {
                  range 1..65535 ;
                }
                units ms ;
                mandatory true ;
              }
              leaf max-wait {
                description 'The max waiting time of scan. Default value is 500'
                          + '0.'
                            ;
                type uint32 {
                  range 1..65535 ;
                }
                units ms ;
                mandatory true ;
              }
              ncd:revise-date 2016-07-07 ;
            }
            leaf bgp-label {
              description 'Mpls label mode.'
                          ;
              type enumeration {
                enum per-vrf-by-rt {
                  value 0 ;
                  description 'Allocate label according to per-vrf and find VRF'
                            + ' according to route-target.'
                              ;
                }
                enum per-vrf-by-rd {
                  value 3 ;
                  description 'Allocate label according to per-vrf and find VRF'
                            + ' according to route-distinguisher.'
                              ;
                }
                enum per-nexthop {
                  value 1 ;
                  description 'Allocate label according to nexthop.'
                              ;
                }
                enum per-prefix {
                  value 2 ;
                  description 'Allocate label according to prefix.'
                              ;
                }
              }
              default per-vrf-by-rt ;
              ncd:revise-date 2016-07-07 ;
            }
            leaf label-per-nexthop {
              status obsolete {
                ncd:revise-date 2016-06-12 ;
              }
              description 'Allocate label according to nexthop.'
                          ;
              type empty ;
            }
            leaf vpn-frr-capability {
              description 'Enable FRR capability.'
                          ;
              type empty ;
              ncd:revise-date 2017-05-24 ;
            }
            leaf vpn-frr-wtr {
              description 'Set the WTR time.'
                          ;
              type int32 {
                range 1..12 ;
              }
              units min ;
              ncd:revise-date 2017-05-24 ;
            }
            container group-to-group {
              description 'Configure filter group to filter group route reflect'
                        + 'ion.'
                          ;
              presence group-to-group ;
              leaf reflection {
                description 'Reflection of routes is allowed.'
                            ;
                type empty ;
                mandatory true ;
              }
              leaf next-hop-self {
                description 'Disable the next hop calculation.'
                            ;
                type empty ;
              }
              ncd:revise-date 2018-08-04 ;
            }
            leaf import-l2vpn-evpn {
              description 'Import L2VPN EVPN route to VPNv6 unicast table.'
                          ;
              type enumeration {
                enum disable {
                  value 0 ;
                }
                enum enable {
                  value 1 ;
                }
              }
              default disable ;
              ncd:revise-date 2019-07-07 ;
            }
            leaf bgp-bestpath-origin {
              description 'bgp bestpath origin-from L3VPN neighbor or EVPN neig'
                        + 'hbor.'
                          ;
              type enumeration {
                enum l3vpn {
                  value 1 ;
                  description 'bgp bestpath origin-from L3VPN neighbor'
                              ;
                }
                enum evpn {
                  value 2 ;
                  description 'bgp bestpath origin-from EVPN neighbor'
                              ;
                }
              }
              ncd:revise-date 2019-08-08 ;
            }
            leaf vpn-orf {
              description 'Generate local route-target routes'
                          ;
              type enumeration {
                enum disable {
                  value 0 ;
                  description 'Disable generate local route-target routes'
                              ;
                }
                enum enable {
                  value 1 ;
                  description 'Enable generate local route-target routes'
                              ;
                }
              }
              ncd:revise-date 2020-02-08 ;
            }
            leaf slow-peer-detection {
              description 'Set slow peer detection.'
                          ;
              type enumeration {
                enum disable {
                  value 0 ;
                  description 'Disable slow peer detection'
                              ;
                }
                enum enable {
                  value 1 ;
                  description 'Enable slow peer detection'
                              ;
                }
              }
              default disable ;
              ncd:revise-date 2020-09-08 ;
            }
            leaf slow-peer-detection-threshold {
              description 'Set threshold time for slow peer.Default value is 30'
                        + '0.'
                          ;
              type uint32 {
                range 120..3600 {
                  description 'Threshold time range.'
                              ;
                }
              }
              units s ;
              default 300 ;
              ncd:revise-date 2020-09-08 ;
            }
            leaf slow-peer-detection-recover {
              description 'Set recover time for slow peer.Default value is 300.'
                          ;
              type uint32 {
                range 120..3600 {
                  description 'Recover time range.'
                              ;
                }
              }
              units s ;
              default 300 ;
              ncd:revise-date 2020-09-08 ;
            }
            leaf nexthop-recursive-lookup-srv6-sid {
              description 'Enable or disable bgp nexthop recursive-lookup srv6-'
                        + 'sid'
                          ;
              type enumeration {
                enum disable {
                  value 0 ;
                }
                enum enable {
                  value 1 ;
                }
              }
              default disable ;
              ncd:revise-date 2020-10-28 ;
            }
            ncd:revise-date 2016-01-06 ;
          }
          container address-family-ipv6-vpn-mcast {
            description 'Configuration in address family VPNv6 mcast mode.'
                        ;
            presence 'VPNv6 mcast address family.'
                     ;
            container neighbor-ipv4 {
              description 'Specify a IPv4 neighbor.'
                          ;
              list neighbor {
                description 'Specify a neighbor.'
                            ;
                key ipv4-address ;
                leaf ipv4-address {
                  description 'Neighbor IPv4 address.'
                              ;
                  type ncd:ipv4-address ;
                }
                leaf activate {
                  description 'Enable the address family for this neighbor.'
                              ;
                  type enumeration {
                    enum enable {
                      value 1 ;
                    }
                  }
                }
                leaf split-update-group {
                  description 'Split neighbor from update group.'
                              ;
                  type empty ;
                }
                leaf route-reflector-client {
                  description 'Set this neighbor as a client peer.'
                              ;
                  type empty ;
                }
                choice nh-unchanged {
                  case next-hop-unchanged {
                    description 'NEXT_HOP of the IBGP path propagated unchanged'
                              + ' to this neighbor.'
                                ;
                    leaf next-hop-unchanged {
                      description 'Propagate next hop unchanged for IBGP paths '
                                + 'to this neighbor.'
                                  ;
                      type empty ;
                    }
                    ncd:revise-date 2019-06-04 ;
                  }
                  case next-hop-unchanged-all {
                    description 'NEXT_HOP of either EBGP or IBGP path propagate'
                              + 'd unchanged to this neighbor.'
                                ;
                    leaf next-hop-unchanged-all {
                      description 'NEXT_HOP of either EBGP or IBGP path propaga'
                                + 'ted unchanged to this neighbor.'
                                  ;
                      type empty ;
                    }
                    ncd:revise-date 2020-04-07 ;
                  }
                }
                container neighbor-extend {
                  description 'Specify a neighbor.'
                              ;
                  leaf route-map-in-name {
                    description 'Apply route-map to incoming routes.'
                                ;
                    type string {
                      length 1..200 ;
                    }
                  }
                  leaf route-map-out-name {
                    description 'Apply route-map to outbound routes.'
                                ;
                    type string {
                      length 1..200 ;
                    }
                  }
                  leaf announce-msid {
                    description 'Enable multicast service identifier attribute '
                              + 'for this neighbor.'
                                ;
                    type empty ;
                    ncd:revise-date 2021-04-21 ;
                  }
                  leaf non-segmented {
                    description 'Non-segmented inter-AS/intra-AS tunnels.'
                                ;
                    type empty ;
                    ncd:revise-date 2021-04-21 ;
                  }
                  ncd:revise-date 2020-03-02 ;
                }
                leaf weight {
                  description 'Set weight for routes from this neighbor.'
                              ;
                  type uint32 {
                    range 1..65535 ;
                  }
                  ncd:revise-date 2020-03-02 ;
                }
              }
            }
            leaf default-metric {
              description 'Set metric of BGP routes without MED.'
                          ;
              type uint32 {
                range 0..4294967295 ;
              }
              default 0 ;
              ncd:revise-date 2019-04-10 ;
            }
            ncd:revise-date 2016-01-06 ;
          }
          container address-family-ipv6-vpn-multi {
            description 'Configuration in address family VPNv6 multicast mode.'
                        ;
            presence 'VPNv6 multicast address family.'
                     ;
            container neighbor-ipv4 {
              description 'Specify a IPv4 neighbor.'
                          ;
              list neighbor {
                description 'Specify a neighbor.'
                            ;
                key ipv4-address ;
                leaf ipv4-address {
                  description 'Neighbor IPv4 address.'
                              ;
                  type ncd:ipv4-address ;
                }
                leaf activate {
                  description 'Enable the address family for this neighbor.'
                              ;
                  type enumeration {
                    enum enable {
                      value 1 ;
                    }
                  }
                }
                leaf split-update-group {
                  description 'Split neighbor from update group.'
                              ;
                  type empty ;
                }
                leaf route-reflector-client {
                  description 'Set this neighbor as a client peer.'
                              ;
                  type empty ;
                }
                choice nh-unchanged {
                  case next-hop-unchanged {
                    description 'NEXT_HOP of the IBGP path propagated unchanged'
                              + ' to this neighbor.'
                                ;
                    leaf next-hop-unchanged {
                      description 'Propagate next hop unchanged for IBGP paths '
                                + 'to this neighbor.'
                                  ;
                      type empty ;
                    }
                    ncd:revise-date 2019-06-04 ;
                  }
                  case next-hop-unchanged-all {
                    description 'NEXT_HOP of either EBGP or IBGP path propagate'
                              + 'd unchanged to this neighbor.'
                                ;
                    leaf next-hop-unchanged-all {
                      description 'NEXT_HOP of either EBGP or IBGP path propaga'
                                + 'ted unchanged to this neighbor.'
                                  ;
                      type empty ;
                    }
                    ncd:revise-date 2020-04-07 ;
                  }
                }
                container neighbor-extend {
                  description 'Specify a neighbor.'
                              ;
                  leaf route-map-in-name {
                    description 'Apply route-map to incoming routes.'
                                ;
                    type string {
                      length 1..200 ;
                    }
                  }
                  leaf route-map-out-name {
                    description 'Apply route-map to outbound routes.'
                                ;
                    type string {
                      length 1..200 ;
                    }
                  }
                  ncd:revise-date 2020-03-02 ;
                }
                leaf weight {
                  description 'Set weight for routes from this neighbor.'
                              ;
                  type uint32 {
                    range 1..65535 ;
                  }
                  ncd:revise-date 2020-03-02 ;
                }
                container route-server-client {
                  description 'Set route server client only valid for ebgp peer.'
                              ;
                  presence route-server-client ;
                  leaf route-svr-client {
                    description 'Set route server client only valid for ebgp pe'
                              + 'er.'
                                ;
                    type empty ;
                    mandatory true ;
                  }
                  ncd:revise-date 2020-04-07 ;
                }
              }
            }
            leaf default-metric {
              description 'Set metric of BGP routes without MED.'
                          ;
              type uint32 {
                range 0..4294967295 ;
              }
              default 0 ;
              ncd:revise-date 2019-04-10 ;
            }
            ncd:revise-date 2016-01-06 ;
          }
          container rpki-rtr {
            description 'Configuration in RPKI-RTR mode.'
                        ;
            leaf rtr-polling-period {
              description 'Set RPKI-RTR polling period.'
                          ;
              type uint32 {
                range 15..3600 ;
              }
              default 300 ;
            }
            container neighbor {
              description 'Specify a RPKI-RTR neighbor.'
                          ;
              container neighbor-ipv4 {
                description 'Specify a RPKI-RTR IPv4 neighbor.'
                            ;
                list neighbor {
                  description 'Specify a RPKI-RTR IPv4 neighbor.'
                              ;
                  key ipv4-addr ;
                  leaf ipv4-addr {
                    description 'Neighbor IPv4 address.'
                                ;
                    type ncd:ipv4-address ;
                  }
                  leaf port {
                    description 'Specify a port number of RPKI-RTR neighbor.'
                                ;
                    type uint32 {
                      range 1..65535 ;
                    }
                  }
                  leaf rtr-prefence {
                    description 'Set a preference value of the neighbor.'
                                ;
                    type uint32 {
                      range 1..10 ;
                    }
                  }
                  container password {
                    description 'Set a password of the neighbor.'
                                ;
                    choice password {
                      description 'Set a password of the neighbor.'
                                  ;
                      default encrypted-words ;
                      case clear-words {
                        description 'Specify the clear password (1-80 character'
                                  + 's).'
                                    ;
                        leaf clear-words {
                          description 'Specify the clear password (1-80 charact'
                                    + 'ers).'
                                      ;
                          type string {
                            length 1..80 ;
                          }
                        }
                      }
                      case encrypted-words {
                        description 'Specify the encrypted password.'
                                    ;
                        leaf encrypted-words {
                          description 'Specify the encrypted password.'
                                      ;
                          type string {
                            length 64..172 ;
                          }
                        }
                      }
                    }
                  }
                  leaf keychain-name {
                    description 'Keychain name associated to peer for authentic'
                              + 'ation.'
                                ;
                    type string {
                      length 1..31 ;
                    }
                    ncd:revise-date 2016-03-07 ;
                  }
                  container maximum-roa {
                    description 'The action that generated when threshold value'
                              + ' reached.'
                                ;
                    presence 'The action that generated when threshold value re'
                           + 'ached'
                             ;
                    leaf maximum-roa-threshold {
                      description 'Threshold value(%) at which to generate a wa'
                                + 'rning.'
                                  ;
                      type uint32 {
                        range 1..100 ;
                      }
                      mandatory true ;
                    }
                    leaf maximum-roa-number {
                      description 'Maximum number of roa limit.'
                                  ;
                      type uint32 {
                        range 1..4294967295 ;
                      }
                      mandatory true ;
                    }
                    container maximum-roa-action {
                      description 'The action that generated when threshold val'
                                + 'ue reached.'
                                  ;
                      choice maximum-roa-action {
                        description 'The action that generated when threshold v'
                                  + 'alue reached.'
                                    ;
                        mandatory true ;
                        case peer-action {
                          description 'The action that generated when threshold'
                                    + ' value reached.'
                                      ;
                          leaf action {
                            description 'The action that generated when threshold value reached.'
                                        ;
                            type enumeration {
                              enum warning-only {
                                value 1 ;
                                description 'Only give warning message when limit is exceeded.'
                                            ;
                              }
                              enum drop-roa {
                                value 2 ;
                                description 'Drop roa that exceed the maximum-prefix.'
                                            ;
                              }
                              enum down {
                                value 0 ;
                                description 'Break down RPKI connection after limit is exceeded.'
                                            ;
                              }
                            }
                            mandatory true ;
                          }
                        }
                        case restart {
                          description 'Restart RPKI connection after limit is e'
                                    + 'xceeded.'
                                      ;
                          leaf restart-time {
                            description 'Restart interval in minutes.'
                                        ;
                            type uint32 {
                              range 1..30000 ;
                            }
                            units min ;
                            mandatory true ;
                          }
                        }
                      }
                    }
                    ncd:revise-date 2020-12-20 ;
                  }
                }
              }
              container neighbor-ipv6 {
                description 'Specify a RPKI-RTR IPV6 neighbor.'
                            ;
                list neighbor {
                  description 'Specify a RPKI-RTR IPV6 neighbor.'
                              ;
                  key ipv6-addr ;
                  leaf ipv6-addr {
                    description 'Neighbor IPv6 address.'
                                ;
                    type ncd:ipv6-address ;
                  }
                  leaf port {
                    description 'Specify a port number of RPKI-RTR neighbor.'
                                ;
                    type uint32 {
                      range 1..65535 ;
                    }
                  }
                  leaf rtr-prefence {
                    description 'Set a preference value of the neighbor.'
                                ;
                    type uint32 {
                      range 1..10 ;
                    }
                  }
                  container password {
                    description 'Set a password of the neighbor.'
                                ;
                    choice password {
                      description 'Set a password of the neighbor.'
                                  ;
                      default encrypted-words ;
                      case clear-words {
                        description 'Specify the clear password (1-80 character'
                                  + 's).'
                                    ;
                        leaf clear-words {
                          description 'The clear password (1-80 characters).'
                                      ;
                          type string {
                            length 1..80 ;
                          }
                        }
                      }
                      case encrypted-words {
                        description 'Specify the encrypted password.'
                                    ;
                        leaf encrypted-words {
                          description 'Specify the encrypted password.'
                                      ;
                          type string {
                            length 64..172 ;
                          }
                        }
                      }
                    }
                  }
                  leaf keychain-name {
                    description 'Keychain name associated to peer for authentic'
                              + 'ation.'
                                ;
                    type string {
                      length 1..31 ;
                    }
                    ncd:revise-date 2016-03-07 ;
                  }
                  container maximum-roa {
                    description 'The action that generated when threshold value'
                              + ' reached.'
                                ;
                    presence 'The action that generated when threshold value re'
                           + 'ached'
                             ;
                    leaf maximum-roa-threshold {
                      description 'Threshold value(%) at which to generate a wa'
                                + 'rning.'
                                  ;
                      type uint32 {
                        range 1..100 ;
                      }
                      mandatory true ;
                    }
                    leaf maximum-roa-number {
                      description 'Maximum number of roa limit.'
                                  ;
                      type uint32 {
                        range 1..4294967295 ;
                      }
                      mandatory true ;
                    }
                    container maximum-roa-action {
                      description 'The action that generated when threshold val'
                                + 'ue reached.'
                                  ;
                      choice maximum-roa-action {
                        description 'The action that generated when threshold v'
                                  + 'alue reached.'
                                    ;
                        mandatory true ;
                        case peer-action {
                          description 'The action that generated when threshold'
                                    + ' value reached.'
                                      ;
                          leaf action {
                            description 'The action that generated when threshold value reached.'
                                        ;
                            type enumeration {
                              enum warning-only {
                                value 1 ;
                                description 'Only give warning message when limit is exceeded.'
                                            ;
                              }
                              enum drop-roa {
                                value 2 ;
                                description 'Drop roa that exceed the maximum-prefix.'
                                            ;
                              }
                              enum down {
                                value 0 ;
                                description 'Break down RPKI connection after limit is exceeded.'
                                            ;
                              }
                            }
                            mandatory true ;
                          }
                        }
                        case restart {
                          description 'Restart RPKI connection after limit is e'
                                    + 'xceeded.'
                                      ;
                          leaf restart-time {
                            description 'Restart interval in minutes.'
                                        ;
                            type uint32 {
                              range 1..30000 ;
                            }
                            units min ;
                            mandatory true ;
                          }
                        }
                      }
                    }
                    ncd:revise-date 2020-12-20 ;
                  }
                }
              }
            }
            ncd:revise-date 2016-01-06 ;
          }
          container bmp {
            description 'Configuration in BMP mode.'
                        ;
            leaf listen-port {
              description 'Set listening port.'
                          ;
              type uint32 {
                range 1025..65535 ;
              }
            }
            leaf enable-or-disable {
              description 'Enable or disable BMP.'
                          ;
              type enumeration {
                enum enable {
                  value 0 ;
                  description 'Enable BMP.'
                              ;
                }
                enum disable {
                  value 1 ;
                  description 'Disable BMP.'
                              ;
                }
              }
              default enable ;
            }
            leaf monitor-all-peers {
              description 'Enable or disable BMP monitor all peers.'
                          ;
              type enumeration {
                enum enable {
                  value 1 ;
                  description 'Enable BMP monitor all peers.'
                              ;
                }
                enum disable {
                  value 0 ;
                  description 'Disable BMP monitor all peers.'
                              ;
                }
              }
              default disable ;
              ncd:revise-date 2019-07-29 ;
            }
            leaf statistics-timer {
              description 'Set statistics timer.'
                          ;
              type uint32 {
                range 15..65535 ;
              }
              ncd:revise-date 2019-07-29 ;
            }
            leaf route-mode {
              description 'Configure the route type that BMP reports to the mon'
                        + 'itoring server.'
                          ;
              type enumeration {
                enum post-policy {
                  value 0 ;
                }
                enum pre-policy {
                  value 1 ;
                }
              }
              default post-policy ;
              ncd:revise-date 2019-07-29 ;
            }
            container neighbor {
              description 'Specify a neighbor.'
                          ;
              container neighbor {
                description 'Specify a neighbor.'
                            ;
                container neighbor-ipv4 {
                  description 'Specify a IPv4 neighbor.'
                              ;
                  list neighbor {
                    description 'Specify a neighbor.'
                                ;
                    key ipv4-address ;
                    leaf ipv4-address {
                      description 'Neighbor IPv4 address.'
                                  ;
                      type ncd:ipv4-address ;
                    }
                    leaf station-address {
                      description 'Create BMP neighbor.'
                                  ;
                      type empty ;
                    }
                    leaf station-port {
                      description 'Set BMP port number.'
                                  ;
                      type uint32 {
                        range 1..65535 ;
                      }
                    }
                    leaf passive-only {
                      status obsolete {
                        ncd:revise-date 2020-02-03 ;
                      }
                      description 'Establish a connection passively.'
                                  ;
                      type empty ;
                    }
                    leaf active-only {
                      status obsolete {
                        ncd:revise-date 2020-02-03 ;
                      }
                      description 'Establish a connection actively.'
                                  ;
                      type empty ;
                    }
                    leaf shutdown {
                      description 'Shutdown the connection.'
                                  ;
                      type empty ;
                    }
                    leaf update-source {
                      description 'Specify the interface of the neighbor to bui'
                                + 'ld link.'
                                  ;
                      type ncd:ifname {
                        length 1..31 ;
                      }
                    }
                    leaf connect-retry-interval {
                      description 'Set data of connect-retry timer for this nei'
                                + 'ghbor.'
                                  ;
                      type uint32 {
                        range 1..65535 ;
                      }
                      units s ;
                      ncd:revise-date 2019-12-05 ;
                    }
                    container connection {
                      description 'Set BMP connection type.'
                                  ;
                      choice connection {
                        description 'Set BMP connection type.'
                                    ;
                        case passive-only {
                          description 'Establish a connection passively.'
                                      ;
                          leaf passive-only {
                            description 'Establish a connection passively.'
                                        ;
                            type empty ;
                          }
                        }
                        case active-only {
                          description 'Establish a connection actively.'
                                      ;
                          leaf active-only {
                            description 'Establish a connection actively.'
                                        ;
                            type empty ;
                          }
                        }
                      }
                      ncd:revise-date 2020-02-03 ;
                    }
                  }
                }
                container neighbor-ipv6 {
                  description 'Specify a IPv6 neighbor.'
                              ;
                  list neighbor {
                    description 'Specify a neighbor.'
                                ;
                    key ipv6-address ;
                    leaf ipv6-address {
                      description 'Neighbor IPv6 address.'
                                  ;
                      type ncd:ipv6-address ;
                    }
                    leaf station-address {
                      description 'Create BMP neighbor.'
                                  ;
                      type empty ;
                    }
                    leaf station-port {
                      description 'Set BMP port number.'
                                  ;
                      type uint32 {
                        range 1..65535 ;
                      }
                    }
                    leaf passive-only {
                      status obsolete {
                        ncd:revise-date 2020-02-03 ;
                      }
                      description 'Establish a connection passively.'
                                  ;
                      type empty ;
                    }
                    leaf active-only {
                      status obsolete {
                        ncd:revise-date 2020-02-03 ;
                      }
                      description 'Establish a connection actively.'
                                  ;
                      type empty ;
                    }
                    leaf shutdown {
                      description 'Shutdown the connection.'
                                  ;
                      type empty ;
                    }
                    leaf update-source {
                      description 'Specify the interface of the neighbor to bui'
                                + 'ld link.'
                                  ;
                      type ncd:ifname {
                        length 1..31 ;
                      }
                    }
                    leaf connect-retry-interval {
                      description 'Set data of connect-retry timer for this nei'
                                + 'ghbor.'
                                  ;
                      type uint32 {
                        range 1..65535 ;
                      }
                      units s ;
                      ncd:revise-date 2019-12-05 ;
                    }
                    container connection {
                      description 'Set BMP connection type.'
                                  ;
                      choice connection {
                        description 'Set BMP connection type.'
                                    ;
                        case passive-only {
                          description 'Establish a connection passively.'
                                      ;
                          leaf passive-only {
                            description 'Establish a connection passively.'
                                        ;
                            type empty ;
                          }
                        }
                        case active-only {
                          description 'Establish a connection actively.'
                                      ;
                          leaf active-only {
                            description 'Establish a connection actively.'
                                        ;
                            type empty ;
                          }
                        }
                      }
                      ncd:revise-date 2020-02-03 ;
                    }
                  }
                }
              }
              container neighbor-vrf {
                description 'Specify a VRF neighbor.'
                            ;
                container neighbor-ipv4 {
                  description 'Specify a IPv4 neighbor.'
                              ;
                  list neighbor {
                    description 'Specify a neighbor.'
                                ;
                    key 'ipv4-address vrf-name'
                        ;
                    leaf ipv4-address {
                      description 'Neighbor IPv4 address.'
                                  ;
                      type ncd:ipv4-address ;
                    }
                    leaf vrf-name {
                      description 'VRF name.'
                                  ;
                      type string {
                        length 1..32 ;
                      }
                    }
                    leaf station-address {
                      description 'Create BMP neighbor.'
                                  ;
                      type empty ;
                    }
                    leaf station-port {
                      description 'Set BMP port number.'
                                  ;
                      type uint32 {
                        range 1..65535 ;
                      }
                    }
                    leaf passive-only {
                      status obsolete {
                        ncd:revise-date 2020-02-03 ;
                      }
                      description 'Establish a connection passively.'
                                  ;
                      type empty ;
                    }
                    leaf active-only {
                      status obsolete {
                        ncd:revise-date 2020-02-03 ;
                      }
                      description 'Establish a connection actively.'
                                  ;
                      type empty ;
                    }
                    leaf shutdown {
                      description 'Shutdown the connection.'
                                  ;
                      type empty ;
                    }
                    leaf update-source {
                      description 'Specify the interface of the neighbor to bui'
                                + 'ld link.'
                                  ;
                      type ncd:ifname {
                        length 1..31 ;
                      }
                    }
                    leaf connect-retry-interval {
                      description 'Set data of connect-retry timer for this nei'
                                + 'ghbor.'
                                  ;
                      type uint32 {
                        range 1..65535 ;
                      }
                      units s ;
                      ncd:revise-date 2019-12-05 ;
                    }
                    container connection {
                      description 'Set BMP connection type.'
                                  ;
                      choice connection {
                        description 'Set BMP connection type.'
                                    ;
                        case passive-only {
                          description 'Establish a connection passively.'
                                      ;
                          leaf passive-only {
                            description 'Establish a connection passively.'
                                        ;
                            type empty ;
                          }
                        }
                        case active-only {
                          description 'Establish a connection actively.'
                                      ;
                          leaf active-only {
                            description 'Establish a connection actively.'
                                        ;
                            type empty ;
                          }
                        }
                      }
                      ncd:revise-date 2020-02-03 ;
                    }
                  }
                }
                container neighbor-ipv6 {
                  description 'Specify a IPv6 neighbor.'
                              ;
                  list neighbor {
                    description 'Specify a neighbor.'
                                ;
                    key 'ipv6-address vrf-name'
                        ;
                    leaf ipv6-address {
                      description 'Neighbor IPv6 address.'
                                  ;
                      type ncd:ipv6-address ;
                    }
                    leaf vrf-name {
                      description 'VRF name.'
                                  ;
                      type string {
                        length 1..32 ;
                      }
                    }
                    leaf station-address {
                      description 'Create BMP neighbor.'
                                  ;
                      type empty ;
                    }
                    leaf station-port {
                      description 'Set BMP port number.'
                                  ;
                      type uint32 {
                        range 1..65535 ;
                      }
                    }
                    leaf passive-only {
                      status obsolete {
                        ncd:revise-date 2020-02-03 ;
                      }
                      description 'Establish a connection passively.'
                                  ;
                      type empty ;
                    }
                    leaf active-only {
                      status obsolete {
                        ncd:revise-date 2020-02-03 ;
                      }
                      description 'Establish a connection actively.'
                                  ;
                      type empty ;
                    }
                    leaf shutdown {
                      description 'Shutdown the connection.'
                                  ;
                      type empty ;
                    }
                    leaf update-source {
                      description 'Specify the interface of the neighbor to bui'
                                + 'ld link.'
                                  ;
                      type ncd:ifname {
                        length 1..31 ;
                      }
                    }
                    leaf connect-retry-interval {
                      description 'Set data of connect-retry timer for this nei'
                                + 'ghbor.'
                                  ;
                      type uint32 {
                        range 1..65535 ;
                      }
                      units s ;
                      ncd:revise-date 2019-12-05 ;
                    }
                    container connection {
                      description 'Set BMP connection type.'
                                  ;
                      choice connection {
                        description 'Set BMP connection type.'
                                    ;
                        case passive-only {
                          description 'Establish a connection passively.'
                                      ;
                          leaf passive-only {
                            description 'Establish a connection passively.'
                                        ;
                            type empty ;
                          }
                        }
                        case active-only {
                          description 'Establish a connection actively.'
                                      ;
                          leaf active-only {
                            description 'Establish a connection actively.'
                                        ;
                            type empty ;
                          }
                        }
                      }
                      ncd:revise-date 2020-02-03 ;
                    }
                  }
                }
              }
            }
            ncd:revise-date 2016-01-06 ;
          }
          container address-family-ipv4-flowspec {
            description 'Configuration in address family IPv4 flow specificatio'
                      + 'n mode.'
                        ;
            presence 'IPv4 flow specification address family.'
                     ;
            container neighbor-ipv4-flowspec {
              description 'Specify a neighbor.'
                          ;
              presence neighbor-ipv4-flowspec ;
              container neighbor-group {
                description 'Specify a peergroup neighbor.'
                            ;
                list neighbor-peergroup {
                  description 'Specify a neighbor.'
                              ;
                  key neighbor-group ;
                  leaf neighbor-group {
                    description 'Peer group name (1-31 characters).'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf allowas-in {
                    description 'Accept as-path with my AS present in it.'
                                ;
                    type uint32 {
                      range 1..10 ;
                    }
                    ncd:revise-date 2020-08-11 ;
                  }
                  leaf route-reflector-client {
                    description 'Set this neighbor as a client peer.'
                                ;
                    type empty ;
                  }
                  leaf validation-disable-destination {
                    description 'Disable IPv4 Flowspec destination address vali'
                              + 'dation.'
                                ;
                    type empty ;
                  }
                  leaf validation-disable-redirect {
                    description 'Disable IPv4 Flowspec redirect nexthop validat'
                              + 'ion.'
                                ;
                    type empty ;
                  }
                  leaf send-community {
                    description 'Send community to this neighbor.'
                                ;
                    type empty ;
                    ncd:revise-date 2019-07-24 ;
                  }
                  leaf send-large-community {
                    description 'Send Large-community to this neighbor.'
                                ;
                    type empty ;
                    ncd:revise-date 2020-04-16 ;
                  }
                  container neighbor-extend {
                    description 'Specify a neighbor.'
                                ;
                    leaf route-map-in-name {
                      description 'Apply route-map to incoming routes.'
                                  ;
                      type string {
                        length 1..200 ;
                      }
                    }
                    leaf route-map-out-name {
                      description 'Apply route-map to outbound routes.'
                                  ;
                      type string {
                        length 1..200 ;
                      }
                    }
                    ncd:revise-date 2019-07-24 ;
                  }
                }
              }
              container neighbor-ipv4 {
                description 'Specify a IPv4 neighbor.'
                            ;
                list neighbor {
                  description 'Specify a neighbor.'
                              ;
                  key ipv4-addr ;
                  leaf ipv4-addr {
                    description 'Neighbor IPv4 address.'
                                ;
                    type ncd:ipv4-address ;
                  }
                  leaf joined-group {
                    description 'Only for read operation. The joined group name.'
                                ;
                    type string {
                      length 1..31 ;
                    }
                    ncd:revise-date 2016-05-16 ;
                  }
                  leaf activate {
                    description 'Enable the address family for this neighbor.'
                                ;
                    type enumeration {
                      enum disable {
                        value 0 ;
                      }
                      enum enable {
                        value 1 ;
                      }
                    }
                  }
                  leaf allowas-in {
                    description 'Accept as-path with my AS present in it.'
                                ;
                    type uint32 {
                      range 1..10 ;
                    }
                    ncd:revise-date 2020-08-11 ;
                  }
                  leaf route-reflector-client {
                    description 'Set this neighbor as a client peer.'
                                ;
                    type empty ;
                  }
                  leaf validation-disable-destination {
                    description 'Disable IPv4 Flowspec destination address vali'
                              + 'dation.'
                                ;
                    type empty ;
                  }
                  leaf validation-disable-redirect {
                    description 'Disable IPv4 Flowspec redirect nexthop validat'
                              + 'ion.'
                                ;
                    type empty ;
                  }
                  leaf send-community {
                    description 'Send community to this neighbor.'
                                ;
                    type empty ;
                    ncd:revise-date 2019-07-24 ;
                  }
                  leaf send-large-community {
                    description 'Send Large-community to this neighbor.'
                                ;
                    type empty ;
                    ncd:revise-date 2020-04-16 ;
                  }
                  container neighbor-extend {
                    description 'Specify a neighbor.'
                                ;
                    leaf route-map-in-name {
                      description 'Apply route-map to incoming routes.'
                                  ;
                      type string {
                        length 1..200 ;
                      }
                    }
                    leaf route-map-out-name {
                      description 'Apply route-map to outbound routes.'
                                  ;
                      type string {
                        length 1..200 ;
                      }
                    }
                    ncd:revise-date 2019-07-24 ;
                  }
                }
              }
            }
            leaf default-metric {
              description 'Set metric of BGP routes without MED.'
                          ;
              type uint32 {
                range 0..4294967295 ;
              }
              default 0 ;
              ncd:revise-date 2019-04-10 ;
            }
            ncd:revise-date 2016-04-08 ;
          }
          container address-family-vpnv4-flowspec {
            description 'Configuration in address family VPNv4 flow specificati'
                      + 'on mode.'
                        ;
            presence 'VPNv4 flow specification address family.'
                     ;
            container neighbor-vpnv4-flowspec {
              description 'Specify a neighbor.'
                          ;
              presence neighbor-vpnv4-flowspec ;
              container neighbor-group {
                description 'Specify a peergroup neighbor.'
                            ;
                list neighbor-peergroup {
                  description 'Specify a neighbor.'
                              ;
                  key neighbor-group ;
                  leaf neighbor-group {
                    description 'Peer group name (1-31 characters).'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf allowas-in {
                    description 'Accept as-path with my AS present in it.'
                                ;
                    type uint32 {
                      range 1..10 ;
                    }
                    ncd:revise-date 2020-08-11 ;
                  }
                  leaf route-reflector-client {
                    description 'Set this neighbor as a client peer.'
                                ;
                    type empty ;
                  }
                  leaf send-community {
                    description 'Send community to this neighbor.'
                                ;
                    type empty ;
                    ncd:revise-date 2019-07-24 ;
                  }
                  leaf send-large-community {
                    description 'Send Large-community to this neighbor.'
                                ;
                    type empty ;
                    ncd:revise-date 2020-04-16 ;
                  }
                  container neighbor-extend {
                    description 'Specify a neighbor.'
                                ;
                    leaf route-map-in-name {
                      description 'Apply route-map to incoming routes.'
                                  ;
                      type string {
                        length 1..200 ;
                      }
                    }
                    leaf route-map-out-name {
                      description 'Apply route-map to outbound routes.'
                                  ;
                      type string {
                        length 1..200 ;
                      }
                    }
                    ncd:revise-date 2019-07-24 ;
                  }
                }
              }
              container neighbor-ipv4 {
                description 'Specify a IPv4 neighbor.'
                            ;
                list neighbor {
                  description 'Specify a neighbor.'
                              ;
                  key ipv4-addr ;
                  leaf ipv4-addr {
                    description 'Neighbor IPv4 address.'
                                ;
                    type ncd:ipv4-address ;
                  }
                  leaf joined-group {
                    description 'Only for read operation. The joined group name.'
                                ;
                    type string {
                      length 1..31 ;
                    }
                    ncd:revise-date 2016-05-16 ;
                  }
                  leaf activate {
                    description 'Enable the address family for this neighbor.'
                                ;
                    type enumeration {
                      enum disable {
                        value 0 ;
                      }
                      enum enable {
                        value 1 ;
                      }
                    }
                  }
                  leaf allowas-in {
                    description 'Accept as-path with my AS present in it.'
                                ;
                    type uint32 {
                      range 1..10 ;
                    }
                    ncd:revise-date 2020-08-11 ;
                  }
                  leaf route-reflector-client {
                    description 'Set this neighbor as a client peer.'
                                ;
                    type empty ;
                  }
                  leaf send-community {
                    description 'Send community to this neighbor.'
                                ;
                    type empty ;
                    ncd:revise-date 2019-07-24 ;
                  }
                  leaf send-large-community {
                    description 'Send Large-community to this neighbor.'
                                ;
                    type empty ;
                    ncd:revise-date 2020-04-16 ;
                  }
                  container neighbor-extend {
                    description 'Specify a neighbor.'
                                ;
                    leaf route-map-in-name {
                      description 'Apply route-map to incoming routes.'
                                  ;
                      type string {
                        length 1..200 ;
                      }
                    }
                    leaf route-map-out-name {
                      description 'Apply route-map to outbound routes.'
                                  ;
                      type string {
                        length 1..200 ;
                      }
                    }
                    ncd:revise-date 2019-07-24 ;
                  }
                }
              }
            }
            leaf default-metric {
              description 'Set metric of BGP routes without MED.'
                          ;
              type uint32 {
                range 0..4294967295 ;
              }
              default 0 ;
              ncd:revise-date 2019-04-10 ;
            }
            ncd:revise-date 2016-04-08 ;
          }
          container address-family-ipv4-sr-policy {
            description 'Configuration in address family IPv4 SR policy mode.'
                        ;
            presence 'IPv4 SR policy address family.'
                     ;
            container neighbor-group {
              description 'Specify a peergroup neighbor.'
                          ;
              list neighbor {
                description 'Specify a peergroup neighbor.'
                            ;
                key neighbor-group ;
                leaf neighbor-group {
                  description 'Peer group name (1-31 characters).'
                              ;
                  type string {
                    length 1..31 ;
                  }
                }
                leaf activate {
                  description 'Enable the address family for this neighbor.'
                              ;
                  type enumeration {
                    enum disable {
                      value 0 ;
                    }
                    enum enable {
                      value 1 ;
                    }
                  }
                }
                leaf allowas-in {
                  description 'Accept as-path with my AS present in it.'
                              ;
                  type uint32 {
                    range 1..10 ;
                  }
                }
                leaf as-path-loopcheck {
                  description 'Check as-path sending BGP routing to EBGP neighb'
                            + 'or.'
                              ;
                  type empty ;
                }
                leaf next-hop-self {
                  description 'Disable the next hop calculation for this neighb'
                            + 'or.'
                              ;
                  type enumeration {
                    enum enable {
                      value 1 ;
                      description 'Apply next-hop-self for EBGP route.'
                                  ;
                    }
                    enum all {
                      value 2 ;
                      description 'Apply next-hop-self for both EBGP and IBGP r'
                                + 'oute.'
                                  ;
                    }
                  }
                }
                choice nh-unchanged {
                  case next-hop-unchanged {
                    description 'NEXT_HOP of the IBGP path propagated unchanged'
                              + ' to this neighbor.'
                                ;
                    leaf next-hop-unchanged {
                      description 'Propagate next hop unchanged for IBGP paths '
                                + 'to this neighbor.'
                                  ;
                      type empty ;
                    }
                  }
                  case next-hop-unchanged-all {
                    description 'NEXT_HOP of either EBGP or IBGP path propagate'
                              + 'd unchanged to this neighbor.'
                                ;
                    leaf next-hop-unchanged-all {
                      description 'NEXT_HOP of either EBGP or IBGP path propaga'
                                + 'ted unchanged to this neighbor.'
                                  ;
                      type empty ;
                    }
                    ncd:revise-date 2020-04-07 ;
                  }
                }
                leaf remove-private-as {
                  description 'EBGP use to remove private AS number.'
                              ;
                  type enumeration {
                    enum disable {
                      value 0 ;
                    }
                    enum enable {
                      value 1 ;
                    }
                  }
                }
                leaf route-reflector-client {
                  description 'Set this neighbor as a client peer.'
                              ;
                  type empty ;
                }
                leaf send-community {
                  description 'Send community to this neighbor.'
                              ;
                  type empty ;
                }
                leaf send-large-community {
                  description 'Send Large-community to this neighbor.'
                              ;
                  type empty ;
                  ncd:revise-date 2020-04-16 ;
                }
                leaf send-med {
                  description 'Send metric attribute to this neighbor.'
                              ;
                  type empty ;
                }
                leaf weight {
                  description 'Set weight for routes from this neighbor.'
                              ;
                  type uint32 {
                    range 1..65535 ;
                  }
                }
                leaf maxas-in {
                  description 'Accept as-path not exceeded maxas-in.'
                              ;
                  type uint32 {
                    range 1..250 ;
                  }
                }
                leaf split-update-group {
                  description 'Split neighbor from update group.'
                              ;
                  type empty ;
                }
                container neighbor-extend {
                  description 'Specify a neighbor.'
                              ;
                  leaf route-map-in-name {
                    description 'Apply route-map to incoming routes.'
                                ;
                    type string {
                      length 1..200 ;
                    }
                  }
                  leaf route-map-out-name {
                    description 'Apply route-map to outbound routes.'
                                ;
                    type string {
                      length 1..200 ;
                    }
                  }
                  container maximum-prefix {
                    description 'The action that generated when threshold value'
                              + ' reached.'
                                ;
                    presence 'The action that generated when threshold value re'
                           + 'ached'
                             ;
                    leaf maximum-prefix-number {
                      description 'Maximum number of prefix limit.'
                                  ;
                      type uint32 {
                        range 1..4294967295 ;
                      }
                      mandatory true ;
                    }
                    leaf maximum-prefix-threshold {
                      description 'Threshold value(%) at which to generate a wa'
                                + 'rning.'
                                  ;
                      type uint32 {
                        range 1..100 ;
                      }
                      mandatory true ;
                    }
                    choice maximum-prefix-action {
                      description 'The action that generated when threshold val'
                                + 'ue reached.'
                                  ;
                      mandatory true ;
                      case peer-action {
                        description 'The action that generated when threshold v'
                                  + 'alue reached.'
                                    ;
                        leaf action {
                          description 'The action that generated when threshold'
                                    + ' value reached.'
                                      ;
                          type enumeration {
                            enum down {
                              value 0 ;
                              description 'Break down BGP connection after limit is exceeded.'
                                          ;
                            }
                            enum warning-only {
                              value 1 ;
                              description 'Only give warning message when limit is exceeded.'
                                          ;
                            }
                            enum drop-route {
                              value 2 ;
                              description 'Drop routes that exceed the maximum-prefix.'
                                          ;
                            }
                          }
                          mandatory true ;
                        }
                      }
                      case restart {
                        description 'Restart BGP connection after limit is exce'
                                  + 'eded.'
                                    ;
                        leaf restart-time {
                          description 'Restart interval in minutes.'
                                      ;
                          type uint32 {
                            range 1..30000 ;
                          }
                          mandatory true ;
                        }
                      }
                    }
                  }
                  leaf routepolicy-in-name {
                    description 'Route policy name applied to the inbound route'
                              + 's.'
                                ;
                    type string {
                      length 1..200 ;
                    }
                  }
                  leaf routepolicy-out-name {
                    description 'Route policy name applied to the outbound rout'
                              + 'es.'
                                ;
                    type string {
                      length 1..200 ;
                    }
                  }
                }
              }
            }
            container neighbor-ipv4 {
              description 'Specify a IPv4 neighbor.'
                          ;
              list neighbor {
                description 'Specify a IPv4 neighbor.'
                            ;
                key ipv4-address ;
                leaf ipv4-address {
                  description 'Neighbor IPv4 address.'
                              ;
                  type ncd:ipv4-address ;
                }
                leaf joined-group {
                  description 'Only for read operation. The joined group name.'
                              ;
                  type string {
                    length 1..31 ;
                  }
                }
                leaf activate {
                  description 'Enable the address family for this neighbor.'
                              ;
                  type enumeration {
                    enum disable {
                      value 0 ;
                    }
                    enum enable {
                      value 1 ;
                    }
                  }
                }
                leaf allowas-in {
                  description 'Accept as-path with my AS present in it.'
                              ;
                  type uint32 {
                    range 1..10 ;
                  }
                }
                leaf as-path-loopcheck {
                  description 'Check as-path sending BGP routing to EBGP neighb'
                            + 'or.'
                              ;
                  type empty ;
                }
                leaf next-hop-self {
                  description 'Disable the next hop calculation for this neighb'
                            + 'or.'
                              ;
                  type enumeration {
                    enum enable {
                      value 1 ;
                      description 'Apply next-hop-self for EBGP route.'
                                  ;
                    }
                    enum all {
                      value 2 ;
                      description 'Apply next-hop-self for both EBGP and IBGP r'
                                + 'oute.'
                                  ;
                    }
                  }
                }
                choice nh-unchanged {
                  case next-hop-unchanged {
                    description 'NEXT_HOP of the IBGP path propagated unchanged'
                              + ' to this neighbor.'
                                ;
                    leaf next-hop-unchanged {
                      description 'Propagate next hop unchanged for IBGP paths '
                                + 'to this neighbor.'
                                  ;
                      type empty ;
                    }
                  }
                  case next-hop-unchanged-all {
                    description 'NEXT_HOP of either EBGP or IBGP path propagate'
                              + 'd unchanged to this neighbor.'
                                ;
                    leaf next-hop-unchanged-all {
                      description 'NEXT_HOP of either EBGP or IBGP path propaga'
                                + 'ted unchanged to this neighbor.'
                                  ;
                      type empty ;
                    }
                    ncd:revise-date 2020-04-07 ;
                  }
                }
                leaf remove-private-as {
                  description 'EBGP use to remove private AS number.'
                              ;
                  type enumeration {
                    enum disable {
                      value 0 ;
                    }
                    enum enable {
                      value 1 ;
                    }
                  }
                }
                leaf route-reflector-client {
                  description 'Set this neighbor as a client peer.'
                              ;
                  type empty ;
                }
                leaf send-community {
                  description 'Send community to this neighbor.'
                              ;
                  type empty ;
                }
                leaf send-large-community {
                  description 'Send Large-community to this neighbor.'
                              ;
                  type empty ;
                  ncd:revise-date 2020-04-16 ;
                }
                leaf send-med {
                  description 'Send metric attribute to this neighbor.'
                              ;
                  type empty ;
                }
                leaf weight {
                  description 'Set weight for routes from this neighbor.'
                              ;
                  type uint32 {
                    range 1..65535 ;
                  }
                }
                leaf maxas-in {
                  description 'Accept as-path not exceeded maxas-in.'
                              ;
                  type uint32 {
                    range 1..250 ;
                  }
                }
                leaf split-update-group {
                  description 'Split neighbor from update group.'
                              ;
                  type empty ;
                }
                container neighbor-extend {
                  description 'Specify a neighbor.'
                              ;
                  leaf route-map-in-name {
                    description 'Apply route-map to incoming routes.'
                                ;
                    type string {
                      length 1..200 ;
                    }
                  }
                  leaf route-map-out-name {
                    description 'Apply route-map to outbound routes.'
                                ;
                    type string {
                      length 1..200 ;
                    }
                  }
                  container maximum-prefix {
                    description 'The action that generated when threshold value'
                              + ' reached.'
                                ;
                    presence 'The action that generated when threshold value re'
                           + 'ached'
                             ;
                    leaf maximum-prefix-number {
                      description 'Maximum number of prefix limit.'
                                  ;
                      type uint32 {
                        range 1..4294967295 ;
                      }
                      mandatory true ;
                    }
                    leaf maximum-prefix-threshold {
                      description 'Threshold value(%) at which to generate a wa'
                                + 'rning.'
                                  ;
                      type uint32 {
                        range 1..100 ;
                      }
                      mandatory true ;
                    }
                    choice maximum-prefix-action {
                      description 'The action that generated when threshold val'
                                + 'ue reached.'
                                  ;
                      mandatory true ;
                      case peer-action {
                        description 'The action that generated when threshold v'
                                  + 'alue reached.'
                                    ;
                        leaf action {
                          description 'The action that generated when threshold'
                                    + ' value reached.'
                                      ;
                          type enumeration {
                            enum down {
                              value 0 ;
                              description 'Break down BGP connection after limit is exceeded.'
                                          ;
                            }
                            enum warning-only {
                              value 1 ;
                              description 'Only give warning message when limit is exceeded.'
                                          ;
                            }
                            enum drop-route {
                              value 2 ;
                              description 'Drop routes that exceed the maximum-prefix.'
                                          ;
                            }
                          }
                          mandatory true ;
                        }
                      }
                      case restart {
                        description 'Restart BGP connection after limit is exce'
                                  + 'eded.'
                                    ;
                        leaf restart-time {
                          description 'Restart interval in minutes.'
                                      ;
                          type uint32 {
                            range 1..30000 ;
                          }
                          mandatory true ;
                        }
                      }
                    }
                  }
                  leaf routepolicy-in-name {
                    description 'Route policy name applied to the inbound route'
                              + 's.'
                                ;
                    type string {
                      length 1..200 ;
                    }
                  }
                  leaf routepolicy-out-name {
                    description 'Route policy name applied to the outbound rout'
                              + 'es.'
                                ;
                    type string {
                      length 1..200 ;
                    }
                  }
                }
              }
            }
            container neighbor-ipv6 {
              description 'Specify a IPv6 neighbor.'
                          ;
              list neighbor {
                description 'Specify a IPv6 neighbor.'
                            ;
                key ipv6-addr ;
                leaf ipv6-addr {
                  description 'Neighbor IPv6 address.'
                              ;
                  type ncd:ipv6-address ;
                }
                leaf joined-group {
                  description 'Only for read operation. The joined group name.'
                              ;
                  type string {
                    length 1..31 ;
                  }
                }
                leaf activate {
                  description 'Enable the address family for this neighbor.'
                              ;
                  type enumeration {
                    enum disable {
                      value 0 ;
                    }
                    enum enable {
                      value 1 ;
                    }
                  }
                }
                leaf allowas-in {
                  description 'Accept as-path with my AS present in it.'
                              ;
                  type uint32 {
                    range 1..10 ;
                  }
                }
                leaf as-path-loopcheck {
                  description 'Check as-path sending BGP routing to EBGP neighb'
                            + 'or.'
                              ;
                  type empty ;
                }
                leaf next-hop-self {
                  description 'Disable the next hop calculation for this neighb'
                            + 'or.'
                              ;
                  type enumeration {
                    enum enable {
                      value 1 ;
                      description 'Apply next-hop-self for EBGP route.'
                                  ;
                    }
                    enum all {
                      value 2 ;
                      description 'Apply next-hop-self for both EBGP and IBGP r'
                                + 'oute.'
                                  ;
                    }
                  }
                }
                choice nh-unchanged {
                  case next-hop-unchanged {
                    description 'NEXT_HOP of the IBGP path propagated unchanged'
                              + ' to this neighbor.'
                                ;
                    leaf next-hop-unchanged {
                      description 'Propagate next hop unchanged for IBGP paths '
                                + 'to this neighbor.'
                                  ;
                      type empty ;
                    }
                  }
                  case next-hop-unchanged-all {
                    description 'NEXT_HOP of either EBGP or IBGP path propagate'
                              + 'd unchanged to this neighbor.'
                                ;
                    leaf next-hop-unchanged-all {
                      description 'NEXT_HOP of either EBGP or IBGP path propaga'
                                + 'ted unchanged to this neighbor.'
                                  ;
                      type empty ;
                    }
                    ncd:revise-date 2020-04-07 ;
                  }
                }
                leaf remove-private-as {
                  description 'EBGP use to remove private AS number.'
                              ;
                  type enumeration {
                    enum disable {
                      value 0 ;
                    }
                    enum enable {
                      value 1 ;
                    }
                  }
                }
                leaf route-reflector-client {
                  description 'Set this neighbor as a client peer.'
                              ;
                  type empty ;
                }
                leaf send-community {
                  description 'Send community to this neighbor.'
                              ;
                  type empty ;
                }
                leaf send-large-community {
                  description 'Send Large-community to this neighbor.'
                              ;
                  type empty ;
                  ncd:revise-date 2020-04-16 ;
                }
                leaf send-med {
                  description 'Send metric attribute to this neighbor.'
                              ;
                  type empty ;
                }
                leaf weight {
                  description 'Set weight for routes from this neighbor.'
                              ;
                  type uint32 {
                    range 1..65535 ;
                  }
                }
                leaf maxas-in {
                  description 'Accept as-path not exceeded maxas-in.'
                              ;
                  type uint32 {
                    range 1..250 ;
                  }
                }
                leaf split-update-group {
                  description 'Split neighbor from update group.'
                              ;
                  type empty ;
                }
                container neighbor-extend {
                  description 'Specify a neighbor.'
                              ;
                  leaf route-map-in-name {
                    description 'Apply route-map to incoming routes.'
                                ;
                    type string {
                      length 1..200 ;
                    }
                  }
                  leaf route-map-out-name {
                    description 'Apply route-map to outbound routes.'
                                ;
                    type string {
                      length 1..200 ;
                    }
                  }
                  container maximum-prefix {
                    description 'The action that generated when threshold value'
                              + ' reached.'
                                ;
                    presence 'The action that generated when threshold value re'
                           + 'ached'
                             ;
                    leaf maximum-prefix-number {
                      description 'Maximum number of prefix limit.'
                                  ;
                      type uint32 {
                        range 1..4294967295 ;
                      }
                      mandatory true ;
                    }
                    leaf maximum-prefix-threshold {
                      description 'Threshold value(%) at which to generate a wa'
                                + 'rning.'
                                  ;
                      type uint32 {
                        range 1..100 ;
                      }
                      mandatory true ;
                    }
                    choice maximum-prefix-action {
                      description 'The action that generated when threshold val'
                                + 'ue reached.'
                                  ;
                      mandatory true ;
                      case peer-action {
                        description 'The action that generated when threshold v'
                                  + 'alue reached.'
                                    ;
                        leaf action {
                          description 'The action that generated when threshold'
                                    + ' value reached.'
                                      ;
                          type enumeration {
                            enum down {
                              value 0 ;
                              description 'Break down BGP connection after limit is exceeded.'
                                          ;
                            }
                            enum warning-only {
                              value 1 ;
                              description 'Only give warning message when limit is exceeded.'
                                          ;
                            }
                            enum drop-route {
                              value 2 ;
                              description 'Drop routes that exceed the maximum-prefix.'
                                          ;
                            }
                          }
                          mandatory true ;
                        }
                      }
                      case restart {
                        description 'Restart BGP connection after limit is exce'
                                  + 'eded.'
                                    ;
                        leaf restart-time {
                          description 'Restart interval in minutes.'
                                      ;
                          type uint32 {
                            range 1..30000 ;
                          }
                          mandatory true ;
                        }
                      }
                    }
                  }
                  leaf routepolicy-in-name {
                    description 'Route policy name applied to the inbound route'
                              + 's.'
                                ;
                    type string {
                      length 1..200 ;
                    }
                  }
                  leaf routepolicy-out-name {
                    description 'Route policy name applied to the outbound rout'
                              + 'es.'
                                ;
                    type string {
                      length 1..200 ;
                    }
                  }
                }
              }
            }
            leaf default-metric {
              description 'Set metric of BGP routes without MED.'
                          ;
              type uint32 {
                range 0..4294967295 ;
              }
              default 0 ;
            }
            leaf distance-bgp-external {
              description 'Distance for routes external to the AS.'
                          ;
              type uint32 {
                range 1..255 ;
              }
              default 20 ;
            }
            leaf distance-bgp-internal {
              description 'Distance for routes internal to the AS.'
                          ;
              type uint32 {
                range 1..255 ;
              }
              default 200 ;
            }
            leaf distance-route-map {
              description 'Define distance by route-map.This node has higher pr'
                        + 'iority than distance-bgp-internal and distance-bgp-e'
                        + 'xternal.'
                          ;
              type string {
                length 1..200 ;
              }
              ncd:revise-date 2020-09-08 ;
            }
            leaf distance-route-policy {
              description 'Define distance by route-policy.This node has higher'
                        + ' priority than distance-bgp-internal and distance-bg'
                        + 'p-external.'
                          ;
              type string {
                length 1..200 ;
              }
              ncd:revise-date 2020-10-10 ;
            }
            ncd:revise-date 2019-08-26 ;
          }
          container address-family-ipv6-sr-policy {
            description 'Configuration in address family IPv6 SR policy mode.'
                        ;
            presence 'IPv6 SR policy address family.'
                     ;
            container neighbor-group {
              description 'Specify a peergroup neighbor.'
                          ;
              list neighbor {
                description 'Specify a peergroup neighbor.'
                            ;
                key neighbor-group ;
                leaf neighbor-group {
                  description 'Peer group name (1-31 characters).'
                              ;
                  type string {
                    length 1..31 ;
                  }
                }
                leaf activate {
                  description 'Enable the address family for this neighbor.'
                              ;
                  type enumeration {
                    enum disable {
                      value 0 ;
                    }
                    enum enable {
                      value 1 ;
                    }
                  }
                }
                leaf allowas-in {
                  description 'Accept as-path with my AS present in it.'
                              ;
                  type uint32 {
                    range 1..10 ;
                  }
                }
                leaf as-path-loopcheck {
                  description 'Check as-path sending BGP routing to EBGP neighb'
                            + 'or.'
                              ;
                  type empty ;
                }
                leaf next-hop-self {
                  description 'Disable the next hop calculation for this neighb'
                            + 'or.'
                              ;
                  type enumeration {
                    enum enable {
                      value 1 ;
                      description 'Apply next-hop-self for EBGP route.'
                                  ;
                    }
                    enum all {
                      value 2 ;
                      description 'Apply next-hop-self for both EBGP and IBGP r'
                                + 'oute.'
                                  ;
                    }
                  }
                }
                choice nh-unchanged {
                  case next-hop-unchanged {
                    description 'NEXT_HOP of the IBGP path propagated unchanged'
                              + ' to this neighbor.'
                                ;
                    leaf next-hop-unchanged {
                      description 'Propagate next hop unchanged for IBGP paths '
                                + 'to this neighbor.'
                                  ;
                      type empty ;
                    }
                  }
                  case next-hop-unchanged-all {
                    description 'NEXT_HOP of either EBGP or IBGP path propagate'
                              + 'd unchanged to this neighbor.'
                                ;
                    leaf next-hop-unchanged-all {
                      description 'NEXT_HOP of either EBGP or IBGP path propaga'
                                + 'ted unchanged to this neighbor.'
                                  ;
                      type empty ;
                    }
                    ncd:revise-date 2020-04-07 ;
                  }
                }
                leaf remove-private-as {
                  description 'EBGP use to remove private AS number.'
                              ;
                  type enumeration {
                    enum disable {
                      value 0 ;
                    }
                    enum enable {
                      value 1 ;
                    }
                  }
                }
                leaf route-reflector-client {
                  description 'Set this neighbor as a client peer.'
                              ;
                  type empty ;
                }
                leaf send-community {
                  description 'Send community to this neighbor.'
                              ;
                  type empty ;
                }
                leaf send-large-community {
                  description 'Send Large-community to this neighbor.'
                              ;
                  type empty ;
                  ncd:revise-date 2020-04-16 ;
                }
                leaf send-med {
                  description 'Send metric attribute to this neighbor.'
                              ;
                  type empty ;
                }
                leaf weight {
                  description 'Set weight for routes from this neighbor.'
                              ;
                  type uint32 {
                    range 1..65535 ;
                  }
                }
                leaf maxas-in {
                  description 'Accept as-path not exceeded maxas-in.'
                              ;
                  type uint32 {
                    range 1..250 ;
                  }
                }
                leaf split-update-group {
                  description 'Split neighbor from update group.'
                              ;
                  type empty ;
                }
                container neighbor-extend {
                  description 'Specify a neighbor.'
                              ;
                  leaf route-map-in-name {
                    description 'Apply route-map to incoming routes.'
                                ;
                    type string {
                      length 1..200 ;
                    }
                  }
                  leaf route-map-out-name {
                    description 'Apply route-map to outbound routes.'
                                ;
                    type string {
                      length 1..200 ;
                    }
                  }
                  container maximum-prefix {
                    description 'The action that generated when threshold value'
                              + ' reached.'
                                ;
                    presence 'The action that generated when threshold value re'
                           + 'ached'
                             ;
                    leaf maximum-prefix-number {
                      description 'Maximum number of prefix limit.'
                                  ;
                      type uint32 {
                        range 1..4294967295 ;
                      }
                      mandatory true ;
                    }
                    leaf maximum-prefix-threshold {
                      description 'Threshold value(%) at which to generate a wa'
                                + 'rning.'
                                  ;
                      type uint32 {
                        range 1..100 ;
                      }
                      mandatory true ;
                    }
                    choice maximum-prefix-action {
                      description 'The action that generated when threshold val'
                                + 'ue reached.'
                                  ;
                      mandatory true ;
                      case peer-action {
                        description 'The action that generated when threshold v'
                                  + 'alue reached.'
                                    ;
                        leaf action {
                          description 'The action that generated when threshold'
                                    + ' value reached.'
                                      ;
                          type enumeration {
                            enum down {
                              value 0 ;
                              description 'Break down BGP connection after limit is exceeded.'
                                          ;
                            }
                            enum warning-only {
                              value 1 ;
                              description 'Only give warning message when limit is exceeded.'
                                          ;
                            }
                            enum drop-route {
                              value 2 ;
                              description 'Drop routes that exceed the maximum-prefix.'
                                          ;
                            }
                          }
                          mandatory true ;
                        }
                      }
                      case restart {
                        description 'Restart BGP connection after limit is exce'
                                  + 'eded.'
                                    ;
                        leaf restart-time {
                          description 'Restart interval in minutes.'
                                      ;
                          type uint32 {
                            range 1..30000 ;
                          }
                          mandatory true ;
                        }
                      }
                    }
                  }
                  leaf routepolicy-in-name {
                    description 'Route policy name applied to the inbound route'
                              + 's.'
                                ;
                    type string {
                      length 1..200 ;
                    }
                  }
                  leaf routepolicy-out-name {
                    description 'Route policy name applied to the outbound rout'
                              + 'es.'
                                ;
                    type string {
                      length 1..200 ;
                    }
                  }
                }
              }
            }
            container neighbor-ipv4 {
              description 'Specify a IPv4 neighbor.'
                          ;
              list neighbor {
                description 'Specify a IPv4 neighbor.'
                            ;
                key ipv4-address ;
                leaf ipv4-address {
                  description 'Neighbor IPv4 address.'
                              ;
                  type ncd:ipv4-address ;
                }
                leaf joined-group {
                  description 'Only for read operation. The joined group name.'
                              ;
                  type string {
                    length 1..31 ;
                  }
                }
                leaf activate {
                  description 'Enable the address family for this neighbor.'
                              ;
                  type enumeration {
                    enum disable {
                      value 0 ;
                    }
                    enum enable {
                      value 1 ;
                    }
                  }
                }
                leaf allowas-in {
                  description 'Accept as-path with my AS present in it.'
                              ;
                  type uint32 {
                    range 1..10 ;
                  }
                }
                leaf as-path-loopcheck {
                  description 'Check as-path sending BGP routing to EBGP neighb'
                            + 'or.'
                              ;
                  type empty ;
                }
                leaf next-hop-self {
                  description 'Disable the next hop calculation for this neighb'
                            + 'or.'
                              ;
                  type enumeration {
                    enum enable {
                      value 1 ;
                      description 'Apply next-hop-self for EBGP route.'
                                  ;
                    }
                    enum all {
                      value 2 ;
                      description 'Apply next-hop-self for both EBGP and IBGP r'
                                + 'oute.'
                                  ;
                    }
                  }
                }
                choice nh-unchanged {
                  case next-hop-unchanged {
                    description 'NEXT_HOP of the IBGP path propagated unchanged'
                              + ' to this neighbor.'
                                ;
                    leaf next-hop-unchanged {
                      description 'Propagate next hop unchanged for IBGP paths '
                                + 'to this neighbor.'
                                  ;
                      type empty ;
                    }
                  }
                  case next-hop-unchanged-all {
                    description 'NEXT_HOP of either EBGP or IBGP path propagate'
                              + 'd unchanged to this neighbor.'
                                ;
                    leaf next-hop-unchanged-all {
                      description 'NEXT_HOP of either EBGP or IBGP path propaga'
                                + 'ted unchanged to this neighbor.'
                                  ;
                      type empty ;
                    }
                    ncd:revise-date 2020-04-07 ;
                  }
                }
                leaf remove-private-as {
                  description 'EBGP use to remove private AS number.'
                              ;
                  type enumeration {
                    enum disable {
                      value 0 ;
                    }
                    enum enable {
                      value 1 ;
                    }
                  }
                }
                leaf route-reflector-client {
                  description 'Set this neighbor as a client peer.'
                              ;
                  type empty ;
                }
                leaf send-community {
                  description 'Send community to this neighbor.'
                              ;
                  type empty ;
                }
                leaf send-large-community {
                  description 'Send Large-community to this neighbor.'
                              ;
                  type empty ;
                  ncd:revise-date 2020-04-16 ;
                }
                leaf send-med {
                  description 'Send metric attribute to this neighbor.'
                              ;
                  type empty ;
                }
                leaf weight {
                  description 'Set weight for routes from this neighbor.'
                              ;
                  type uint32 {
                    range 1..65535 ;
                  }
                }
                leaf maxas-in {
                  description 'Accept as-path not exceeded maxas-in.'
                              ;
                  type uint32 {
                    range 1..250 ;
                  }
                }
                leaf split-update-group {
                  description 'Split neighbor from update group.'
                              ;
                  type empty ;
                }
                container neighbor-extend {
                  description 'Specify a neighbor.'
                              ;
                  leaf route-map-in-name {
                    description 'Apply route-map to incoming routes.'
                                ;
                    type string {
                      length 1..200 ;
                    }
                  }
                  leaf route-map-out-name {
                    description 'Apply route-map to outbound routes.'
                                ;
                    type string {
                      length 1..200 ;
                    }
                  }
                  container maximum-prefix {
                    description 'The action that generated when threshold value'
                              + ' reached.'
                                ;
                    presence 'The action that generated when threshold value re'
                           + 'ached'
                             ;
                    leaf maximum-prefix-number {
                      description 'Maximum number of prefix limit.'
                                  ;
                      type uint32 {
                        range 1..4294967295 ;
                      }
                      mandatory true ;
                    }
                    leaf maximum-prefix-threshold {
                      description 'Threshold value(%) at which to generate a wa'
                                + 'rning.'
                                  ;
                      type uint32 {
                        range 1..100 ;
                      }
                      mandatory true ;
                    }
                    choice maximum-prefix-action {
                      description 'The action that generated when threshold val'
                                + 'ue reached.'
                                  ;
                      mandatory true ;
                      case peer-action {
                        description 'The action that generated when threshold v'
                                  + 'alue reached.'
                                    ;
                        leaf action {
                          description 'The action that generated when threshold'
                                    + ' value reached.'
                                      ;
                          type enumeration {
                            enum down {
                              value 0 ;
                              description 'Break down BGP connection after limit is exceeded.'
                                          ;
                            }
                            enum warning-only {
                              value 1 ;
                              description 'Only give warning message when limit is exceeded.'
                                          ;
                            }
                            enum drop-route {
                              value 2 ;
                              description 'Drop routes that exceed the maximum-prefix.'
                                          ;
                            }
                          }
                          mandatory true ;
                        }
                      }
                      case restart {
                        description 'Restart BGP connection after limit is exce'
                                  + 'eded.'
                                    ;
                        leaf restart-time {
                          description 'Restart interval in minutes.'
                                      ;
                          type uint32 {
                            range 1..30000 ;
                          }
                          mandatory true ;
                        }
                      }
                    }
                  }
                  leaf routepolicy-in-name {
                    description 'Route policy name applied to the inbound route'
                              + 's.'
                                ;
                    type string {
                      length 1..200 ;
                    }
                  }
                  leaf routepolicy-out-name {
                    description 'Route policy name applied to the outbound rout'
                              + 'es.'
                                ;
                    type string {
                      length 1..200 ;
                    }
                  }
                }
              }
            }
            container neighbor-ipv6 {
              description 'Specify a IPv6 neighbor.'
                          ;
              list neighbor {
                description 'Specify a IPv6 neighbor.'
                            ;
                key ipv6-addr ;
                leaf ipv6-addr {
                  description 'Neighbor IPv6 address.'
                              ;
                  type ncd:ipv6-address ;
                }
                leaf joined-group {
                  description 'Only for read operation. The joined group name.'
                              ;
                  type string {
                    length 1..31 ;
                  }
                }
                leaf activate {
                  description 'Enable the address family for this neighbor.'
                              ;
                  type enumeration {
                    enum disable {
                      value 0 ;
                    }
                    enum enable {
                      value 1 ;
                    }
                  }
                }
                leaf allowas-in {
                  description 'Accept as-path with my AS present in it.'
                              ;
                  type uint32 {
                    range 1..10 ;
                  }
                }
                leaf as-path-loopcheck {
                  description 'Check as-path sending BGP routing to EBGP neighb'
                            + 'or.'
                              ;
                  type empty ;
                }
                leaf next-hop-self {
                  description 'Disable the next hop calculation for this neighb'
                            + 'or.'
                              ;
                  type enumeration {
                    enum enable {
                      value 1 ;
                      description 'Apply next-hop-self for EBGP route.'
                                  ;
                    }
                    enum all {
                      value 2 ;
                      description 'Apply next-hop-self for both EBGP and IBGP r'
                                + 'oute.'
                                  ;
                    }
                  }
                }
                choice nh-unchanged {
                  case next-hop-unchanged {
                    description 'NEXT_HOP of the IBGP path propagated unchanged'
                              + ' to this neighbor.'
                                ;
                    leaf next-hop-unchanged {
                      description 'Propagate next hop unchanged for IBGP paths '
                                + 'to this neighbor.'
                                  ;
                      type empty ;
                    }
                  }
                  case next-hop-unchanged-all {
                    description 'NEXT_HOP of either EBGP or IBGP path propagate'
                              + 'd unchanged to this neighbor.'
                                ;
                    leaf next-hop-unchanged-all {
                      description 'NEXT_HOP of either EBGP or IBGP path propaga'
                                + 'ted unchanged to this neighbor.'
                                  ;
                      type empty ;
                    }
                    ncd:revise-date 2020-04-07 ;
                  }
                }
                leaf remove-private-as {
                  description 'EBGP use to remove private AS number.'
                              ;
                  type enumeration {
                    enum disable {
                      value 0 ;
                    }
                    enum enable {
                      value 1 ;
                    }
                  }
                }
                leaf route-reflector-client {
                  description 'Set this neighbor as a client peer.'
                              ;
                  type empty ;
                }
                leaf send-community {
                  description 'Send community to this neighbor.'
                              ;
                  type empty ;
                }
                leaf send-large-community {
                  description 'Send Large-community to this neighbor.'
                              ;
                  type empty ;
                  ncd:revise-date 2020-04-16 ;
                }
                leaf send-med {
                  description 'Send metric attribute to this neighbor.'
                              ;
                  type empty ;
                }
                leaf weight {
                  description 'Set weight for routes from this neighbor.'
                              ;
                  type uint32 {
                    range 1..65535 ;
                  }
                }
                leaf maxas-in {
                  description 'Accept as-path not exceeded maxas-in.'
                              ;
                  type uint32 {
                    range 1..250 ;
                  }
                }
                leaf split-update-group {
                  description 'Split neighbor from update group.'
                              ;
                  type empty ;
                }
                container neighbor-extend {
                  description 'Specify a neighbor.'
                              ;
                  leaf route-map-in-name {
                    description 'Apply route-map to incoming routes.'
                                ;
                    type string {
                      length 1..200 ;
                    }
                  }
                  leaf route-map-out-name {
                    description 'Apply route-map to outbound routes.'
                                ;
                    type string {
                      length 1..200 ;
                    }
                  }
                  container maximum-prefix {
                    description 'The action that generated when threshold value'
                              + ' reached.'
                                ;
                    presence 'The action that generated when threshold value re'
                           + 'ached'
                             ;
                    leaf maximum-prefix-number {
                      description 'Maximum number of prefix limit.'
                                  ;
                      type uint32 {
                        range 1..4294967295 ;
                      }
                      mandatory true ;
                    }
                    leaf maximum-prefix-threshold {
                      description 'Threshold value(%) at which to generate a wa'
                                + 'rning.'
                                  ;
                      type uint32 {
                        range 1..100 ;
                      }
                      mandatory true ;
                    }
                    choice maximum-prefix-action {
                      description 'The action that generated when threshold val'
                                + 'ue reached.'
                                  ;
                      mandatory true ;
                      case peer-action {
                        description 'The action that generated when threshold v'
                                  + 'alue reached.'
                                    ;
                        leaf action {
                          description 'The action that generated when threshold'
                                    + ' value reached.'
                                      ;
                          type enumeration {
                            enum down {
                              value 0 ;
                              description 'Break down BGP connection after limit is exceeded.'
                                          ;
                            }
                            enum warning-only {
                              value 1 ;
                              description 'Only give warning message when limit is exceeded.'
                                          ;
                            }
                            enum drop-route {
                              value 2 ;
                              description 'Drop routes that exceed the maximum-prefix.'
                                          ;
                            }
                          }
                          mandatory true ;
                        }
                      }
                      case restart {
                        description 'Restart BGP connection after limit is exce'
                                  + 'eded.'
                                    ;
                        leaf restart-time {
                          description 'Restart interval in minutes.'
                                      ;
                          type uint32 {
                            range 1..30000 ;
                          }
                          mandatory true ;
                        }
                      }
                    }
                  }
                  leaf routepolicy-in-name {
                    description 'Route policy name applied to the inbound route'
                              + 's.'
                                ;
                    type string {
                      length 1..200 ;
                    }
                  }
                  leaf routepolicy-out-name {
                    description 'Route policy name applied to the outbound rout'
                              + 'es.'
                                ;
                    type string {
                      length 1..200 ;
                    }
                  }
                }
              }
            }
            leaf default-metric {
              description 'Set metric of BGP routes without MED.'
                          ;
              type uint32 {
                range 0..4294967295 ;
              }
              default 0 ;
            }
            leaf distance-bgp-external {
              description 'Distance for routes external to the AS.'
                          ;
              type uint32 {
                range 1..255 ;
              }
              default 20 ;
            }
            leaf distance-bgp-internal {
              description 'Distance for routes internal to the AS.'
                          ;
              type uint32 {
                range 1..255 ;
              }
              default 200 ;
            }
            leaf distance-route-map {
              description 'Define distance by route-map.This node has higher pr'
                        + 'iority than distance-bgp-internal and distance-bgp-e'
                        + 'xternal.'
                          ;
              type string {
                length 1..200 ;
              }
              ncd:revise-date 2020-09-08 ;
            }
            leaf distance-route-policy {
              description 'Define distance by route-policy.This node has higher'
                        + ' priority than distance-bgp-internal and distance-bg'
                        + 'p-external.'
                          ;
              type string {
                length 1..200 ;
              }
              ncd:revise-date 2020-10-10 ;
            }
            ncd:revise-date 2019-08-26 ;
          }
          container address-family-ipv6-flowspec {
            description 'Configuration in address family IPv6 flow specificatio'
                      + 'n mode.'
                        ;
            presence 'IPv6 flow specification address family.'
                     ;
            leaf default-metric {
              description 'Set metric of BGP routes without MED.'
                          ;
              type uint32 {
                range 0..4294967295 ;
              }
              default 0 ;
            }
            container neighbor-ipv6-flowspec {
              description 'Specify a neighbor.'
                          ;
              presence neighbor-ipv6-flowspec ;
              container neighbor-group {
                description 'Specify a peergroup neighbor.'
                            ;
                list neighbor-peergroup {
                  description 'Specify a neighbor.'
                              ;
                  key neighbor-group ;
                  leaf neighbor-group {
                    description 'Peer group name (1-31 characters).'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf allowas-in {
                    description 'Accept as-path with my AS present in it.'
                                ;
                    type uint32 {
                      range 1..10 ;
                    }
                    ncd:revise-date 2020-08-11 ;
                  }
                  leaf route-reflector-client {
                    description 'Set this neighbor as a client peer.'
                                ;
                    type empty ;
                  }
                  leaf validation-disable-destination {
                    description 'Disable IPv6 Flowspec destination address vali'
                              + 'dation.'
                                ;
                    type empty ;
                  }
                  leaf validation-disable-redirect {
                    description 'Disable IPv6 Flowspec redirect nexthop validat'
                              + 'ion.'
                                ;
                    type empty ;
                  }
                  leaf send-community {
                    description 'Send community to this neighbor.'
                                ;
                    type empty ;
                    ncd:revise-date 2021-01-19 ;
                  }
                  leaf send-large-community {
                    description 'Send Large-community to this neighbor.'
                                ;
                    type empty ;
                    ncd:revise-date 2021-01-19 ;
                  }
                  container neighbor-extend {
                    description 'Specify a neighbor.'
                                ;
                    leaf route-map-in-name {
                      description 'Apply route-map to incoming routes.'
                                  ;
                      type string {
                        length 1..200 ;
                      }
                    }
                    leaf route-map-out-name {
                      description 'Apply route-map to outbound routes.'
                                  ;
                      type string {
                        length 1..200 ;
                      }
                    }
                    ncd:revise-date 2021-01-19 ;
                  }
                }
              }
              container neighbor-ipv4 {
                description 'Specify a IPv4 neighbor.'
                            ;
                list neighbor {
                  description 'Specify a neighbor.'
                              ;
                  key ipv4-addr ;
                  leaf ipv4-addr {
                    description 'Neighbor IPv4 address.'
                                ;
                    type ncd:ipv4-address ;
                  }
                  leaf joined-group {
                    description 'Only for read operation. The joined group name.'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf allowas-in {
                    description 'Accept as-path with my AS present in it.'
                                ;
                    type uint32 {
                      range 1..10 ;
                    }
                    ncd:revise-date 2020-08-11 ;
                  }
                  leaf route-reflector-client {
                    description 'Set this neighbor as a client peer.'
                                ;
                    type empty ;
                  }
                  leaf validation-disable-destination {
                    description 'Disable IPv6 Flowspec destination address vali'
                              + 'dation.'
                                ;
                    type empty ;
                  }
                  leaf validation-disable-redirect {
                    description 'Disable IPv6 Flowspec redirect nexthop validat'
                              + 'ion.'
                                ;
                    type empty ;
                  }
                  leaf send-community {
                    description 'Send community to this neighbor.'
                                ;
                    type empty ;
                    ncd:revise-date 2021-01-19 ;
                  }
                  leaf send-large-community {
                    description 'Send Large-community to this neighbor.'
                                ;
                    type empty ;
                    ncd:revise-date 2021-01-19 ;
                  }
                  container neighbor-extend {
                    description 'Specify a neighbor.'
                                ;
                    leaf route-map-in-name {
                      description 'Apply route-map to incoming routes.'
                                  ;
                      type string {
                        length 1..200 ;
                      }
                    }
                    leaf route-map-out-name {
                      description 'Apply route-map to outbound routes.'
                                  ;
                      type string {
                        length 1..200 ;
                      }
                    }
                    ncd:revise-date 2021-01-19 ;
                  }
                }
              }
              container neighbor-ipv6 {
                description 'Specify a IPv6 neighbor.'
                            ;
                list neighbor {
                  description 'Specify a neighbor.'
                              ;
                  key ipv6-addr ;
                  leaf ipv6-addr {
                    description 'Neighbor IPv6 address.'
                                ;
                    type ncd:ipv6-address ;
                  }
                  leaf joined-group {
                    description 'Only for read operation. The joined group name.'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf allowas-in {
                    description 'Accept as-path with my AS present in it.'
                                ;
                    type uint32 {
                      range 1..10 ;
                    }
                    ncd:revise-date 2020-08-11 ;
                  }
                  leaf route-reflector-client {
                    description 'Set this neighbor as a client peer.'
                                ;
                    type empty ;
                  }
                  leaf validation-disable-destination {
                    description 'Disable IPv6 Flowspec destination address vali'
                              + 'dation.'
                                ;
                    type empty ;
                  }
                  leaf validation-disable-redirect {
                    description 'Disable IPv6 Flowspec redirect nexthop validat'
                              + 'ion.'
                                ;
                    type empty ;
                  }
                  leaf send-community {
                    description 'Send community to this neighbor.'
                                ;
                    type empty ;
                    ncd:revise-date 2021-01-19 ;
                  }
                  leaf send-large-community {
                    description 'Send Large-community to this neighbor.'
                                ;
                    type empty ;
                    ncd:revise-date 2021-01-19 ;
                  }
                  container neighbor-extend {
                    description 'Specify a neighbor.'
                                ;
                    leaf route-map-in-name {
                      description 'Apply route-map to incoming routes.'
                                  ;
                      type string {
                        length 1..200 ;
                      }
                    }
                    leaf route-map-out-name {
                      description 'Apply route-map to outbound routes.'
                                  ;
                      type string {
                        length 1..200 ;
                      }
                    }
                    ncd:revise-date 2021-01-19 ;
                  }
                }
              }
            }
            ncd:revise-date 2019-11-27 ;
          }
          container address-family-vpnv6-flowspec {
            description 'Configuration in address family VPNv6 flow specificati'
                      + 'on mode.'
                        ;
            presence 'VPNv6 flow specification address family.'
                     ;
            leaf default-metric {
              description 'Set metric of BGP routes without MED.'
                          ;
              type uint32 {
                range 0..4294967295 ;
              }
              default 0 ;
            }
            container neighbor-vpnv6-flowspec {
              description 'Specify a neighbor.'
                          ;
              presence neighbor-vpnv6-flowspec ;
              container neighbor-group {
                description 'Specify a peergroup neighbor.'
                            ;
                list neighbor-peergroup {
                  description 'Specify a neighbor.'
                              ;
                  key neighbor-group ;
                  leaf neighbor-group {
                    description 'Peer group name (1-31 characters).'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf allowas-in {
                    description 'Accept as-path with my AS present in it.'
                                ;
                    type uint32 {
                      range 1..10 ;
                    }
                    ncd:revise-date 2020-08-11 ;
                  }
                  leaf route-reflector-client {
                    description 'Set this neighbor as a client peer.'
                                ;
                    type empty ;
                  }
                  leaf send-community {
                    description 'Send community to this neighbor.'
                                ;
                    type empty ;
                    ncd:revise-date 2021-01-19 ;
                  }
                  leaf send-large-community {
                    description 'Send Large-community to this neighbor.'
                                ;
                    type empty ;
                    ncd:revise-date 2021-01-19 ;
                  }
                  container neighbor-extend {
                    description 'Specify a neighbor.'
                                ;
                    leaf route-map-in-name {
                      description 'Apply route-map to incoming routes.'
                                  ;
                      type string {
                        length 1..200 ;
                      }
                    }
                    leaf route-map-out-name {
                      description 'Apply route-map to outbound routes.'
                                  ;
                      type string {
                        length 1..200 ;
                      }
                    }
                    ncd:revise-date 2021-01-19 ;
                  }
                }
              }
              container neighbor-ipv4 {
                description 'Specify a IPv4 neighbor.'
                            ;
                list neighbor {
                  description 'Specify a neighbor.'
                              ;
                  key ipv4-addr ;
                  leaf ipv4-addr {
                    description 'Neighbor IPv4 address.'
                                ;
                    type ncd:ipv4-address ;
                  }
                  leaf joined-group {
                    description 'Only for read operation. The joined group name.'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf allowas-in {
                    description 'Accept as-path with my AS present in it.'
                                ;
                    type uint32 {
                      range 1..10 ;
                    }
                    ncd:revise-date 2020-08-11 ;
                  }
                  leaf route-reflector-client {
                    description 'Set this neighbor as a client peer.'
                                ;
                    type empty ;
                  }
                  leaf send-community {
                    description 'Send community to this neighbor.'
                                ;
                    type empty ;
                    ncd:revise-date 2021-01-19 ;
                  }
                  leaf send-large-community {
                    description 'Send Large-community to this neighbor.'
                                ;
                    type empty ;
                    ncd:revise-date 2021-01-19 ;
                  }
                  container neighbor-extend {
                    description 'Specify a neighbor.'
                                ;
                    leaf route-map-in-name {
                      description 'Apply route-map to incoming routes.'
                                  ;
                      type string {
                        length 1..200 ;
                      }
                    }
                    leaf route-map-out-name {
                      description 'Apply route-map to outbound routes.'
                                  ;
                      type string {
                        length 1..200 ;
                      }
                    }
                    ncd:revise-date 2021-01-19 ;
                  }
                }
              }
              container neighbor-ipv6 {
                description 'Specify a IPv6 neighbor.'
                            ;
                list neighbor {
                  description 'Specify a neighbor.'
                              ;
                  key ipv6-addr ;
                  leaf ipv6-addr {
                    description 'Neighbor IPv6 address.'
                                ;
                    type ncd:ipv6-address ;
                  }
                  leaf joined-group {
                    description 'Only for read operation. The joined group name.'
                                ;
                    type string {
                      length 1..31 ;
                    }
                  }
                  leaf activate {
                    description 'Enable the address family for this neighbor.'
                                ;
                    type enumeration {
                      enum disable {
                        value 0 ;
                      }
                      enum enable {
                        value 1 ;
                      }
                    }
                  }
                  leaf allowas-in {
                    description 'Accept as-path with my AS present in it.'
                                ;
                    type uint32 {
                      range 1..10 ;
                    }
                    ncd:revise-date 2020-08-11 ;
                  }
                  leaf route-reflector-client {
                    description 'Set this neighbor as a client peer.'
                                ;
                    type empty ;
                  }
                  leaf send-community {
                    description 'Send community to this neighbor.'
                                ;
                    type empty ;
                    ncd:revise-date 2021-01-19 ;
                  }
                  leaf send-large-community {
                    description 'Send Large-community to this neighbor.'
                                ;
                    type empty ;
                    ncd:revise-date 2021-01-19 ;
                  }
                  container neighbor-extend {
                    description 'Specify a neighbor.'
                                ;
                    leaf route-map-in-name {
                      description 'Apply route-map to incoming routes.'
                                  ;
                      type string {
                        length 1..200 ;
                      }
                    }
                    leaf route-map-out-name {
                      description 'Apply route-map to outbound routes.'
                                  ;
                      type string {
                        length 1..200 ;
                      }
                    }
                    ncd:revise-date 2021-01-19 ;
                  }
                }
              }
            }
            ncd:revise-date 2019-11-27 ;
          }
          container address-family-vrf {
            description 'Specify parameters for VRF.'
                        ;
            list address-family {
              description 'Specify parameters for VRF.'
                          ;
              key vrf-name ;
              leaf vrf-name {
                description 'VPN Routing/Forwarding instance name.'
                            ;
                type string {
                  length 1..32 ;
                }
              }
              leaf bgp-local-as {
                description 'the Autonomy system number of BGP in local equipme'
                          + 'nt.'
                            ;
                type ncd:asn-dot ;
              }
              leaf router-id-addr {
                description 'Manually configured router identifier.'
                            ;
                type ncd:ipv4-address {
                  pattern '([1-9][0-9]*\.[1-9][0-9]*\.[1-9][0-9]*\.[1-9][0-9]*)'
                        + '|([1-9][0-9]*\.0\.0\.0)|(0\.[1-9][0-9]*\.0\.0)|(0\.0'
                        + '\.[1-9][0-9]*\.0)|(0\.0\.0\.[1-9][0-9]*)|([1-9][0-9]'
                        + '*\.[1-9][0-9]*\.0\.0)|(0\.[1-9][0-9]*\.[1-9][0-9]*\.'
                        + '0)|(0\.0\.[1-9][0-9]*\.[1-9][0-9]*)|([1-9][0-9]*\.0\.'
                        + '0\.[1-9][0-9]*)|(0\.[1-9][0-9]*\.0\.[1-9][0-9]*)|([1'
                        + '-9][0-9]*\.0\.[1-9][0-9]*\.0)|([1-9][0-9]*\.[1-9][0-'
                        + '9]*\.[1-9][0-9]*\.0)|([1-9][0-9]*\.[1-9][0-9]*\.0\.['
                        + '1-9][0-9]*)|([1-9][0-9]*\.0\.[1-9][0-9]*\.[1-9][0-9]'
                        + '*)|(0\.[1-9][0-9]*\.[1-9][0-9]*\.[1-9][0-9]*)'
                          ;
                }
              }
              container neighbor-vrf {
                description 'Specify a neighbor.'
                            ;
                presence neighbor-vrf ;
                container neighbor-group {
                  description 'Specify a peergroup neighbor.'
                              ;
                  list neighbor-peergroup {
                    description 'Specify a peergroup neighbor.'
                                ;
                    key neighbor-group ;
                    leaf neighbor-group {
                      description 'Peer group name (1-31 characters).'
                                  ;
                      type string {
                        length 1..31 ;
                      }
                    }
                    leaf remote-as {
                      description 'Specify a BGP neighbor AS number.'
                                  ;
                      type ncd:asn-dot ;
                    }
                    leaf advertisement-interval {
                      description 'Minimum interval between sending BGP routing'
                                + ' which is not locally originated updates.'
                                  ;
                      type uint32 {
                        range 1..65535 ;
                      }
                      units s ;
                    }
                    leaf connect-retry-interval {
                      description 'Set data of connect-retry timer for this nei'
                                + 'ghbor.'
                                  ;
                      type uint32 {
                        range 1..65535 ;
                      }
                      units s ;
                    }
                    leaf description {
                      description 'Neighbor specific description.'
                                  ;
                      type ncd:string-with-blank {
                        length 1..80 ;
                      }
                    }
                    leaf dscp {
                      description 'Set DSCP value.'
                                  ;
                      type uint8 {
                        range 0..63 ;
                      }
                    }
                    leaf enforce-first-as-disable {
                      description 'Not enforce the first AS for EBGP neighbor r'
                                + 'outes'
                                  ;
                      type empty ;
                    }
                    container fall-over {
                      description 'Set BFD supporting for fallover.'
                                  ;
                      presence fall-over ;
                      leaf bfd {
                        description 'Enable BFD support for fallover.'
                                    ;
                        type empty ;
                        mandatory true ;
                      }
                      container bfd-parameters {
                        description 'The parameters of BFD.'
                                    ;
                        presence bfd-parameters ;
                        choice bfd-parameters {
                          description 'Config bfd parameters'
                                      ;
                          case template-name {
                            description 'Template name'
                                        ;
                            leaf template {
                              description 'BFD template name'
                                          ;
                              type string {
                                length 1..31 ;
                              }
                            }
                          }
                          case parameters {
                            description Parameters. ;
                            leaf interval {
                              description 'Minimum send interval.'
                                          ;
                              type uint32 {
                                range 10..990 ;
                              }
                              units ms ;
                              mandatory true ;
                            }
                            leaf min-rx {
                              description 'Minimum receive interval.'
                                          ;
                              type uint32 {
                                range 10..990 ;
                              }
                              units ms ;
                              mandatory true ;
                            }
                            leaf multiplier {
                              description Multiplier. ;
                              type uint8 {
                                range 3..50 ;
                              }
                              mandatory true ;
                            }
                          }
                        }
                      }
                      leaf bfd-hop {
                        description 'bfd optional hop'
                                    ;
                        type enumeration {
                          enum single-hop {
                            value 1 ;
                            description 'Set single-hop bfd'
                                        ;
                          }
                          enum multi-hop {
                            value 2 ;
                            description 'Set multi-hop bfd'
                                        ;
                          }
                        }
                      }
                    }
                    leaf open-delay {
                      description 'Delay to send open message.'
                                  ;
                      type uint32 {
                        range 1..240 ;
                      }
                      units s ;
                    }
                    leaf originate-interval {
                      description 'Minimum interval between sending BGP routing'
                                + ' which is locally originated updates.'
                                  ;
                      type uint32 {
                        range 1..65535 ;
                      }
                      units s ;
                    }
                    leaf passive {
                      description "Don't send open messages to this neighbor ac"
                                + "tively."
                                  ;
                      type empty ;
                    }
                    leaf orf-prefix-filter-cisco {
                      description 'Compatible with CISCO.'
                                  ;
                      type empty ;
                    }
                    leaf enhanced-route-refresh-disable {
                      description 'Enhanced route refresh capability.'
                                  ;
                      type empty ;
                      ncd:revise-date 2020-10-10 ;
                    }
                    leaf four-byte-as-disable {
                      description 'Disable 4-byte AS capability.'
                                  ;
                      type empty ;
                      ncd:revise-date 2020-10-10 ;
                    }
                    leaf receive-single-label {
                      description 'Receive single label only for label unicast '
                                + 'route.'
                                  ;
                      type enumeration {
                        enum disable {
                          value 0 ;
                          description 'Disable receive single label only for la'
                                    + 'bel unicast route'
                                      ;
                        }
                        enum enable {
                          value 1 ;
                          description 'Enable receive single label only for lab'
                                    + 'el unicast route'
                                      ;
                        }
                        enum inherit {
                          value 2 ;
                          description 'If the neighbor joined a group, the stat'
                                    + 'us inherited from group'
                                      ;
                        }
                      }
                    }
                    leaf ignore-error-packet {
                      description 'Ignore error packet for this neighbor.'
                                  ;
                      type enumeration {
                        enum disable {
                          value 0 ;
                          description 'Disable peer ignore error packet'
                                      ;
                        }
                        enum enable {
                          value 1 ;
                          description 'Enable peer ignore error packet'
                                      ;
                        }
                        enum inherit {
                          value 2 ;
                          description 'If the neighbor joined a group, the stat'
                                    + 'us inherited from group.'
                                      ;
                        }
                      }
                    }
                    container set-ttl {
                      description 'ebgp-multihop-ttl and ttl-security-hops are '
                                + 'mutex.'
                                  ;
                      choice set-ttl {
                        description 'ebgp-multihop-ttl and ttl-security-hops ar'
                                  + 'e mutex.'
                                    ;
                        case ebgp-multihop-ttl {
                          description 'Allow EBGP neighbors not on directly con'
                                    + 'nected net.'
                                      ;
                          leaf ebgp-multihop {
                            description 'Allow EBGP neighbors not on directly connected net.'
                                        ;
                            type uint8 {
                              range 1..255 ;
                            }
                          }
                        }
                        case ttl-security-hops {
                          description 'Enable EBGP TTL security check.'
                                      ;
                          leaf ttl-security-hops {
                            description 'Enable EBGP TTL security check.'
                                        ;
                            type uint8 {
                              range 1..254 ;
                            }
                          }
                        }
                      }
                    }
                    container shutdown {
                      description 'Shut down this neighbor administratively or '
                                + 'when state of track-group is down.'
                                  ;
                      presence shutdown ;
                      leaf shut-down {
                        description 'Administratively shut down this neighbor.'
                                    ;
                        type empty ;
                        mandatory true ;
                      }
                      leaf track-group {
                        description 'Shut down this neighbor when state of trac'
                                  + 'k-group is down.'
                                    ;
                        type string {
                          length 1..31 ;
                        }
                      }
                    }
                    container update-source-ex {
                      description 'Specify the update-source configuration of t'
                                + 'he neighbor.'
                                  ;
                      choice update-source {
                        description 'Specify the update-source interface name o'
                                  + 'f the neighbor.'
                                    ;
                        case update-source-if {
                          description 'Specify the update-source interface name'
                                    + ' of the neighbor.'
                                      ;
                          leaf update-source-ifname {
                            description 'Specify the update-source interface name of the neighbor.'
                                        ;
                            type ncd:ifname ;
                          }
                        }
                        case update-source-ipv4 {
                          description 'Specify the update-source IPv4 address o'
                                    + 'f the neighbor.'
                                      ;
                          leaf update-source-addrv4 {
                            description 'Specify the update-source IPv4 address of the neighbor.'
                                        ;
                            type ncd:ipv4-address-none-zero ;
                          }
                        }
                        case update-source-ipv6 {
                          description 'Specify the update-source IPv6 address o'
                                    + 'f the neighbor.'
                                      ;
                          leaf update-source-addrv6 {
                            description 'Specify the update-source IPv6 address of the neighbor.'
                                        ;
                            type ncd:ipv6-address-none-zero ;
                          }
                        }
                      }
                    }
                    container neighbor-extend {
                      description 'Specify a neighbor.'
                                  ;
                      container idle-hold-time {
                        description 'Specifiy the length of time the peer is he'
                                  + 'ld in the idle state.'
                                    ;
                        presence idle-hold-time ;
                        leaf hold-time {
                          description 'Idle hold time.'
                                      ;
                          type uint32 {
                            range 1..3000 ;
                          }
                          units s ;
                          mandatory true ;
                        }
                        leaf increase {
                          description 'Increase idle hold time doubly to maximu'
                                    + 'm 3000.'
                                      ;
                          type empty ;
                        }
                      }
                      leaf keychain-name {
                        description 'Keychain name associated to peer for authe'
                                  + 'ntication.'
                                    ;
                        type string {
                          length 1..31 ;
                        }
                      }
                      container local-as {
                        description 'Specify a local-as number.'
                                    ;
                        presence local-as ;
                        leaf as-number {
                          description 'Autonomous system number (normal or 4 Oc'
                                    + 'tets).'
                                      ;
                          type ncd:asn-dot {
                            pattern '-?([1-9]+(\.(\d*)|0)?)|(0(\.\d+){1})'
                                    ;
                          }
                          mandatory true ;
                        }
                        leaf no-prepend {
                          description 'Do not prepend local-as to updates from '
                                    + 'EBGP peer.'
                                      ;
                          type empty ;
                        }
                        leaf replace-as {
                          description 'Replace real AS with local AS in the EBG'
                                    + 'P updates.'
                                      ;
                          type empty ;
                        }
                        leaf dual-as {
                          description 'Accept real AS or local AS from the EBGP'
                                    + ' peer.'
                                      ;
                          type empty ;
                        }
                      }
                      container password {
                        description 'Set a password of the neighbor.'
                                    ;
                        choice password {
                          description 'Set a password of the neighbor.'
                                      ;
                          case clear-words {
                            description 'Specify the clear password (1-80 characters).'
                                        ;
                            leaf clear-words {
                              description 'The clear password (1-80 characters).'
                                          ;
                              type string {
                                length 1..80 ;
                              }
                            }
                          }
                          case encrypt-words {
                            description 'Specify the encrypted password.'
                                        ;
                            leaf encrypt-words {
                              description 'Specify the encrypted password.'
                                          ;
                              type string {
                                length 64..172 ;
                              }
                            }
                          }
                        }
                      }
                      container timers {
                        description 'BGP per neighbor timers.'
                                    ;
                        presence timers ;
                        leaf keepalive {
                          description 'Adjust keepalive interval.'
                                      ;
                          type uint32 {
                            range 0..65535 ;
                          }
                          units s ;
                          mandatory true ;
                        }
                        leaf holdtime {
                          description 'Adjust holdtime.'
                                      ;
                          type uint32 {
                            range '0 | 3..65535'
                                  ;
                          }
                          units s ;
                          mandatory true ;
                        }
                      }
                      container tracking {
                        description 'Enable peer tracking.'
                                    ;
                        presence tracking ;
                        leaf tracking-ex {
                          description 'Peer tracking.'
                                      ;
                          type enumeration {
                            enum enable {
                              value 1 ;
                              description 'Enable peer tracking.'
                                          ;
                            }
                            enum disable {
                              value 0 ;
                              description 'Disable peer tracking.'
                                          ;
                            }
                            enum inherit {
                              value 2 ;
                              description 'If the neighbor joined a group, the status of tracking inherited from group.'
                                          ;
                            }
                          }
                          mandatory true ;
                        }
                        leaf delay {
                          description 'Delay time to reset the session.'
                                      ;
                          type uint32 {
                            range 1..65535 ;
                          }
                          units s ;
                        }
                      }
                      container transport {
                        description 'Specify TCP path MTU discovery or TCP MSS '
                                  + 'to this neighbor.'
                                    ;
                        choice transport {
                          description 'Specify TCP path MTU discovery or TCP MS'
                                    + 'S to this neighbor.'
                                      ;
                          case path-mtu-discovery {
                            description 'Use transport path MTU discovery.'
                                        ;
                            leaf path-mtu-discovery {
                              description 'Use transport path MTU discovery.'
                                          ;
                              type empty ;
                            }
                          }
                          case mss {
                            description 'Specify TCP MSS to this neighbor.'
                                        ;
                            leaf mss {
                              description 'Set TCP initial maximum segment size.'
                                          ;
                              type uint32 {
                                range 68..10000 ;
                              }
                            }
                          }
                        }
                      }
                      leaf neighbor-stalepath-time {
                        description "Set the max time to hold on to restarting "
                                  + "peer's stale paths."
                                    ;
                        type uint32 {
                          range 1..604800 {
                            description 'Delay value.'
                                        ;
                          }
                        }
                        units s ;
                        ncd:revise-date 2021-02-01 ;
                      }
                      leaf neighbor-stalepath-time-permanent {
                        description 'Hold on stale paths permanently.'
                                    ;
                        type empty ;
                        ncd:revise-date 2021-02-01 ;
                      }
                    }
                  }
                }
                container neighbor-ipv4 {
                  description 'Specify a IPv4 neighbor.'
                              ;
                  list neighbor {
                    description 'Specify a neighbor.'
                                ;
                    key ipv4-address ;
                    leaf ipv4-address {
                      description 'Neighbor IPv4 address.'
                                  ;
                      type ncd:ipv4-address ;
                    }
                    leaf remote-as {
                      description 'Specify a BGP neighbor AS number.'
                                  ;
                      type ncd:asn-dot ;
                    }
                    leaf join-peergroup {
                      description 'Create/Join a peer group(1-31 characters).'
                                  ;
                      type string {
                        length 1..31 ;
                      }
                    }
                    leaf advertisement-interval {
                      description 'Minimum interval between sending BGP routing'
                                + ' which is not locally originated updates.'
                                  ;
                      type uint32 {
                        range 1..65535 ;
                      }
                      units s ;
                    }
                    leaf connect-retry-interval {
                      description 'Set data of connect-retry timer for this nei'
                                + 'ghbor.'
                                  ;
                      type uint32 {
                        range 1..65535 ;
                      }
                      units s ;
                    }
                    leaf description {
                      description 'Neighbor specific description.'
                                  ;
                      type ncd:string-with-blank {
                        length 1..80 ;
                      }
                    }
                    leaf dscp {
                      description 'Set DSCP value.'
                                  ;
                      type uint8 {
                        range 0..63 ;
                      }
                    }
                    leaf enforce-first-as-disable {
                      description 'Not enforce the first AS for EBGP neighbor r'
                                + 'outes'
                                  ;
                      type empty ;
                    }
                    container fall-over {
                      description 'Set BFD supporting for fallover.'
                                  ;
                      presence fall-over ;
                      leaf bfd {
                        description 'Enable BFD support for fallover.'
                                    ;
                        type empty ;
                        mandatory true ;
                      }
                      container bfd-parameters {
                        description 'The parameters of BFD.'
                                    ;
                        presence bfd-parameters ;
                        choice bfd-parameters {
                          description 'Config bfd parameters'
                                      ;
                          case template-name {
                            description 'Template name'
                                        ;
                            leaf template {
                              description 'BFD template name.'
                                          ;
                              type string {
                                length 1..31 ;
                              }
                            }
                          }
                          case parameters {
                            description Parameters. ;
                            leaf interval {
                              description 'Minimum send interval.'
                                          ;
                              type uint32 {
                                range 10..990 ;
                              }
                              units ms ;
                              mandatory true ;
                            }
                            leaf min-rx {
                              description 'Minimum receive interval.'
                                          ;
                              type uint32 {
                                range 10..990 ;
                              }
                              units ms ;
                              mandatory true ;
                            }
                            leaf multiplier {
                              description Multiplier. ;
                              type uint8 {
                                range 3..50 ;
                              }
                              mandatory true ;
                            }
                          }
                        }
                      }
                      leaf bfd-hop {
                        description 'bfd optional hop'
                                    ;
                        type enumeration {
                          enum single-hop {
                            value 1 ;
                            description 'Set single-hop bfd'
                                        ;
                          }
                          enum multi-hop {
                            value 2 ;
                            description 'Set multi-hop bfd'
                                        ;
                          }
                        }
                      }
                    }
                    leaf open-delay {
                      description 'Delay to send open message.'
                                  ;
                      type uint32 {
                        range 1..240 ;
                      }
                      units s ;
                    }
                    leaf originate-interval {
                      description 'Minimum interval between sending BGP routing'
                                + ' which is locally originated updates.'
                                  ;
                      type uint32 {
                        range 1..65535 ;
                      }
                      units s ;
                    }
                    leaf passive {
                      description "Don't send open messages to this neighbor ac"
                                + "tively."
                                  ;
                      type empty ;
                    }
                    leaf orf-prefix-filter-cisco {
                      description 'Compatible with CISCO.'
                                  ;
                      type empty ;
                    }
                    leaf enhanced-route-refresh-disable {
                      description 'Enhanced route refresh capability.'
                                  ;
                      type empty ;
                      ncd:revise-date 2020-10-10 ;
                    }
                    leaf four-byte-as-disable {
                      description 'Disable 4-byte AS capability.'
                                  ;
                      type empty ;
                      ncd:revise-date 2020-10-10 ;
                    }
                    leaf receive-single-label {
                      description 'Receive single label only for label unicast '
                                + 'route.'
                                  ;
                      type enumeration {
                        enum disable {
                          value 0 ;
                          description 'Disable receive single label only for la'
                                    + 'bel unicast route'
                                      ;
                        }
                        enum enable {
                          value 1 ;
                          description 'Enable receive single label only for lab'
                                    + 'el unicast route'
                                      ;
                        }
                        enum inherit {
                          value 2 ;
                          description 'If the neighbor joined a group, the stat'
                                    + 'us inherited from group'
                                      ;
                        }
                      }
                    }
                    leaf ignore-error-packet {
                      description 'Ignore error packet for this neighbor.'
                                  ;
                      type enumeration {
                        enum disable {
                          value 0 ;
                          description 'Disable peer ignore error packet'
                                      ;
                        }
                        enum enable {
                          value 1 ;
                          description 'Enable peer ignore error packet'
                                      ;
                        }
                        enum inherit {
                          value 2 ;
                          description 'If the neighbor joined a group, the stat'
                                    + 'us inherited from group.'
                                      ;
                        }
                      }
                    }
                    container set-ttl {
                      description 'ebgp-multihop-ttl and ttl-security-hops are '
                                + 'mutex.'
                                  ;
                      choice set-ttl {
                        description 'ebgp-multihop-ttl and ttl-security-hops ar'
                                  + 'e mutex.'
                                    ;
                        case ebgp-multihop-ttl {
                          description 'Allow EBGP neighbors not on directly con'
                                    + 'nected net.'
                                      ;
                          leaf ebgp-multihop {
                            description 'Allow EBGP neighbors not on directly connected net.'
                                        ;
                            type uint8 {
                              range 1..255 ;
                            }
                          }
                        }
                        case ttl-security-hops {
                          description 'Enable EBGP TTL security check.'
                                      ;
                          leaf ttl-security-hops {
                            description 'Enable EBGP TTL security check.'
                                        ;
                            type uint8 {
                              range 1..254 ;
                            }
                          }
                        }
                      }
                    }
                    container shutdown {
                      description 'Shut down this neighbor administratively or '
                                + 'when state of track-group is down.'
                                  ;
                      presence shutdown ;
                      leaf shut-down {
                        description 'Administratively shut down this neighbor.'
                                    ;
                        type empty ;
                        mandatory true ;
                      }
                      leaf track-group {
                        description 'Shut down this neighbor when state of trac'
                                  + 'k-group is down.'
                                    ;
                        type string {
                          length 1..31 ;
                        }
                      }
                    }
                    container update-source-ex {
                      description 'Specify the update-source configuration of t'
                                + 'he neighbor.'
                                  ;
                      choice update-source {
                        description 'Specify the update-source interface name o'
                                  + 'f the neighbor.'
                                    ;
                        case update-source-if {
                          description 'Specify the update-source interface name'
                                    + ' of the neighbor.'
                                      ;
                          leaf update-source-ifname {
                            description 'Specify the update-source interface name of the neighbor.'
                                        ;
                            type ncd:ifname ;
                          }
                        }
                        case update-source-ipv4 {
                          description 'Specify the update-source IPv4 address o'
                                    + 'f the neighbor.'
                                      ;
                          leaf update-source-addrv4 {
                            description 'Specify the update-source IPv4 address of the neighbor.'
                                        ;
                            type ncd:ipv4-address-none-zero ;
                          }
                        }
                        case update-source-ipv6 {
                          description 'Specify the update-source IPv6 address o'
                                    + 'f the neighbor.'
                                      ;
                          leaf update-source-addrv6 {
                            description 'Specify the update-source IPv6 address of the neighbor.'
                                        ;
                            type ncd:ipv6-address-none-zero ;
                          }
                        }
                      }
                    }
                    container neighbor-extend {
                      description 'Specify a neighbor.'
                                  ;
                      container idle-hold-time {
                        description 'Specifiy the length of time the peer is he'
                                  + 'ld in the idle state.'
                                    ;
                        presence idle-hold-time ;
                        leaf hold-time {
                          description 'Idle hold time.'
                                      ;
                          type uint32 {
                            range 1..3000 ;
                          }
                          units s ;
                          mandatory true ;
                        }
                        leaf increase {
                          description 'Increase idle hold time doubly to maximu'
                                    + 'm 3000.'
                                      ;
                          type empty ;
                        }
                      }
                      leaf keychain-name {
                        description 'Keychain name associated to peer for authe'
                                  + 'ntication.'
                                    ;
                        type string {
                          length 1..31 ;
                        }
                      }
                      container local-as {
                        description 'Specify a local-as number.'
                                    ;
                        presence local-as ;
                        leaf as-number {
                          description 'Autonomous system number (normal or 4 Oc'
                                    + 'tets).'
                                      ;
                          type ncd:asn-dot {
                            pattern '-?([1-9]+(\.(\d*)|0)?)|(0(\.\d+){1})'
                                    ;
                          }
                          mandatory true ;
                        }
                        leaf no-prepend {
                          description 'Do not prepend local-as to updates from '
                                    + 'EBGP peer.'
                                      ;
                          type empty ;
                        }
                        leaf replace-as {
                          description 'Replace real AS with local AS in the EBG'
                                    + 'P updates.'
                                      ;
                          type empty ;
                        }
                        leaf dual-as {
                          description 'Accept real AS or local AS from the EBGP'
                                    + ' peer.'
                                      ;
                          type empty ;
                        }
                      }
                      container password {
                        description 'Set a password of the neighbor.'
                                    ;
                        choice password {
                          description 'Set a password of the neighbor.'
                                      ;
                          case clear-words {
                            description 'Specify the clear password (1-80 characters).'
                                        ;
                            leaf clear-words {
                              description 'The clear password (1-80 characters).'
                                          ;
                              type string {
                                length 1..80 ;
                              }
                            }
                          }
                          case encrypt-words {
                            description 'Specify the encrypted password.'
                                        ;
                            leaf encrypt-words {
                              description 'Specify the encrypted password.'
                                          ;
                              type string {
                                length 64..172 ;
                              }
                            }
                          }
                        }
                      }
                      container timers {
                        description 'BGP per neighbor timers.'
                                    ;
                        presence timers ;
                        leaf keepalive {
                          description 'Adjust keepalive interval.'
                                      ;
                          type uint32 {
                            range 0..65535 ;
                          }
                          units s ;
                          mandatory true ;
                        }
                        leaf holdtime {
                          description 'Adjust holdtime.'
                                      ;
                          type uint32 {
                            range '0 | 3..65535'
                                  ;
                          }
                          units s ;
                          mandatory true ;
                        }
                      }
                      container tracking {
                        description 'Enable peer tracking.'
                                    ;
                        presence tracking ;
                        leaf tracking-ex {
                          description 'Peer tracking.'
                                      ;
                          type enumeration {
                            enum enable {
                              value 1 ;
                              description 'Enable peer tracking.'
                                          ;
                            }
                            enum disable {
                              value 0 ;
                              description 'Disable peer tracking.'
                                          ;
                            }
                            enum inherit {
                              value 2 ;
                              description 'If the neighbor joined a group, the status of tracking inherited from group.'
                                          ;
                            }
                          }
                          mandatory true ;
                        }
                        leaf delay {
                          description 'Delay time to reset the session.'
                                      ;
                          type uint32 {
                            range 1..65535 ;
                          }
                          units s ;
                        }
                      }
                      container transport {
                        description 'Specify TCP path MTU discovery or TCP MSS '
                                  + 'to this neighbor.'
                                    ;
                        choice transport {
                          description 'Specify TCP path MTU discovery or TCP MS'
                                    + 'S to this neighbor.'
                                      ;
                          case path-mtu-discovery {
                            description 'Use transport path MTU discovery.'
                                        ;
                            leaf path-mtu-discovery {
                              description 'Use transport path MTU discovery.'
                                          ;
                              type empty ;
                            }
                          }
                          case mss {
                            description 'Specify TCP MSS to this neighbor.'
                                        ;
                            leaf mss {
                              description 'Set TCP initial maximum segment size.'
                                          ;
                              type uint32 {
                                range 68..10000 ;
                              }
                            }
                          }
                        }
                      }
                      leaf neighbor-stalepath-time {
                        description "Set the max time to hold on to restarting "
                                  + "peer's stale paths."
                                    ;
                        type uint32 {
                          range 1..604800 {
                            description 'Delay value.'
                                        ;
                          }
                        }
                        units s ;
                        ncd:revise-date 2021-02-01 ;
                      }
                      leaf neighbor-stalepath-time-permanent {
                        description 'Hold on stale paths permanently.'
                                    ;
                        type empty ;
                        ncd:revise-date 2021-02-01 ;
                      }
                    }
                  }
                }
                container neighbor-ipv6 {
                  description 'Specify a IPv6 neighbor.'
                              ;
                  list neighbor {
                    description 'Specify a neighbor.'
                                ;
                    key ipv6-address ;
                    leaf ipv6-address {
                      description 'Neighbor IPv6 address.'
                                  ;
                      type ncd:ipv6-address ;
                    }
                    leaf remote-as {
                      description 'Specify a BGP neighbor AS number.'
                                  ;
                      type ncd:asn-dot ;
                    }
                    leaf join-peergroup {
                      description 'Create/Join a peer group(1-31 characters).'
                                  ;
                      type string {
                        length 1..31 ;
                      }
                    }
                    leaf advertisement-interval {
                      description 'Minimum interval between sending BGP routing'
                                + ' which is not locally originated updates.'
                                  ;
                      type uint32 {
                        range 1..65535 ;
                      }
                      units s ;
                    }
                    leaf connect-retry-interval {
                      description 'Set data of connect-retry timer for this nei'
                                + 'ghbor.'
                                  ;
                      type uint32 {
                        range 1..65535 ;
                      }
                      units s ;
                    }
                    leaf description {
                      description 'Neighbor specific description.'
                                  ;
                      type ncd:string-with-blank {
                        length 1..80 ;
                      }
                    }
                    leaf dscp {
                      description 'Set DSCP value.'
                                  ;
                      type uint8 {
                        range 0..63 ;
                      }
                    }
                    leaf enforce-first-as-disable {
                      description 'Not enforce the first AS for EBGP neighbor r'
                                + 'outes'
                                  ;
                      type empty ;
                    }
                    container fall-over {
                      description 'Set BFD supporting for fallover.'
                                  ;
                      presence 'Enable BFD support for fallover.'
                               ;
                      leaf bfd {
                        description 'Enable BFD support for fallover.'
                                    ;
                        type empty ;
                        mandatory true ;
                      }
                      container bfd-parameters {
                        description 'The parameters of BFD.'
                                    ;
                        presence bfd-parameters ;
                        choice bfd-parameters {
                          description 'Config bfd parameters'
                                      ;
                          case template-name {
                            description 'Template name'
                                        ;
                            leaf template {
                              description 'BFD template name.'
                                          ;
                              type string {
                                length 1..31 ;
                              }
                            }
                          }
                          case parameters {
                            description Parameters ;
                            leaf interval {
                              description 'Minimum send interval.'
                                          ;
                              type uint32 {
                                range 10..990 ;
                              }
                              units ms ;
                              mandatory true ;
                            }
                            leaf min-rx {
                              description 'Minimum receive interval.'
                                          ;
                              type uint32 {
                                range 10..990 ;
                              }
                              units ms ;
                              mandatory true ;
                            }
                            leaf multiplier {
                              description Multiplier. ;
                              type uint8 {
                                range 3..50 ;
                              }
                              mandatory true ;
                            }
                          }
                        }
                      }
                      leaf bfd-hop {
                        description 'bfd optional hop'
                                    ;
                        type enumeration {
                          enum single-hop {
                            value 1 ;
                            description 'Set single-hop bfd'
                                        ;
                          }
                          enum multi-hop {
                            value 2 ;
                            description 'Set multi-hop bfd'
                                        ;
                          }
                        }
                      }
                    }
                    leaf open-delay {
                      description 'Delay to send open message.'
                                  ;
                      type uint32 {
                        range 1..240 ;
                      }
                      units s ;
                    }
                    leaf originate-interval {
                      description 'Minimum interval between sending BGP routing'
                                + ' which is locally originated updates.'
                                  ;
                      type uint32 {
                        range 1..65535 ;
                      }
                      units s ;
                    }
                    leaf passive {
                      description "Don't send open messages to this neighbor ac"
                                + "tively."
                                  ;
                      type empty ;
                    }
                    leaf orf-prefix-filter-cisco {
                      description 'Compatible with CISCO.'
                                  ;
                      type empty ;
                    }
                    leaf four-byte-as-disable {
                      description 'Disable 4-byte AS capability.'
                                  ;
                      type empty ;
                      ncd:revise-date 2020-10-10 ;
                    }
                    leaf enhanced-route-refresh-disable {
                      description 'Enhanced route refresh capability.'
                                  ;
                      type empty ;
                      ncd:revise-date 2020-10-10 ;
                    }
                    leaf receive-single-label {
                      description 'Receive single label only for label unicast '
                                + 'route.'
                                  ;
                      type enumeration {
                        enum disable {
                          value 0 ;
                          description 'Disable receive single label only for la'
                                    + 'bel unicast route'
                                      ;
                        }
                        enum enable {
                          value 1 ;
                          description 'Enable receive single label only for lab'
                                    + 'el unicast route'
                                      ;
                        }
                        enum inherit {
                          value 2 ;
                          description 'If the neighbor joined a group, the stat'
                                    + 'us inherited from group'
                                      ;
                        }
                      }
                      ncd:revise-date 2020-10-10 ;
                    }
                    leaf ignore-error-packet {
                      description 'Ignore error packet for this neighbor.'
                                  ;
                      type enumeration {
                        enum disable {
                          value 0 ;
                          description 'Disable peer ignore error packet'
                                      ;
                        }
                        enum enable {
                          value 1 ;
                          description 'Enable peer ignore error packet'
                                      ;
                        }
                        enum inherit {
                          value 2 ;
                          description 'If the neighbor joined a group, the stat'
                                    + 'us inherited from group.'
                                      ;
                        }
                      }
                      ncd:revise-date 2020-10-10 ;
                    }
                    container set-ttl {
                      description 'ebgp-multihop-ttl and ttl-security-hops are '
                                + 'mutex.'
                                  ;
                      choice set-ttl {
                        description 'ebgp-multihop-ttl and ttl-security-hops ar'
                                  + 'e mutex.'
                                    ;
                        case ebgp-multihop-ttl {
                          description 'Allow EBGP neighbors not on directly con'
                                    + 'nected net.'
                                      ;
                          leaf ebgp-multihop {
                            description 'Allow EBGP neighbors not on directly connected net.'
                                        ;
                            type uint8 {
                              range 1..255 ;
                            }
                          }
                        }
                        case ttl-security-hops {
                          description 'Enable EBGP TTL security check.'
                                      ;
                          leaf ttl-security-hops {
                            description 'Enable EBGP TTL security check.'
                                        ;
                            type uint8 {
                              range 1..254 ;
                            }
                          }
                        }
                      }
                    }
                    container shutdown {
                      description 'Shut down this neighbor administratively or '
                                + 'when state of track-group is down.'
                                  ;
                      presence shutdown ;
                      leaf shut-down {
                        description 'Administratively shut down this neighbor.'
                                    ;
                        type empty ;
                        mandatory true ;
                      }
                      leaf track-group {
                        description 'Shut down this neighbor when state of trac'
                                  + 'k-group is down.'
                                    ;
                        type string {
                          length 1..31 ;
                        }
                      }
                    }
                    container update-source-ex {
                      description 'Specify the update-source configuration of t'
                                + 'he neighbor.'
                                  ;
                      choice update-source {
                        description 'Specify the update-source interface name o'
                                  + 'f the neighbor.'
                                    ;
                        case update-source-if {
                          description 'Specify the update-source interface name'
                                    + ' of the neighbor.'
                                      ;
                          leaf update-source-ifname {
                            description 'Specify the update-source interface name of the neighbor.'
                                        ;
                            type ncd:ifname ;
                          }
                        }
                        case update-source-ipv4 {
                          description 'Specify the update-source IPv4 address o'
                                    + 'f the neighbor.'
                                      ;
                          leaf update-source-addrv4 {
                            description 'Specify the update-source IPv4 address of the neighbor.'
                                        ;
                            type ncd:ipv4-address-none-zero ;
                          }
                        }
                        case update-source-ipv6 {
                          description 'Specify the update-source IPv6 address o'
                                    + 'f the neighbor.'
                                      ;
                          leaf update-source-addrv6 {
                            description 'Specify the update-source IPv6 address of the neighbor.'
                                        ;
                            type ncd:ipv6-address-none-zero ;
                          }
                        }
                      }
                    }
                    container neighbor-extend {
                      description 'Specify a neighbor.'
                                  ;
                      container idle-hold-time {
                        description 'Specifiy the length of time the peer is he'
                                  + 'ld in the idle state.'
                                    ;
                        presence idle-hold-time ;
                        leaf hold-time {
                          description 'Idle hold time.'
                                      ;
                          type uint32 {
                            range 1..3000 ;
                          }
                          units s ;
                          mandatory true ;
                        }
                        leaf increase {
                          description 'Increase idle hold time doubly to maximu'
                                    + 'm 3000.'
                                      ;
                          type empty ;
                        }
                      }
                      leaf keychain-name {
                        description 'Keychain name associated to peer for authe'
                                  + 'ntication.'
                                    ;
                        type string {
                          length 1..31 ;
                        }
                      }
                      container local-as {
                        description 'Specify a local-as number.'
                                    ;
                        presence local-as ;
                        leaf as-number {
                          description 'Autonomous system number (normal or 4 Oc'
                                    + 'tets).'
                                      ;
                          type ncd:asn-dot {
                            pattern '-?([1-9]+(\.(\d*)|0)?)|(0(\.\d+){1})'
                                    ;
                          }
                          mandatory true ;
                        }
                        leaf no-prepend {
                          description 'Do not prepend local-as to updates from '
                                    + 'EBGP peer.'
                                      ;
                          type empty ;
                        }
                        leaf replace-as {
                          description 'Replace real AS with local AS in the EBG'
                                    + 'P updates.'
                                      ;
                          type empty ;
                        }
                        leaf dual-as {
                          description 'Accept real AS or local AS from the EBGP'
                                    + ' peer.'
                                      ;
                          type empty ;
                        }
                      }
                      container password {
                        description 'Set a password of the neighbor.'
                                    ;
                        choice password {
                          description 'Set a password of the neighbor.'
                                      ;
                          case clear-words {
                            description 'Specify the clear password (1-80 characters).'
                                        ;
                            leaf clear-words {
                              description 'The clear password (1-80 characters).'
                                          ;
                              type string {
                                length 1..80 ;
                              }
                            }
                          }
                          case encrypt-words {
                            description 'Specify the encrypted password.'
                                        ;
                            leaf encrypt-words {
                              description 'Specify the encrypted password.'
                                          ;
                              type string {
                                length 64..172 ;
                              }
                            }
                          }
                        }
                      }
                      container timers {
                        description 'BGP per neighbor timers.'
                                    ;
                        presence timers ;
                        leaf keepalive {
                          description 'Adjust keepalive interval.'
                                      ;
                          type uint32 {
                            range 0..65535 ;
                          }
                          units s ;
                          mandatory true ;
                        }
                        leaf holdtime {
                          description 'Adjust holdtime.'
                                      ;
                          type uint32 {
                            range '0 | 3..65535'
                                  ;
                          }
                          units s ;
                          mandatory true ;
                        }
                      }
                      container tracking {
                        description 'Enable peer tracking.'
                                    ;
                        presence tracking ;
                        leaf tracking-ex {
                          description 'Peer tracking.'
                                      ;
                          type enumeration {
                            enum enable {
                              value 1 ;
                              description 'Enable peer tracking.'
                                          ;
                            }
                            enum disable {
                              value 0 ;
                              description 'Disable peer tracking.'
                                          ;
                            }
                            enum inherit {
                              value 2 ;
                              description 'If the neighbor joined a group, the status of tracking inherited from group.'
                                          ;
                            }
                          }
                          mandatory true ;
                        }
                        leaf delay {
                          description 'Delay time to reset the session.'
                                      ;
                          type uint32 {
                            range 1..65535 ;
                          }
                          units s ;
                        }
                      }
                      container transport {
                        description 'Specify TCP path MTU discovery or TCP MSS '
                                  + 'to this neighbor.'
                                    ;
                        choice transport {
                          description 'Specify TCP path MTU discovery or TCP MS'
                                    + 'S to this neighbor.'
                                      ;
                          case path-mtu-discovery {
                            description 'Use transport path MTU discovery.'
                                        ;
                            leaf path-mtu-discovery {
                              description 'Use transport path MTU discovery.'
                                          ;
                              type empty ;
                            }
                          }
                          case mss {
                            description 'Specify TCP MSS to this neighbor.'
                                        ;
                            leaf mss {
                              description 'Set TCP initial maximum segment size.'
                                          ;
                              type uint32 {
                                range 68..10000 ;
                              }
                            }
                          }
                        }
                      }
                      leaf neighbor-stalepath-time {
                        description "Set the max time to hold on to restarting "
                                  + "peer's stale paths."
                                    ;
                        type uint32 {
                          range 1..604800 {
                            description 'Delay value.'
                                        ;
                          }
                        }
                        units s ;
                        ncd:revise-date 2021-02-01 ;
                      }
                      leaf neighbor-stalepath-time-permanent {
                        description 'Hold on stale paths permanently.'
                                    ;
                        type empty ;
                        ncd:revise-date 2021-02-01 ;
                      }
                    }
                  }
                }
              }
              container safi-ipv4-unicast {
                description 'Specify parameters for IPv4 unicast VRF.'
                            ;
                presence safi-ipv4-unicast ;
                leaf advertise-active-only {
                  description 'Advertise the active routes only.'
                              ;
                  type empty ;
                }
                leaf maximum-paths-ibgp {
                  description 'Set IBGP-multipath.'
                              ;
                  type uint32 {
                    range 1..32 ;
                  }
                  default 1 ;
                }
                leaf maximum-paths-ebgp {
                  description 'Set EBGP-multipath.'
                              ;
                  type uint32 {
                    range 1..32 ;
                  }
                  default 1 ;
                }
                leaf maximum-paths-eibgp {
                  description 'Set EIBGP-multipath. Mutex with maximum-paths-ib'
                            + 'gp and maximum-paths-ebgp.'
                              ;
                  type uint32 {
                    range 1..32 ;
                  }
                  default 1 ;
                }
                leaf nexthop-trigger-delay {
                  description 'Set the delay time to trigger nexthop tracking.'
                              ;
                  type uint32 {
                    range 1..1200 {
                      description 'Delay value.'
                                  ;
                    }
                  }
                  units s ;
                }
                leaf default-information-originate {
                  description 'Notify default route.'
                              ;
                  type empty ;
                }
                leaf default-metric {
                  description 'Set metric of BGP routes without MED.'
                              ;
                  type uint32 {
                    range 0..4294967295 ;
                  }
                  default 0 ;
                }
                leaf distance-bgp-external {
                  description 'Distance for routes external to the AS.'
                              ;
                  type uint32 {
                    range 1..255 ;
                  }
                  default 20 ;
                }
                leaf distance-bgp-internal {
                  description 'Distance for routes internal to the AS.'
                              ;
                  type uint32 {
                    range 1..255 ;
                  }
                  default 200 ;
                }
                leaf distance-bgp-local {
                  description 'Distance for BGP local routes.'
                              ;
                  type uint32 {
                    range 1..255 ;
                  }
                  default 254 ;
                }
                leaf distance-route-map {
                  description 'Define distance by route-map.This node has highe'
                            + 'r priority than distance-bgp-internal,distance-b'
                            + 'gp-external and distance-bgp-local.'
                              ;
                  type string {
                    length 1..200 ;
                  }
                  ncd:revise-date 2020-09-08 ;
                }
                leaf distance-route-policy {
                  description 'Define distance by route-policy.This node has hi'
                            + 'gher priority than distance-bgp-internal,distanc'
                            + 'e-bgp-external and distance-bgp-local.'
                              ;
                  type string {
                    length 1..200 ;
                  }
                  ncd:revise-date 2020-10-10 ;
                }
                leaf import-best-path {
                  description 'Maximum number of paths that can be imported int'
                            + 'o the VRF.'
                              ;
                  type uint32 {
                    range 1..32 ;
                  }
                }
                leaf table-map {
                  description 'Map external entry attributes into routing table.'
                              ;
                  type string {
                    length 1..200 ;
                  }
                }
                leaf frr-capability {
                  description 'Enable FRR capability.'
                              ;
                  type empty ;
                }
                leaf frr-wtr {
                  description 'Set the WTR time.'
                              ;
                  type int32 {
                    range 1..12 ;
                  }
                  units min ;
                }
                leaf frr-enhanced {
                  description 'If there is no BGP route as a backup route, then'
                            + ' choose the default route for FRR.'
                              ;
                  type empty ;
                }
                leaf table-policy {
                  description 'Set external entry attributes into routing table.'
                              ;
                  type string {
                    length 1..200 ;
                  }
                }
                container route-scan-time {
                  description 'Adjust BGP route scan timers.'
                              ;
                  presence 'The ability of BGP route scan.'
                           ;
                  leaf interval-wait {
                    description 'The interval of scan waiting. Default value is'
                              + ' 500.'
                                ;
                    type uint32 {
                      range 1..65535 ;
                    }
                    units ms ;
                    mandatory true ;
                  }
                  leaf initial {
                    description 'The initialization time of scan. Default value'
                              + ' is 50.'
                                ;
                    type uint32 {
                      range 1..65535 ;
                    }
                    units ms ;
                    mandatory true ;
                  }
                  leaf max-wait {
                    description 'The max waiting time of scan. Default value is'
                              + ' 5000.'
                                ;
                    type uint32 {
                      range 1..65535 ;
                    }
                    units ms ;
                    mandatory true ;
                  }
                }
                container additional-paths {
                  description 'Additional paths in the BGP table.'
                              ;
                  leaf selection-route-map {
                    description 'Selection criteria to pick the additional path'
                              + 's.'
                                ;
                    type string {
                      length 1..200 ;
                    }
                  }
                }
                leaf urpf-id-download {
                  if-feature urpf ;
                  description 'Download URPF-ID information to RTM.'
                              ;
                  type empty ;
                }
                container group-to-group {
                  description 'Configure filter group to filter group route ref'
                            + 'lection.'
                              ;
                  presence group-to-group ;
                  leaf reflection {
                    description 'Reflection of routes is allowed.'
                                ;
                    type empty ;
                    mandatory true ;
                  }
                  leaf next-hop-self {
                    description 'Disable the next hop calculation.'
                                ;
                    type empty ;
                  }
                }
                leaf default-set-mpls-label {
                  description 'Set MPLS label for local route.'
                              ;
                  type empty ;
                }
                leaf ebgp-interface-sensitive {
                  description 'Enable or disable interface sensitive for EBGP n'
                            + 'eighbor.'
                              ;
                  type enumeration {
                    enum disable {
                      value 0 ;
                    }
                    enum enable {
                      value 1 ;
                    }
                  }
                  default enable ;
                }
                leaf entropy-label {
                  description 'entropy-label enable or disable'
                              ;
                  type enumeration {
                    enum disable {
                      value 0 ;
                    }
                    enum enable {
                      value 1 ;
                    }
                  }
                }
                leaf bgp-bestpath-origin {
                  description 'bgp bestpath origin-from L3VPN neighbor or EVPN '
                            + 'neighbor.'
                              ;
                  type enumeration {
                    enum l3vpn {
                      value 1 ;
                      description 'bgp bestpath origin-from L3VPN neighbor'
                                  ;
                    }
                    enum evpn {
                      value 2 ;
                      description 'bgp bestpath origin-from EVPN neighbor'
                                  ;
                    }
                  }
                }
                leaf link-bandwidth-download {
                  description 'Download link-bandwidth information to RTM.'
                              ;
                  type empty ;
                }
                leaf nexthop-recursive-default-route {
                  description 'Nexthop recursive lookup default-route.'
                              ;
                  type enumeration {
                    enum enable {
                      value 1 ;
                    }
                    enum disable {
                      value 0 ;
                    }
                  }
                  default enable ;
                }
                leaf nexthop-recursive-null1 {
                  description 'Nexthop recursive lookup null1.'
                              ;
                  type enumeration {
                    enum enable {
                      value 1 ;
                    }
                    enum disable {
                      value 0 ;
                    }
                  }
                  default enable ;
                  ncd:revise-date 2020-12-09 ;
                }
                leaf bgp-bestpath-nexthop-priority {
                  description 'Set BGP bestpath nexthop priority.'
                              ;
                  type enumeration {
                    enum ipv4 {
                      value 1 ;
                      description 'BGP bestpath nexthop priority is ipv4'
                                  ;
                    }
                    enum ipv6 {
                      value 2 ;
                      description 'BGP bestpath nexthop priority is ipv6'
                                  ;
                    }
                  }
                  ncd:revise-date 2020-08-29 ;
                }
                leaf download-community {
                  description 'The maximum number of communities for one route.'
                              ;
                  type uint8 {
                    range 1..255 ;
                  }
                  ncd:revise-date 2020-10-10 ;
                }
                leaf bgp-attr-set {
                  description 'Receive or/and send ATTR-SET attribute.'
                              ;
                  type enumeration {
                    enum both {
                      value 1 ;
                      description 'Receive and send ATTR-SET attribute.'
                                  ;
                    }
                    enum receive {
                      value 2 ;
                      description 'Receive ATTR-SET attribute.'
                                  ;
                    }
                    enum send {
                      value 3 ;
                      description 'Send ATTR-SET attribute.'
                                  ;
                    }
                  }
                  ncd:revise-date 2021-04-21 ;
                }
                container rib-only {
                  description 'BGP routes are not delivered to the IP routing t'
                            + 'able.'
                              ;
                  presence 'BGP routes are not delivered to the IP routing table'
                           ;
                  leaf rib-only-set {
                    description 'Enable rib-only.'
                                ;
                    type empty ;
                    mandatory true ;
                  }
                  leaf rib-only-routemap {
                    description 'Routing policy.'
                                ;
                    type string {
                      length 1..200 ;
                    }
                  }
                  leaf rib-only-routepolicy {
                    description 'Routing policy.'
                                ;
                    type string {
                      length 1..200 ;
                    }
                    ncd:revise-date 2020-10-10 ;
                  }
                }
                container damp {
                  description 'Enable route-flap dampening.'
                              ;
                  presence damp ;
                  choice dampening {
                    description 'Enable route-flap dampening.'
                                ;
                    case route-map {
                      description 'Route-map to specify criteria for dampening.'
                                  ;
                      leaf route-map-name {
                        description 'Route-map to specify criteria for dampenin'
                                  + 'g.'
                                    ;
                        type string {
                          length 1..200 ;
                        }
                      }
                      leaf route-policy-name {
                        description 'Route-policy to specify criteria for dampe'
                                  + 'ning.'
                                    ;
                        type string {
                          length 1..200 ;
                        }
                        ncd:revise-date 2020-10-10 ;
                      }
                    }
                    case parameter {
                      description 'Damp parameter.'
                                  ;
                      leaf half-time {
                        description 'Half-life time for the penalty.'
                                    ;
                        type uint32 {
                          range 1..45 ;
                        }
                        units min ;
                        mandatory true ;
                      }
                      leaf reuse {
                        description 'Value to start reusing a route.'
                                    ;
                        type uint32 {
                          range 1..20000 ;
                        }
                        mandatory true ;
                      }
                      leaf suppress {
                        description 'Value to start suppressing a route.'
                                    ;
                        type uint32 {
                          range 1..20000 ;
                        }
                        mandatory true ;
                      }
                      leaf max-suppress-time {
                        description 'Maximum duration to suppress a route.'
                                    ;
                        type uint32 {
                          range 1..255 ;
                        }
                        units min ;
                        mandatory true ;
                      }
                    }
                  }
                }
                container aggregates {
                  description 'Configure BGP aggregate entries.'
                              ;
                  presence aggregates ;
                  list aggregate {
                    description 'Configure BGP aggregate entries.'
                                ;
                    key 'aggregate-address aggregate-mask'
                        ;
                    leaf aggregate-address {
                      description 'Aggregate address.'
                                  ;
                      type ncd:ipv4-address ;
                    }
                    leaf aggregate-mask {
                      description 'Aggregate mask.'
                                  ;
                      type ncd:ipv4-mask ;
                    }
                    leaf as-set {
                      description 'Generate AS set path information.'
                                  ;
                      type empty ;
                    }
                    leaf strict {
                      description 'Strict condition.'
                                  ;
                      type empty ;
                    }
                    leaf summary-only {
                      description 'Filter more specific routes from updates.'
                                  ;
                      type empty ;
                    }
                    container agg-policies {
                      description 'Apply policy to aggregate route.'
                                  ;
                      choice agg-policy {
                        description 'Apply policy to aggregate route.'
                                    ;
                        case route-map {
                          description 'Apply route map to aggregate route.'
                                      ;
                          leaf attr-map {
                            description 'Attribute map name.'
                                        ;
                            type string {
                              length 1..200 ;
                            }
                          }
                          leaf supp-map {
                            description 'Suppress map name.'
                                        ;
                            type string {
                              length 1..200 ;
                            }
                          }
                          leaf orig-map {
                            description 'Origin map name.'
                                        ;
                            type string {
                              length 1..200 ;
                            }
                          }
                        }
                        case route-policy {
                          description 'Apply route-policy to aggregate route.'
                                      ;
                          leaf policy {
                            description 'Route-policy name.'
                                        ;
                            type string {
                              length 1..200 ;
                            }
                          }
                        }
                      }
                    }
                  }
                }
                container track {
                  description 'Event tracking.'
                              ;
                  presence track ;
                  container track-adjust-type-with-interface {
                    description 'Configure adjust-priority of track object with'
                              + ' interface.'
                                ;
                    list track-adjust-with-interface {
                      description 'Configure adjust-priority of track object wi'
                                + 'th interface.'
                                  ;
                      key 'track-name track-interface'
                          ;
                      leaf track-name {
                        description 'Name of track object (1-31 characters).'
                                    ;
                        type string {
                          length 1..31 ;
                        }
                      }
                      leaf track-interface {
                        description 'Source of track object.'
                                    ;
                        type ncd:ifname {
                          length 1..31 ;
                        }
                      }
                      leaf adjust-value {
                        description 'Value of adjust-priority.'
                                    ;
                        type uint32 {
                          range 1..100 ;
                        }
                        mandatory true ;
                      }
                    }
                  }
                  container track-adjust-type-without-interface {
                    description 'Configure adjust-priority of track object with'
                              + 'out interface.'
                                ;
                    list track-adjust-without-interface {
                      description 'Configure adjust-priority of track object wi'
                                + 'thout interface.'
                                  ;
                      max-elements 1 ;
                      key track-name ;
                      leaf track-name {
                        description 'Name of track object (1-31 characters).'
                                    ;
                        type string {
                          length 1..31 ;
                        }
                      }
                      leaf adjust-value {
                        description 'Value of adjust-priority.'
                                    ;
                        type uint32 {
                          range 1..100 ;
                        }
                        mandatory true ;
                      }
                    }
                  }
                }
                container neighbors {
                  description 'Specify a neighbor.'
                              ;
                  container neighbor-group {
                    description 'Specify a neighbor.'
                                ;
                    list neighbor-peergroup {
                      description 'Specify a neighbor.'
                                  ;
                      key neighbor-group ;
                      leaf neighbor-group {
                        description 'Peer group name (1-31 characters).'
                                    ;
                        type string {
                          length 1..31 ;
                        }
                      }
                      leaf activate {
                        description 'Enable the address family for this neighbo'
                                  + 'r.'
                                    ;
                        type enumeration {
                          enum disable {
                            value 0 ;
                          }
                          enum enable {
                            value 1 ;
                          }
                        }
                      }
                      leaf monitor {
                        description 'Config BMP monitor for the address family '
                                  + 'of this neighbor.'
                                    ;
                        type enumeration {
                          enum disable {
                            value 2 ;
                          }
                          enum enable {
                            value 1 ;
                          }
                          enum inherit-global-config {
                            value 0 ;
                          }
                        }
                      }
                      leaf advertise-maximum-prefix {
                        description 'Maximum number of prefix send to this peer.'
                                    ;
                        type uint32 {
                          range 1..4294967295 ;
                        }
                      }
                      leaf allowas-in {
                        description 'Accept as-path with my AS present in it.'
                                    ;
                        type uint32 {
                          range 1..10 ;
                        }
                      }
                      leaf as-override {
                        description 'Override matching AS-number while sending '
                                  + 'update.'
                                    ;
                        type empty ;
                      }
                      leaf as-path-loopcheck {
                        description 'Check as-path sending BGP routing to EBGP '
                                  + 'neighbor.'
                                    ;
                        type empty ;
                      }
                      leaf default-originate {
                        description 'Originate default route to this neighbor.'
                                    ;
                        type empty ;
                      }
                      leaf default-originate-routemap {
                        description 'Map external entry attributes into routing'
                                  + ' table.'
                                    ;
                        type string {
                          length 1..200 ;
                        }
                      }
                      leaf default-originate-routepolicy {
                        description 'Set external entry attributes into routing'
                                  + ' table.'
                                    ;
                        type string {
                          length 1..200 ;
                        }
                        ncd:revise-date 2020-10-10 ;
                      }
                      leaf maxas-in {
                        description 'Accept as-path not exceeded maxas-in.'
                                    ;
                        type uint32 {
                          range 1..250 ;
                        }
                      }
                      leaf next-hop-self {
                        description 'Disable the next hop calculation for this '
                                  + 'neighbor.'
                                    ;
                        type enumeration {
                          enum enable {
                            value 1 ;
                            description 'Apply next-hop-self for EBGP route.'
                                        ;
                          }
                          enum all {
                            value 2 ;
                            description 'Apply next-hop-self for both EBGP and IBGP route.'
                                        ;
                          }
                        }
                      }
                      leaf originate-interval {
                        status obsolete {
                          ncd:revise-date 2021-01-15 ;
                        }
                        description 'Minimum interval between sending BGP routi'
                                  + 'ng which is locally originated updates.'
                                    ;
                        type uint32 {
                          range 1..65535 ;
                        }
                        units s ;
                      }
                      leaf remove-private-as {
                        description 'EBGP use to remove private AS number.'
                                    ;
                        type enumeration {
                          enum disable {
                            value 0 ;
                          }
                          enum enable {
                            value 1 ;
                          }
                        }
                      }
                      leaf send-community {
                        description 'Send community to this neighbor.'
                                    ;
                        type empty ;
                      }
                      leaf send-large-community {
                        description 'Send Large-community to this neighbor.'
                                    ;
                        type empty ;
                      }
                      leaf route-reflector-client {
                        description 'Set this neighbor as a client peer.'
                                    ;
                        type empty ;
                      }
                      leaf send-med {
                        description 'Send metric attribute to this neighbor.'
                                    ;
                        type empty ;
                      }
                      leaf inherit-igp-metric {
                        description 'Med attribute inherited from IGP metric be'
                                  + 'fore sending updates'
                                    ;
                        type empty ;
                      }
                      leaf soft-reconfig {
                        description 'Neighbor soft reconfiguration.'
                                    ;
                        type enumeration {
                          enum soft-reconfiguration {
                            value 1 ;
                            description Soft-reconfiguration. ;
                          }
                          enum enforce-soft-reconfiguration {
                            value 2 ;
                            description 'Enforce soft-reconfiguration instead of sending route-refresh.'
                                        ;
                          }
                        }
                      }
                      leaf soo {
                        description 'Site-of-Origin extended community.'
                                    ;
                        type union {
                          type ncd:asn-nn ;
                          type ncd:asnd-nn ;
                          type ncd:ipadd-nn ;
                        }
                      }
                      leaf split-update-group {
                        description 'Split neighbor from update group.'
                                    ;
                        type empty ;
                      }
                      leaf orf-prefix-filter {
                        description 'Advertise prefixlist ORF capability to thi'
                                  + 's neighbor.'
                                    ;
                        type enumeration {
                          enum receive {
                            value 1 ;
                            description 'Capability to receive the ORF from this neighbor.'
                                        ;
                          }
                          enum send {
                            value 2 ;
                            description 'Capability to send the ORF to this neighbor.'
                                        ;
                          }
                          enum both {
                            value 3 ;
                            description 'Capability to send and receive the ORF.'
                                        ;
                          }
                        }
                      }
                      leaf weight {
                        description 'Set weight for routes from this neighbor.'
                                    ;
                        type uint32 {
                          range 1..65535 ;
                        }
                      }
                      leaf aigp {
                        description 'Enable AIGP for this neighbor.'
                                    ;
                        type empty ;
                      }
                      leaf send-label {
                        description 'Send NLRI with MPLS label to this neighbor.'
                                    ;
                        type empty ;
                      }
                      leaf announce-sid {
                        description 'Enable Prefix-SID attribute for this neigh'
                                  + 'bor.'
                                    ;
                        type enumeration {
                          enum enable {
                            value 1 ;
                            description 'Enable Prefix-SID attribute for this neighbor.'
                                        ;
                          }
                        }
                      }
                      container route-filter-group {
                        description 'Specify a neighbor to join a route-filter-'
                                  + 'group.'
                                    ;
                        presence route-filter-group ;
                        leaf filter-group {
                          description 'Route filter group name (1-31 characters'
                                    + ').'
                                      ;
                          type string {
                            length 1..31 ;
                          }
                          mandatory true ;
                        }
                        leaf next-hop-self {
                          description 'Disable the next hop calculation for thi'
                                    + 's neighbor.'
                                      ;
                          type empty ;
                        }
                      }
                      container advertise-map {
                        description 'Specify route-map for conditional advertis'
                                  + 'ement.'
                                    ;
                        presence 'Specify route-map for conditional advertiseme'
                               + 'nt'
                                 ;
                        leaf advertise-map-name {
                          description 'Advertise route-map name.'
                                      ;
                          type string {
                            length 1..200 ;
                          }
                          mandatory true ;
                        }
                        choice condition-map {
                          description 'Specify route-map for conditional advert'
                                    + 'isement.'
                                      ;
                          mandatory true ;
                          case exist-map {
                            description 'Advertise prefix only if prefix exists.'
                                        ;
                            leaf exist-map-name {
                              description 'Advertise prefix only if prefix exists.'
                                          ;
                              type string {
                                length 1..200 ;
                              }
                              mandatory true ;
                            }
                          }
                          case nonexist-map {
                            description 'Advertise prefix only if prefix does not exist.'
                                        ;
                            leaf non-exist-map-name {
                              description 'Advertise prefix only if prefix does not exist.'
                                          ;
                              type string {
                                length 1..200 ;
                              }
                              mandatory true ;
                            }
                          }
                        }
                      }
                      container neighbor-extend {
                        description 'Specify a neighbor.'
                                    ;
                        leaf prefix-list-in-name {
                          description 'Apply prefix list to incoming routes.'
                                      ;
                          type string {
                            length 1..169 ;
                          }
                        }
                        leaf prefix-list-out-name {
                          description 'Apply  prefix list to outbound routes.'
                                      ;
                          type string {
                            length 1..169 ;
                          }
                        }
                        leaf route-map-in-name {
                          description 'Apply route-map to incoming routes.'
                                      ;
                          type string {
                            length 1..200 ;
                          }
                        }
                        leaf route-map-out-name {
                          description 'Apply route-map to outbound routes.'
                                      ;
                          type string {
                            length 1..200 ;
                          }
                        }
                        container maximum-prefix {
                          description 'The action that generated when threshold'
                                    + ' value reached.'
                                      ;
                          presence 'The action that generated when threshold va'
                                 + 'lue reached'
                                   ;
                          leaf maximum-prefix-number {
                            description 'Maximum number of prefix limit.'
                                        ;
                            type uint32 {
                              range 1..4294967295 ;
                            }
                            mandatory true ;
                          }
                          leaf maximum-prefix-threshold {
                            description 'Threshold value(%) at which to generate a warning.'
                                        ;
                            type uint32 {
                              range 1..100 ;
                            }
                            mandatory true ;
                          }
                          container exceed-action {
                            description 'The action that generated when threshold value reached.'
                                        ;
                            choice exceed-action {
                              description 'The action that generated when threshold value reached.'
                                          ;
                              case peer-action {
                                description 'The action that generated when threshold value reached.'
                                            ;
                                leaf action {
                                  description 'The action that generated when threshold value reached.'
                                              ;
                                  type enumeration {
                                    enum down {
                                      value 0 ;
                                      description 'Break down BGP connection after limit is exceeded.'
                                                  ;
                                    }
                                    enum warning-only {
                                      value 1 ;
                                      description 'Only give warning message when limit is exceeded.'
                                                  ;
                                    }
                                    enum drop-routes {
                                      value 2 ;
                                      description 'Drop routes that exceed the maximum-prefix.'
                                                  ;
                                    }
                                  }
                                }
                              }
                              case restart {
                                description 'Restart BGP connection after limit is exceeded.'
                                            ;
                                leaf restart-time {
                                  description 'Restart interval in minutes.'
                                              ;
                                  type uint32 {
                                    range 1..30000 ;
                                  }
                                  units min ;
                                }
                              }
                            }
                          }
                        }
                        leaf routepolicy-in-name {
                          description 'Route policy name applied to the inbound'
                                    + ' routes.'
                                      ;
                          type string {
                            length 1..200 ;
                          }
                        }
                        leaf routepolicy-out-name {
                          description 'Route policy name applied to the outboun'
                                    + 'd routes.'
                                      ;
                          type string {
                            length 1..200 ;
                          }
                        }
                        container withdraw {
                          description 'Withdraw routes when state of track-grou'
                                    + 'p is down.'
                                      ;
                          presence withdraw ;
                          leaf track-group {
                            description 'Track-group name.'
                                        ;
                            type string {
                              length 1..31 ;
                            }
                            mandatory true ;
                          }
                          leaf route-map {
                            description 'Route-map name.'
                                        ;
                            type string {
                              length 1..200 ;
                            }
                          }
                        }
                        container second-withdraw {
                          description 'Withdraw routes when state of the second'
                                    + ' track-group is down.'
                                      ;
                          presence second-withdraw ;
                          leaf track-group {
                            description 'Track-group name.'
                                        ;
                            type string {
                              length 1..31 ;
                            }
                            mandatory true ;
                          }
                          leaf route-map {
                            description 'Route-map name.'
                                        ;
                            type string {
                              length 1..200 ;
                            }
                          }
                        }
                      }
                    }
                  }
                  container neighbor-ipv4 {
                    description 'Specify a IPv4 neighbor.'
                                ;
                    list neighbor {
                      description 'Specify a neighbor.'
                                  ;
                      key ipv4-address ;
                      leaf ipv4-address {
                        description 'Neighbor IPv4 address.'
                                    ;
                        type ncd:ipv4-address ;
                      }
                      leaf activate {
                        description 'Enable the address family for this neighbo'
                                  + 'r.'
                                    ;
                        type enumeration {
                          enum disable {
                            value 0 ;
                          }
                          enum enable {
                            value 1 ;
                          }
                        }
                      }
                      leaf joined-group {
                        description 'Only for read operation. The joined group '
                                  + 'name.'
                                    ;
                        type string {
                          length 1..31 ;
                        }
                      }
                      leaf monitor {
                        description 'Config BMP monitor for the address family '
                                  + 'of this neighbor.'
                                    ;
                        type enumeration {
                          enum disable {
                            value 2 ;
                          }
                          enum enable {
                            value 1 ;
                          }
                          enum inherit-global-config {
                            value 0 ;
                          }
                        }
                      }
                      leaf advertise-maximum-prefix {
                        description 'Maximum number of prefix send to this peer.'
                                    ;
                        type uint32 {
                          range 1..4294967295 ;
                        }
                      }
                      leaf allowas-in {
                        description 'Accept as-path with my AS present in it.'
                                    ;
                        type uint32 {
                          range 1..10 ;
                        }
                      }
                      leaf as-override {
                        description 'Override matching AS-number while sending '
                                  + 'update.'
                                    ;
                        type empty ;
                      }
                      leaf as-path-loopcheck {
                        description 'Check as-path sending BGP routing to EBGP '
                                  + 'neighbor.'
                                    ;
                        type empty ;
                      }
                      leaf default-originate {
                        description 'Originate default route to this neighbor.'
                                    ;
                        type empty ;
                      }
                      leaf default-originate-routemap {
                        description 'Map external entry attributes into routing'
                                  + ' table.'
                                    ;
                        type string {
                          length 1..200 ;
                        }
                      }
                      leaf default-originate-routepolicy {
                        description 'Set external entry attributes into routing'
                                  + ' table.'
                                    ;
                        type string {
                          length 1..200 ;
                        }
                        ncd:revise-date 2020-10-10 ;
                      }
                      leaf maxas-in {
                        description 'Accept as-path not exceeded maxas-in.'
                                    ;
                        type uint32 {
                          range 1..250 ;
                        }
                      }
                      leaf next-hop-self {
                        description 'Disable the next hop calculation for this '
                                  + 'neighbor.'
                                    ;
                        type enumeration {
                          enum enable {
                            value 1 ;
                            description 'Apply next-hop-self for EBGP route.'
                                        ;
                          }
                          enum all {
                            value 2 ;
                            description 'Apply next-hop-self for both EBGP and IBGP route.'
                                        ;
                          }
                        }
                      }
                      leaf originate-interval {
                        status obsolete {
                          ncd:revise-date 2021-01-15 ;
                        }
                        description 'Minimum interval between sending BGP routi'
                                  + 'ng which is locally originated updates.'
                                    ;
                        type uint32 {
                          range 1..65535 ;
                        }
                        units s ;
                        ncd:revise-date 2020-10-10 ;
                      }
                      leaf remove-private-as {
                        description 'EBGP use to remove private AS number.'
                                    ;
                        type enumeration {
                          enum disable {
                            value 0 ;
                          }
                          enum enable {
                            value 1 ;
                          }
                        }
                      }
                      leaf send-community {
                        description 'Send community to this neighbor.'
                                    ;
                        type empty ;
                      }
                      leaf send-large-community {
                        description 'Send Large-community to this neighbor.'
                                    ;
                        type empty ;
                      }
                      leaf route-reflector-client {
                        description 'Set this neighbor as a client peer.'
                                    ;
                        type empty ;
                      }
                      leaf send-label {
                        description 'Send NLRI with MPLS label to this neighbor.'
                                    ;
                        type empty ;
                      }
                      leaf send-med {
                        description 'Send metric attribute to this neighbor.'
                                    ;
                        type empty ;
                      }
                      leaf inherit-igp-metric {
                        description 'Med attribute inherited from IGP metric be'
                                  + 'fore sending updates'
                                    ;
                        type empty ;
                      }
                      leaf soft-reconfig {
                        description 'Neighbor soft reconfiguration.'
                                    ;
                        type enumeration {
                          enum soft-reconfiguration {
                            value 1 ;
                            description Soft-reconfiguration. ;
                          }
                          enum enforce-soft-reconfiguration {
                            value 2 ;
                            description 'Enforce soft-reconfiguration instead of sending route-refresh.'
                                        ;
                          }
                        }
                      }
                      leaf soo {
                        description 'Site-of-Origin extended community.'
                                    ;
                        type union {
                          type ncd:asn-nn ;
                          type ncd:asnd-nn ;
                          type ncd:ipadd-nn ;
                        }
                      }
                      leaf split-update-group {
                        description 'Split neighbor from update group.'
                                    ;
                        type empty ;
                      }
                      leaf weight {
                        description 'Set weight for routes from this neighbor.'
                                    ;
                        type uint32 {
                          range 1..65535 ;
                        }
                      }
                      leaf orf-prefix-filter {
                        description 'Advertise prefixlist ORF capability to thi'
                                  + 's neighbor.'
                                    ;
                        type enumeration {
                          enum receive {
                            value 1 ;
                            description 'Capability to receive the ORF from this neighbor.'
                                        ;
                          }
                          enum send {
                            value 2 ;
                            description 'Capability to send the ORF to this neighbor.'
                                        ;
                          }
                          enum both {
                            value 3 ;
                            description 'Capability to send and receive the ORF.'
                                        ;
                          }
                        }
                      }
                      leaf aigp {
                        description 'Enable AIGP for this neighbor.'
                                    ;
                        type empty ;
                      }
                      leaf announce-sid {
                        description 'Enable Prefix-SID attribute for this neigh'
                                  + 'bor.'
                                    ;
                        type enumeration {
                          enum enable {
                            value 1 ;
                            description 'Enable Prefix-SID attribute for this neighbor.'
                                        ;
                          }
                        }
                      }
                      container advertise-map {
                        description 'Specify route-map for conditional advertis'
                                  + 'ement.'
                                    ;
                        presence 'Specify route-map for conditional advertiseme'
                               + 'nt'
                                 ;
                        leaf advertise-map-name {
                          description 'Advertise route-map name.'
                                      ;
                          type string {
                            length 1..200 ;
                          }
                          mandatory true ;
                        }
                        choice advertise-map {
                          description 'Specify route-map for conditional advert'
                                    + 'isement.'
                                      ;
                          mandatory true ;
                          case exist-map {
                            description 'Advertise prefix only if prefix exists.'
                                        ;
                            leaf exist-map-name {
                              description 'Advertise prefix only if prefix exists.'
                                          ;
                              type string {
                                length 1..200 ;
                              }
                              mandatory true ;
                            }
                          }
                          case nonexist-map {
                            description 'Advertise prefix only if prefix does not exist.'
                                        ;
                            leaf nonexist-map-name {
                              description 'Advertise prefix only if prefix does not exist.'
                                          ;
                              type string {
                                length 1..200 ;
                              }
                              mandatory true ;
                            }
                          }
                        }
                      }
                      container route-filter-group {
                        description 'Specify a neighbor to join a route-filter-'
                                  + 'group.'
                                    ;
                        presence route-filter-group ;
                        leaf filter-group {
                          description 'Route filter group name (1-31 characters'
                                    + ').'
                                      ;
                          type string {
                            length 1..31 ;
                          }
                          mandatory true ;
                        }
                        leaf next-hop-self {
                          description 'Disable the next hop calculation for thi'
                                    + 's neighbor.'
                                      ;
                          type empty ;
                        }
                      }
                      container neighbor-extend {
                        description 'Specify a neighbor.'
                                    ;
                        leaf prefix-list-in-name {
                          description 'Apply prefix list to incoming routes.'
                                      ;
                          type string {
                            length 1..169 ;
                          }
                        }
                        leaf prefix-list-out-name {
                          description 'Apply  prefix list to outbound routes.'
                                      ;
                          type string {
                            length 1..169 ;
                          }
                        }
                        leaf route-map-in-name {
                          description 'Apply route-map to incoming routes.'
                                      ;
                          type string {
                            length 1..200 ;
                          }
                        }
                        leaf route-map-out-name {
                          description 'Apply route-map to outbound routes.'
                                      ;
                          type string {
                            length 1..200 ;
                          }
                        }
                        container maximum-prefix {
                          description 'The action that generated when threshold'
                                    + ' value reached.'
                                      ;
                          presence 'The action that generated when threshold va'
                                 + 'lue reached'
                                   ;
                          leaf maximum-prefix-number {
                            description 'Maximum number of prefix limit.'
                                        ;
                            type uint32 {
                              range 1..4294967295 ;
                            }
                            mandatory true ;
                          }
                          leaf maximum-prefix-threshold {
                            description 'Threshold value(%) at which to generate a warning.'
                                        ;
                            type uint32 {
                              range 1..100 ;
                            }
                            mandatory true ;
                          }
                          container exceed-action {
                            description 'The action that generated when threshold value reached.'
                                        ;
                            choice exceed-action {
                              description 'The action that generated when threshold value reached.'
                                          ;
                              case peer-action {
                                description 'The action that generated when threshold value reached.'
                                            ;
                                leaf action {
                                  description 'The action that generated when threshold value reached.'
                                              ;
                                  type enumeration {
                                    enum down {
                                      value 0 ;
                                      description 'Break down BGP connection after limit is exceeded.'
                                                  ;
                                    }
                                    enum warning-only {
                                      value 1 ;
                                      description 'Only give warning message when limit is exceeded.'
                                                  ;
                                    }
                                    enum drop-routes {
                                      value 2 ;
                                      description 'Drop routes that exceed the maximum-prefix.'
                                                  ;
                                    }
                                  }
                                }
                              }
                              case restart {
                                description 'Restart BGP connection after limit is exceeded.'
                                            ;
                                leaf restart-time {
                                  description 'Restart interval in minutes.'
                                              ;
                                  type uint32 {
                                    range 1..30000 ;
                                  }
                                  units min ;
                                }
                              }
                            }
                          }
                        }
                        leaf routepolicy-in-name {
                          description 'Route policy name applied to the inbound'
                                    + ' routes.'
                                      ;
                          type string {
                            length 1..200 ;
                          }
                        }
                        leaf routepolicy-out-name {
                          description 'Route policy name applied to the outboun'
                                    + 'd routes.'
                                      ;
                          type string {
                            length 1..200 ;
                          }
                        }
                        container withdraw {
                          description 'Withdraw routes when state of track-grou'
                                    + 'p is down.'
                                      ;
                          presence withdraw ;
                          leaf track-group {
                            description 'Track-group name.'
                                        ;
                            type string {
                              length 1..31 ;
                            }
                            mandatory true ;
                          }
                          leaf route-map {
                            description 'Route-map name.'
                                        ;
                            type string {
                              length 1..200 ;
                            }
                          }
                        }
                        container second-withdraw {
                          description 'Withdraw routes when state of the second'
                                    + ' track-group is down.'
                                      ;
                          presence second-withdraw ;
                          leaf track-group {
                            description 'Track-group name.'
                                        ;
                            type string {
                              length 1..31 ;
                            }
                            mandatory true ;
                          }
                          leaf route-map {
                            description 'Route-map name.'
                                        ;
                            type string {
                              length 1..200 ;
                            }
                          }
                        }
                      }
                    }
                  }
                }
                container networks {
                  description 'Specify a network to announce via BGP.'
                              ;
                  presence networks ;
                  list network {
                    description 'Specify a network to announce via BGP.'
                                ;
                    key 'ipv4-address ipv4-mask'
                        ;
                    leaf ipv4-address {
                      description 'Network prefix.'
                                  ;
                      type ncd:ipv4-address ;
                    }
                    leaf ipv4-mask {
                      description 'Network mask.'
                                  ;
                      type ncd:ipv4-mask ;
                    }
                    leaf route-map {
                      description 'Route-map to modify the attributes.'
                                  ;
                      type string {
                        length 1..200 ;
                      }
                    }
                    leaf route-policy {
                      description 'Route-policy to modify the attributes.'
                                  ;
                      type string {
                        length 1..200 ;
                      }
                      ncd:revise-date 2020-10-10 ;
                    }
                  }
                }
                container redistribute-v4-vrf {
                  description 'Redistribute information from another routing pr'
                            + 'otocol.'
                              ;
                  presence redistributes ;
                  container redistribute-vrf {
                    description 'Redistribute information from another routing '
                              + 'protocol.'
                                ;
                    list redistribute {
                      description 'Redistribute information from another routin'
                                + 'g protocol.'
                                  ;
                      key protocol ;
                      leaf protocol {
                        description 'Routing protocol type.'
                                    ;
                        type enumeration {
                          enum connected {
                            value 1 ;
                            description 'Connected routes.'
                                        ;
                          }
                          enum static {
                            value 2 ;
                            description 'Static routes.'
                                        ;
                          }
                          enum rip {
                            value 3 ;
                            description 'Routing information protocol(RIP).'
                                        ;
                          }
                          enum bras-pool {
                            value 24 ;
                            description 'Broadband Remote Access Server pool routes.'
                                        ;
                          }
                          enum ipsec {
                            value 25 ;
                            description 'IPsec routes'
                                        ;
                          }
                          enum hagp {
                            value 26 ;
                            description 'Hybrid access gateway protocol routes.'
                                        ;
                          }
                          enum dyn-leasedline {
                            value 29 ;
                            description 'Dynamic-leased-line routes assigned by AAA.'
                                        ;
                          }
                          enum address {
                            value 9 ;
                            description 'Address routes.'
                                        ;
                          }
                        }
                      }
                      leaf route-map {
                        description 'Apply route-map to redistribute.'
                                    ;
                        type string {
                          length 1..200 ;
                        }
                      }
                      leaf route-policy {
                        description 'Apply route-policy to redistribute.'
                                    ;
                        type string {
                          length 1..200 ;
                        }
                        ncd:revise-date 2020-10-10 ;
                      }
                      container set-metric {
                        description 'Set route metric.'
                                    ;
                        leaf metric {
                          description 'Set route metric.'
                                      ;
                          type uint32 {
                            range 0..4294967295 ;
                          }
                        }
                      }
                    }
                  }
                  container redistribute-isis-vrf {
                    description 'Redistribute information from ISIS protocol.'
                                ;
                    list redistribute-isis {
                      description 'Redistribute information from ISIS protocol.'
                                  ;
                      key 'protocol process-id'
                          ;
                      leaf protocol {
                        description 'Routing protocol type(ISIS-1,ISIS-2 or ISI'
                                  + 'S-1-2).'
                                    ;
                        type enumeration {
                          enum isis-1 {
                            value 4 ;
                            description 'IS-IS level-1 routes only.'
                                        ;
                          }
                          enum isis-2 {
                            value 5 ;
                            description 'IS-IS level-2 routes only.'
                                        ;
                          }
                        }
                      }
                      leaf process-id {
                        description 'ISIS process ID.'
                                    ;
                        type uint32 {
                          range 0..65535 ;
                        }
                      }
                      leaf route-map {
                        description 'Apply route-map to redistribute.'
                                    ;
                        type string {
                          length 1..200 ;
                        }
                      }
                      leaf route-policy {
                        description 'Apply route-policy to redistribute.'
                                    ;
                        type string {
                          length 1..200 ;
                        }
                        ncd:revise-date 2020-10-10 ;
                      }
                      container set-metric {
                        description 'Set route metric.'
                                    ;
                        leaf metric {
                          description 'Set route metric.'
                                      ;
                          type uint32 {
                            range 0..4294967295 ;
                          }
                        }
                      }
                    }
                  }
                  container redistribute-ospf-vrf {
                    description 'Redistribute information from OSPF protocol.'
                                ;
                    list redistribute-ospf {
                      description 'Redistribute information from OSPF protocol.'
                                  ;
                      key 'protocol process-id'
                          ;
                      leaf protocol {
                        description 'Routing protocol type(OSPF-EXT or OSPF-INT'
                                  + ').'
                                    ;
                        type enumeration {
                          enum ospf-ext {
                            value 7 ;
                            description 'Open shortest path first(OSPF) external routes.'
                                        ;
                          }
                          enum ospf-int {
                            value 8 ;
                            description 'Open shortest path first(OSPF) internal routes.'
                                        ;
                          }
                        }
                      }
                      leaf process-id {
                        description 'OSPF process ID.'
                                    ;
                        type uint32 {
                          range 1..65535 ;
                        }
                      }
                      leaf route-map {
                        description 'Apply route-map to redistribute.'
                                    ;
                        type string {
                          length 1..200 ;
                        }
                      }
                      leaf route-policy {
                        description 'Apply route-policy to redistribute.'
                                    ;
                        type string {
                          length 1..200 ;
                        }
                        ncd:revise-date 2020-10-10 ;
                      }
                      container set-metric {
                        description 'Set route metric.'
                                    ;
                        leaf metric {
                          description 'Set route metric.'
                                      ;
                          type uint32 {
                            range 0..4294967295 ;
                          }
                        }
                      }
                    }
                  }
                }
                leaf slow-peer-detection {
                  description 'Set slow peer detection.'
                              ;
                  type enumeration {
                    enum disable {
                      value 0 ;
                      description 'Disable slow peer detection'
                                  ;
                    }
                    enum enable {
                      value 1 ;
                      description 'Enable slow peer detection'
                                  ;
                    }
                  }
                  default disable ;
                  ncd:revise-date 2020-09-08 ;
                }
                leaf slow-peer-detection-threshold {
                  description 'Set threshold time for slow peer.Default value i'
                            + 's 300.'
                              ;
                  type uint32 {
                    range 120..3600 {
                      description 'Threshold time range.'
                                  ;
                    }
                  }
                  units s ;
                  default 300 ;
                  ncd:revise-date 2020-09-08 ;
                }
                leaf slow-peer-detection-recover {
                  description 'Set recover time for slow peer.Default value is '
                            + '300.'
                              ;
                  type uint32 {
                    range 120..3600 {
                      description 'Recover time range.'
                                  ;
                    }
                  }
                  units s ;
                  default 300 ;
                  ncd:revise-date 2020-09-08 ;
                }
                leaf bestpath-external {
                  description 'Routes from external peer or RR client are prefe'
                            + 'rred in bestpath selection.'
                              ;
                  type enumeration {
                    enum inherit {
                      value 0 ;
                      description 'Inherit from address family VPNv4 or L2VPN E'
                                + 'VPN'
                                  ;
                    }
                    enum enable {
                      value 1 ;
                    }
                    enum disable {
                      value 2 ;
                    }
                  }
                  default inherit ;
                  ncd:revise-date 2020-11-23 ;
                }
                leaf bestpath-igp-metric-compare {
                  description 'Compare IGP metric in maximum-paths.'
                              ;
                  type enumeration {
                    enum inherit {
                      value 0 ;
                      description 'Inherit from address family VPNv4 or L2VPN E'
                                + 'VPN'
                                  ;
                    }
                    enum enable {
                      value 1 ;
                    }
                    enum disable {
                      value 2 ;
                    }
                  }
                  default inherit ;
                  ncd:revise-date 2020-11-23 ;
                }
                leaf bestpath-igp-metric-ignore {
                  description 'Ignore IGP metric in bestpath selection.'
                              ;
                  type enumeration {
                    enum inherit {
                      value 0 ;
                      description 'Inherit from address family VPNv4 or L2VPN E'
                                + 'VPN'
                                  ;
                    }
                    enum enable {
                      value 1 ;
                    }
                    enum disable {
                      value 2 ;
                    }
                  }
                  default inherit ;
                  ncd:revise-date 2020-11-23 ;
                }
              }
              container safi-ipv4-multicast {
                description 'Specify parameters for IPv4 multicast VRF.'
                            ;
                presence safi-ipv4-multicast ;
                leaf default-metric {
                  description 'Set metric of BGP routes without MED.'
                              ;
                  type uint32 {
                    range 0..4294967295 ;
                  }
                  default 0 ;
                }
                container neighbors {
                  description 'Specify a neighbor.'
                              ;
                  container neighbor-ipv4 {
                    description 'Specify a IPv4 neighbor.'
                                ;
                    list neighbor {
                      description 'Specify a neighbor.'
                                  ;
                      key ipv4-address ;
                      leaf ipv4-address {
                        description 'Neighbor IPv4 address.'
                                    ;
                        type ncd:ipv4-address-none-zero ;
                      }
                      leaf activate {
                        type enumeration {
                          enum disable {
                            value 0 ;
                          }
                          enum enable {
                            value 1 ;
                          }
                        }
                      }
                      leaf joined-group {
                        description 'Only for read operation. The joined group '
                                  + 'name.'
                                    ;
                        type string {
                          length 1..31 ;
                        }
                      }
                      leaf as-path-loopback {
                        description 'Check as-path sending BGP routing to EBGP '
                                  + 'neighbor.'
                                    ;
                        type empty ;
                      }
                      leaf split-update-group {
                        description 'Split neighbor from update group.'
                                    ;
                        type empty ;
                      }
                    }
                  }
                }
                container network {
                  description 'Specify a network to announce via BGP.'
                              ;
                  presence network ;
                  list network {
                    description 'Specify a network to announce via BGP.'
                                ;
                    key 'ipv4-address ipv4-mask'
                        ;
                    leaf ipv4-address {
                      description 'Network prefix.'
                                  ;
                      type ncd:ipv4-address ;
                    }
                    leaf ipv4-mask {
                      description 'Network mask.'
                                  ;
                      type ncd:ipv4-mask ;
                    }
                    leaf route-map {
                      description 'Route-map to modify the attributes.'
                                  ;
                      type string {
                        length 1..200 ;
                      }
                    }
                    leaf route-policy {
                      description 'Route-policy to modify the attributes.'
                                  ;
                      type string {
                        length 1..200 ;
                      }
                      ncd:revise-date 2020-10-10 ;
                    }
                  }
                }
                container redistribute-v4-vrf {
                  description 'Redistribute information from another routing pr'
                            + 'otocol.'
                              ;
                  presence redistribute ;
                  container redistribute-vrf {
                    description 'Redistribute information from another routing '
                              + 'protocol.'
                                ;
                    list redistribute {
                      description 'Redistribute information from another routin'
                                + 'g protocol.'
                                  ;
                      key protocol ;
                      leaf protocol {
                        description 'Routing protocol type.'
                                    ;
                        type enumeration {
                          enum connected {
                            value 1 ;
                            description 'Connected routes.'
                                        ;
                          }
                          enum static {
                            value 2 ;
                            description 'Static routes.'
                                        ;
                          }
                          enum rip {
                            value 3 ;
                            description 'Routing information protocol(RIP).'
                                        ;
                          }
                          enum bras-pool {
                            value 24 ;
                            description 'Broadband Remote Access Server pool routes.'
                                        ;
                          }
                          enum ipsec {
                            value 25 ;
                            description 'IPsec routes'
                                        ;
                          }
                          enum hagp {
                            value 26 ;
                            description 'Hybrid access gateway protocol routes.'
                                        ;
                          }
                          enum dyn-leasedline {
                            value 29 ;
                            description 'Dynamic-leased-line routes assigned by AAA.'
                                        ;
                          }
                          enum address {
                            value 9 ;
                            description 'Address routes.'
                                        ;
                          }
                        }
                      }
                      leaf route-map {
                        description 'Apply route-map to redistribute.'
                                    ;
                        type string {
                          length 1..200 ;
                        }
                      }
                      leaf route-policy {
                        description 'Apply route-policy to redistribute.'
                                    ;
                        type string {
                          length 1..200 ;
                        }
                        ncd:revise-date 2020-10-10 ;
                      }
                      container set-metric {
                        description 'Set route metric.'
                                    ;
                        leaf metric {
                          description 'Set route metric.'
                                      ;
                          type uint32 {
                            range 0..4294967295 ;
                          }
                        }
                        leaf route-policy {
                          description 'Apply route-policy to redistribute.'
                                      ;
                          type string {
                            length 1..200 ;
                          }
                          ncd:revise-date 2020-10-10 ;
                        }
                      }
                    }
                  }
                  container redistribute-isis-vrf {
                    description 'Redistribute information from ISIS protocol.'
                                ;
                    list redistribute-isis {
                      description 'Redistribute information from ISIS protocol.'
                                  ;
                      key 'protocol process-id'
                          ;
                      leaf protocol {
                        description 'Routing protocol type(ISIS-1,ISIS-2 or ISI'
                                  + 'S-1-2).'
                                    ;
                        type enumeration {
                          enum isis-1 {
                            value 4 ;
                            description 'IS-IS level-1 routes only.'
                                        ;
                          }
                          enum isis-2 {
                            value 5 ;
                            description 'IS-IS level-2 routes only.'
                                        ;
                          }
                        }
                      }
                      leaf process-id {
                        description 'ISIS process ID.'
                                    ;
                        type uint32 {
                          range 0..65535 ;
                        }
                      }
                      leaf route-map {
                        description 'Apply route-map to redistribute.'
                                    ;
                        type string {
                          length 1..200 ;
                        }
                      }
                      leaf route-policy {
                        description 'Apply route-policy to redistribute.'
                                    ;
                        type string {
                          length 1..200 ;
                        }
                        ncd:revise-date 2020-10-10 ;
                      }
                      container set-metric {
                        description 'Set route metric.'
                                    ;
                        leaf metric {
                          description 'Set route metric.'
                                      ;
                          type uint32 {
                            range 0..4294967295 ;
                          }
                        }
                      }
                    }
                  }
                  container redistribute-ospf-vrf {
                    description 'Redistribute information from OSPF protocol.'
                                ;
                    list redistribute-ospf {
                      description 'Redistribute information from OSPF protocol.'
                                  ;
                      key 'protocol process-id'
                          ;
                      leaf protocol {
                        description 'Routing protocol type(OSPF-EXT or OSPF-INT'
                                  + ').'
                                    ;
                        type enumeration {
                          enum ospf-ext {
                            value 7 ;
                            description 'Open shortest path first(OSPF) external routes.'
                                        ;
                          }
                          enum ospf-int {
                            value 8 ;
                            description 'Open shortest path first(OSPF) internal routes.'
                                        ;
                          }
                        }
                      }
                      leaf process-id {
                        description 'OSPF process ID.'
                                    ;
                        type uint32 {
                          range 1..65535 ;
                        }
                      }
                      leaf route-map {
                        description 'Apply route-map to redistribute.'
                                    ;
                        type string {
                          length 1..200 ;
                        }
                      }
                      leaf route-policy {
                        description 'Apply route-policy to redistribute.'
                                    ;
                        type string {
                          length 1..200 ;
                        }
                        ncd:revise-date 2020-10-10 ;
                      }
                      container set-metric {
                        description 'Set route metric.'
                                    ;
                        leaf metric {
                          description 'Set route metric.'
                                      ;
                          type uint32 {
                            range 0..4294967295 ;
                          }
                        }
                        leaf route-policy {
                          status obsolete {
                            ncd:revise-date 2021-01-15 ;
                          }
                          description 'Apply route-policy to redistribute.'
                                      ;
                          type string {
                            length 1..200 ;
                          }
                          ncd:revise-date 2020-10-10 ;
                        }
                      }
                    }
                  }
                }
              }
              container safi-ipv6-unicast {
                description 'Specify parameters for IPv6 unicast VRF.'
                            ;
                presence safi-ipv6-unicast ;
                leaf maximum-paths-ibgp {
                  description 'Set IBGP-multipath.'
                              ;
                  type uint32 {
                    range 1..32 ;
                  }
                  default 1 ;
                }
                leaf maximum-paths-ebgp {
                  description 'Set EBGP-multipath.'
                              ;
                  type uint32 {
                    range 1..32 ;
                  }
                  default 1 ;
                }
                leaf maximum-paths-eibgp {
                  description 'Set EIBGP-multipath. Mutex with maximum-paths-ib'
                            + 'gp and maximum-paths-ebgp.'
                              ;
                  type uint32 {
                    range 1..32 ;
                  }
                  default 1 ;
                }
                leaf default-information-originate {
                  description 'Notify default route.'
                              ;
                  type empty ;
                }
                leaf default-metric {
                  description 'Set metric of BGP routes without MED.'
                              ;
                  type uint32 {
                    range 0..4294967295 ;
                  }
                  default 0 ;
                }
                leaf distance-bgp-external {
                  description 'Distance for routes external to the AS.'
                              ;
                  type uint32 {
                    range 1..255 ;
                  }
                  default 20 ;
                }
                leaf distance-bgp-internal {
                  description 'Distance for routes internal to the AS.'
                              ;
                  type uint32 {
                    range 1..255 ;
                  }
                  default 200 ;
                }
                leaf distance-bgp-local {
                  description 'Distance for BGP local routes.'
                              ;
                  type uint32 {
                    range 1..255 ;
                  }
                  default 254 ;
                }
                leaf distance-route-map {
                  description 'Define distance by route-map.This node has highe'
                            + 'r priority than distance-bgp-internal,distance-b'
                            + 'gp-external and distance-bgp-local.'
                              ;
                  type string {
                    length 1..200 ;
                  }
                  ncd:revise-date 2020-09-08 ;
                }
                leaf distance-route-policy {
                  description 'Define distance by route-policy.This node has hi'
                            + 'gher priority than distance-bgp-internal,distanc'
                            + 'e-bgp-external and distance-bgp-local.'
                              ;
                  type string {
                    length 1..200 ;
                  }
                  ncd:revise-date 2020-10-10 ;
                }
                leaf import-best-path {
                  description 'Maximum number of paths that can be imported int'
                            + 'o the VRF.'
                              ;
                  type uint32 {
                    range 1..32 ;
                  }
                }
                leaf frr-capability {
                  description 'Enable FRR capability.'
                              ;
                  type empty ;
                }
                leaf frr-wtr {
                  description 'Set the WTR time.'
                              ;
                  type int32 {
                    range 1..12 ;
                  }
                  units min ;
                }
                leaf frr-enhanced {
                  description 'If there is no BGP route as a backup route, then'
                            + ' choose the default route for FRR.'
                              ;
                  type empty ;
                }
                leaf table-map {
                  description 'Map external entry attributes into routing table.'
                              ;
                  type string {
                    length 1..200 ;
                  }
                }
                leaf table-policy {
                  description 'Set external entry attributes into routing table.'
                              ;
                  type string {
                    length 1..200 ;
                  }
                }
                container additional-paths {
                  description 'Additional paths in the BGP table.'
                              ;
                  leaf selection-route-map {
                    description 'Selection criteria to pick the additional path'
                              + 's.'
                                ;
                    type string {
                      length 1..200 ;
                    }
                  }
                }
                container route-scan-time {
                  description 'Adjust BGP route scan.'
                              ;
                  presence 'The ability of BGP route scan.'
                           ;
                  leaf interval-wait {
                    description 'The interval of scan waiting. Default value is'
                              + ' 500.'
                                ;
                    type uint32 {
                      range 1..65535 ;
                    }
                    units ms ;
                    mandatory true ;
                  }
                  leaf initial {
                    description 'The initialization time of scan. Default value'
                              + ' is 50.'
                                ;
                    type uint32 {
                      range 1..65535 ;
                    }
                    units ms ;
                    mandatory true ;
                  }
                  leaf max-wait {
                    description 'The max waiting time of scan. Default value is'
                              + ' 5000.'
                                ;
                    type uint32 {
                      range 1..65535 ;
                    }
                    units ms ;
                    mandatory true ;
                  }
                }
                leaf urpf-id-download {
                  if-feature urpf ;
                  description 'Download URPF-ID information to RTM.'
                              ;
                  type empty ;
                }
                container group-to-group {
                  description 'Configure filter group to filter group route ref'
                            + 'lection.'
                              ;
                  presence group-to-group ;
                  leaf reflection {
                    description 'Reflection of routes is allowed.'
                                ;
                    type empty ;
                    mandatory true ;
                  }
                  leaf next-hop-self {
                    description 'Disable the next hop calculation.'
                                ;
                    type empty ;
                  }
                }
                leaf ebgp-interface-sensitive {
                  description 'Enable or disable interface sensitive for EBGP n'
                            + 'eighbor.'
                              ;
                  type enumeration {
                    enum disable {
                      value 0 ;
                    }
                    enum enable {
                      value 1 ;
                    }
                  }
                  default enable ;
                }
                leaf entropy-label {
                  description 'entropy-label enable or disable'
                              ;
                  type enumeration {
                    enum disable {
                      value 0 ;
                    }
                    enum enable {
                      value 1 ;
                    }
                  }
                }
                leaf bgp-bestpath-origin {
                  description 'bgp bestpath origin-from L3VPN neighbor or EVPN '
                            + 'neighbor.'
                              ;
                  type enumeration {
                    enum l3vpn {
                      value 1 ;
                      description 'bgp bestpath origin-from L3VPN neighbor'
                                  ;
                    }
                    enum evpn {
                      value 2 ;
                      description 'bgp bestpath origin-from EVPN neighbor'
                                  ;
                    }
                  }
                }
                leaf link-bandwidth-download {
                  description 'Download link-bandwidth information to RTM.'
                              ;
                  type empty ;
                }
                leaf nexthop-recursive-default-route {
                  description 'Nexthop recursive lookup default-route.'
                              ;
                  type enumeration {
                    enum enable {
                      value 1 ;
                    }
                    enum disable {
                      value 0 ;
                    }
                  }
                  default enable ;
                }
                leaf nexthop-recursive-null1 {
                  description 'Nexthop recursive lookup null1.'
                              ;
                  type enumeration {
                    enum enable {
                      value 1 ;
                    }
                    enum disable {
                      value 0 ;
                    }
                  }
                  default enable ;
                  ncd:revise-date 2020-12-09 ;
                }
                leaf bgp-bestpath-nexthop-priority {
                  description 'Set BGP bestpath nexthop priority.'
                              ;
                  type enumeration {
                    enum ipv4 {
                      value 1 ;
                      description 'BGP bestpath nexthop priority is ipv4'
                                  ;
                    }
                    enum ipv6 {
                      value 2 ;
                      description 'BGP bestpath nexthop priority is ipv6'
                                  ;
                    }
                  }
                  ncd:revise-date 2020-08-29 ;
                }
                leaf download-community {
                  description 'The maximum number of communities for one route.'
                              ;
                  type uint8 {
                    range 1..255 ;
                  }
                  ncd:revise-date 2020-10-10 ;
                }
                leaf bgp-attr-set {
                  description 'Receive or/and send ATTR-SET attribute.'
                              ;
                  type enumeration {
                    enum both {
                      value 1 ;
                      description 'Receive and send ATTR-SET attribute.'
                                  ;
                    }
                    enum receive {
                      value 2 ;
                      description 'Receive ATTR-SET attribute.'
                                  ;
                    }
                    enum send {
                      value 3 ;
                      description 'Send ATTR-SET attribute.'
                                  ;
                    }
                  }
                  ncd:revise-date 2021-04-21 ;
                }
                container rib-only {
                  description 'BGP routes are not delivered to the IP routing t'
                            + 'able.'
                              ;
                  presence 'BGP routes are not delivered to the IP routing table'
                           ;
                  leaf rib-only-set {
                    description 'Enable rib-only.'
                                ;
                    type empty ;
                    mandatory true ;
                  }
                  leaf rib-only-routemap {
                    description 'Routing policy.'
                                ;
                    type string {
                      length 1..200 ;
                    }
                  }
                  leaf rib-only-routepolicy {
                    description 'Routing policy.'
                                ;
                    type string {
                      length 1..200 ;
                    }
                    ncd:revise-date 2020-10-10 ;
                  }
                }
                container damp {
                  description 'Enable BGP route-flap dampening.'
                              ;
                  presence damp ;
                  choice dampening {
                    description 'Enable BGP route-flap dampening.'
                                ;
                    case route-map {
                      description 'Route-map to specify criteria for dampening.'
                                  ;
                      leaf route-map-name {
                        description 'Route-map to specify criteria for dampenin'
                                  + 'g.'
                                    ;
                        type string {
                          length 1..200 ;
                        }
                      }
                      leaf route-policy-name {
                        description 'Route-policy to specify criteria for dampe'
                                  + 'ning.'
                                    ;
                        type string {
                          length 1..200 ;
                        }
                        ncd:revise-date 2020-10-10 ;
                      }
                    }
                    case parameter {
                      description 'Damp parameter.'
                                  ;
                      leaf half-time {
                        description 'Half-life time for the penalty.'
                                    ;
                        type uint32 {
                          range 1..45 ;
                        }
                        units min ;
                        mandatory true ;
                      }
                      leaf reuse {
                        description 'Value to start reusing a route.'
                                    ;
                        type uint32 {
                          range 1..20000 ;
                        }
                        mandatory true ;
                      }
                      leaf suppress {
                        description 'Value to start suppressing a route.'
                                    ;
                        type uint32 {
                          range 1..20000 ;
                        }
                        mandatory true ;
                      }
                      leaf max-suppress-time {
                        description 'Maximum duration to suppress a route.'
                                    ;
                        type uint32 {
                          range 1..255 ;
                        }
                        units min ;
                        mandatory true ;
                      }
                    }
                  }
                }
                container aggregates {
                  description 'Configure BGP aggregate entries.'
                              ;
                  presence aggregates ;
                  list aggregate {
                    description 'Configure BGP aggregate entries.'
                                ;
                    key 'ipv6-address ipv6-mask-len'
                        ;
                    leaf ipv6-address {
                      description 'Aggregate address.'
                                  ;
                      type ncd:ipv6-address ;
                    }
                    leaf ipv6-mask-len {
                      description 'Aggregate mask length.'
                                  ;
                      type uint8 {
                        range 0..128 ;
                      }
                    }
                    leaf as-set {
                      description 'Generate AS set path information.'
                                  ;
                      type empty ;
                    }
                    leaf strict {
                      description 'Strict condition.'
                                  ;
                      type empty ;
                    }
                    leaf summary-only {
                      description 'Filter more specific routes from updates.'
                                  ;
                      type empty ;
                    }
                    container agg-policies {
                      description 'Apply policy to aggregate route.'
                                  ;
                      choice agg-policy {
                        description 'Apply policy to aggregate route.'
                                    ;
                        case route-map {
                          description 'Apply route map to aggregate route.'
                                      ;
                          leaf attr-map {
                            description 'Attribute map name.'
                                        ;
                            type string {
                              length 1..200 ;
                            }
                          }
                          leaf supp-map {
                            description 'Suppress map name.'
                                        ;
                            type string {
                              length 1..200 ;
                            }
                          }
                          leaf orig-map {
                            description 'Origin map name.'
                                        ;
                            type string {
                              length 1..200 ;
                            }
                          }
                        }
                        case route-policy {
                          description 'Apply route-policy to aggregate route.'
                                      ;
                          leaf policy {
                            description 'Route-policy name.'
                                        ;
                            type string {
                              length 1..200 ;
                            }
                          }
                        }
                      }
                    }
                  }
                }
                container track {
                  description 'Event tracking.'
                              ;
                  presence track ;
                  container track-adjust-type-with-interface {
                    description 'Configure adjust-priority of track object with'
                              + ' interface.'
                                ;
                    list track-adjust-with-interface {
                      description 'Configure adjust-priority of track object wi'
                                + 'th interface.'
                                  ;
                      key 'track-name track-interface'
                          ;
                      leaf track-name {
                        description 'Name of track object (1-31 characters).'
                                    ;
                        type string {
                          length 1..31 ;
                        }
                      }
                      leaf track-interface {
                        description 'Source of track object.'
                                    ;
                        type ncd:ifname {
                          length 1..31 ;
                        }
                      }
                      leaf adjust-value {
                        description 'Value of adjust-priority.'
                                    ;
                        type uint32 {
                          range 1..100 ;
                        }
                        mandatory true ;
                      }
                    }
                  }
                  container track-adjust-type-without-interface {
                    description 'Configure adjust-priority of track object with'
                              + 'out interface.'
                                ;
                    list track-adjust-without-interface {
                      description 'Configure adjust-priority of track object wi'
                                + 'thout interface.'
                                  ;
                      max-elements 1 ;
                      key track-name ;
                      leaf track-name {
                        description 'Name of track object (1-31 characters).'
                                    ;
                        type string {
                          length 1..31 ;
                        }
                      }
                      leaf adjust-value {
                        description 'Value of adjust-priority.'
                                    ;
                        type uint32 {
                          range 1..100 ;
                        }
                        mandatory true ;
                      }
                    }
                  }
                }
                container neighbors {
                  description 'Specify a neighbor.'
                              ;
                  container neighbor-group {
                    description 'Specify a neighbor.'
                                ;
                    list neighbor-peergroup {
                      description 'Specify a neighbor.'
                                  ;
                      key neighbor-group ;
                      leaf neighbor-group {
                        description 'Peer group name (1-31 characters).'
                                    ;
                        type string {
                          length 1..31 ;
                        }
                      }
                      leaf activate {
                        description 'Enable the address family for this neighbo'
                                  + 'r.'
                                    ;
                        type enumeration {
                          enum disable {
                            value 0 ;
                          }
                          enum enable {
                            value 1 ;
                          }
                        }
                      }
                      leaf monitor {
                        description 'Config BMP monitor for the address family '
                                  + 'of this neighbor.'
                                    ;
                        type enumeration {
                          enum disable {
                            value 2 ;
                          }
                          enum enable {
                            value 1 ;
                          }
                          enum inherit-global-config {
                            value 0 ;
                          }
                        }
                      }
                      leaf advertise-maximum-prefix {
                        description 'Maximum number of prefix send to this peer.'
                                    ;
                        type uint32 {
                          range 1..4294967295 ;
                        }
                      }
                      leaf allowas-in {
                        description 'Accept as-path with my AS present in it.'
                                    ;
                        type uint32 {
                          range 1..10 ;
                        }
                      }
                      leaf as-override {
                        description 'Override matching AS-number while sending '
                                  + 'update.'
                                    ;
                        type empty ;
                      }
                      leaf as-path-loopcheck {
                        description 'Check as-path sending BGP routing to EBGP '
                                  + 'neighbor.'
                                    ;
                        type empty ;
                      }
                      leaf default-originate {
                        description 'Originate default route to this neighbor.'
                                    ;
                        type empty ;
                      }
                      leaf default-originate-routemap {
                        description 'Map external entry attributes into routing'
                                  + ' table.'
                                    ;
                        type string {
                          length 1..200 ;
                        }
                      }
                      leaf default-originate-routepolicy {
                        description 'Set external entry attributes into routing'
                                  + ' table.'
                                    ;
                        type string {
                          length 1..200 ;
                        }
                        ncd:revise-date 2020-10-10 ;
                      }
                      leaf maxas-in {
                        description 'Accept as-path not exceeded maxas-in.'
                                    ;
                        type uint32 {
                          range 1..250 ;
                        }
                      }
                      leaf next-hop-self {
                        description 'Disable the next hop calculation for this '
                                  + 'neighbor.'
                                    ;
                        type enumeration {
                          enum enable {
                            value 1 ;
                            description 'Apply next-hop-self for EBGP route.'
                                        ;
                          }
                          enum all {
                            value 2 ;
                            description 'Apply next-hop-self for both EBGP and IBGP route.'
                                        ;
                          }
                        }
                      }
                      leaf remove-private-as {
                        description 'EBGP use to remove private AS number.'
                                    ;
                        type enumeration {
                          enum disable {
                            value 0 ;
                          }
                          enum enable {
                            value 1 ;
                          }
                        }
                      }
                      leaf send-community {
                        description 'Send community to this neighbor.'
                                    ;
                        type empty ;
                      }
                      leaf send-large-community {
                        description 'Send Large-community to this neighbor.'
                                    ;
                        type empty ;
                      }
                      leaf route-reflector-client {
                        description 'Set this neighbor as a client peer.'
                                    ;
                        type empty ;
                      }
                      leaf send-med {
                        description 'Send metric attribute to this neighbor.'
                                    ;
                        type empty ;
                      }
                      leaf inherit-igp-metric {
                        description 'Med attribute inherited from IGP metric be'
                                  + 'fore sending updates'
                                    ;
                        type empty ;
                      }
                      leaf soft-reconfig {
                        description 'Neighbor soft reconfiguration.'
                                    ;
                        type enumeration {
                          enum soft-reconfiguration {
                            value 1 ;
                            description Soft-reconfiguration. ;
                          }
                          enum enforce-soft-reconfiguration {
                            value 2 ;
                            description 'Enforce soft-reconfiguration instead of sending route-refresh.'
                                        ;
                          }
                        }
                      }
                      leaf soo {
                        description 'Site-of-Origin extended community.'
                                    ;
                        type union {
                          type ncd:asn-nn ;
                          type ncd:asnd-nn ;
                          type ncd:ipadd-nn ;
                        }
                      }
                      leaf split-update-group {
                        description 'Split neighbor from update group.'
                                    ;
                        type empty ;
                      }
                      leaf weight {
                        description 'Set weight for routes from this neighbor.'
                                    ;
                        type uint32 {
                          range 1..65535 ;
                        }
                      }
                      leaf aigp {
                        description 'Enable AIGP for this neighbor.'
                                    ;
                        type empty ;
                      }
                      leaf send-label {
                        description 'Send NLRI with MPLS label to this neighbor.'
                                    ;
                        type empty ;
                      }
                      leaf announce-sid {
                        description 'Enable Prefix-SID attribute for this neigh'
                                  + 'bor.'
                                    ;
                        type enumeration {
                          enum enable {
                            value 1 ;
                            description 'Enable Prefix-SID attribute for this neighbor.'
                                        ;
                          }
                        }
                      }
                      container route-filter-group {
                        description 'Specify a neighbor to join a route-filter-'
                                  + 'group.'
                                    ;
                        presence route-filter-group ;
                        leaf filter-group {
                          description 'Route filter group name (1-31 characters'
                                    + ').'
                                      ;
                          type string {
                            length 1..31 ;
                          }
                          mandatory true ;
                        }
                        leaf next-hop-self {
                          description 'Disable the next hop calculation for thi'
                                    + 's neighbor.'
                                      ;
                          type empty ;
                        }
                      }
                      container advertise-map {
                        description 'Specify route-map for conditional advertis'
                                  + 'ement.'
                                    ;
                        presence 'Specify route-map for conditional advertiseme'
                               + 'nt'
                                 ;
                        leaf advertise-map-name {
                          description 'Advertise route-map name.'
                                      ;
                          type string {
                            length 1..200 ;
                          }
                          mandatory true ;
                        }
                        choice advertise-map {
                          description 'Specify route-map for conditional advert'
                                    + 'isement.'
                                      ;
                          mandatory true ;
                          case exist-map {
                            description 'Advertise prefix only if prefix exists.'
                                        ;
                            leaf exist-map-name {
                              description 'Advertise prefix only if prefix exists.'
                                          ;
                              type string {
                                length 1..200 ;
                              }
                              mandatory true ;
                            }
                          }
                          case nonexist-map {
                            description 'Advertise prefix only if prefix does not exist.'
                                        ;
                            leaf non-exist-map-name {
                              description 'Advertise prefix only if prefix does not exist.'
                                          ;
                              type string {
                                length 1..200 ;
                              }
                              mandatory true ;
                            }
                          }
                        }
                      }
                      container neighbor-extend {
                        description 'Specify a neighbor.'
                                    ;
                        leaf prefix-list-in-name {
                          description 'Apply prefix list to incoming routes.'
                                      ;
                          type string {
                            length 1..169 ;
                          }
                        }
                        leaf prefix-list-out-name {
                          description 'Apply  prefix list to outbound routes.'
                                      ;
                          type string {
                            length 1..169 ;
                          }
                        }
                        leaf route-map-in-name {
                          description 'Apply route-map to incoming routes.'
                                      ;
                          type string {
                            length 1..200 ;
                          }
                        }
                        leaf route-map-out-name {
                          description 'Apply route-map to outbound routes.'
                                      ;
                          type string {
                            length 1..200 ;
                          }
                        }
                        container maximum-prefix {
                          description 'The action that generated when threshold'
                                    + ' value reached.'
                                      ;
                          presence 'The action that generated when threshold va'
                                 + 'lue reached'
                                   ;
                          leaf maximum-prefix-number {
                            description 'Maximum number of prefix limit.'
                                        ;
                            type uint32 {
                              range 1..4294967295 ;
                            }
                            mandatory true ;
                          }
                          leaf maximum-prefix-threshold {
                            description 'Threshold value(%) at which to generate a warning.'
                                        ;
                            type uint32 {
                              range 1..100 ;
                            }
                            mandatory true ;
                          }
                          container exceed-action {
                            description 'The action that generated when threshold value reached.'
                                        ;
                            choice exceed-action {
                              description 'The action that generated when threshold value reached.'
                                          ;
                              case peer-action {
                                description 'The action that generated when threshold value reached.'
                                            ;
                                leaf action {
                                  description 'The action that generated when threshold value reached.'
                                              ;
                                  type enumeration {
                                    enum down {
                                      value 0 ;
                                      description 'Break down BGP connection after limit is exceeded.'
                                                  ;
                                    }
                                    enum warning-only {
                                      value 1 ;
                                      description 'Only give warning message when limit is exceeded.'
                                                  ;
                                    }
                                    enum drop-routes {
                                      value 2 ;
                                      description 'Drop routes that exceed the maximum-prefix.'
                                                  ;
                                    }
                                  }
                                }
                              }
                              case restart {
                                description 'Restart BGP connection after limit is exceeded.'
                                            ;
                                leaf restart-time {
                                  description 'Restart interval in minutes.'
                                              ;
                                  type uint32 {
                                    range 1..30000 ;
                                  }
                                  units min ;
                                }
                              }
                            }
                          }
                        }
                        leaf routepolicy-in-name {
                          description 'Route policy name applied to the inbound'
                                    + ' routes.'
                                      ;
                          type string {
                            length 1..200 ;
                          }
                        }
                        leaf routepolicy-out-name {
                          description 'Route policy name applied to the outboun'
                                    + 'd routes.'
                                      ;
                          type string {
                            length 1..200 ;
                          }
                        }
                        container withdraw {
                          description 'Withdraw routes when state of track-grou'
                                    + 'p is down.'
                                      ;
                          presence withdraw ;
                          leaf track-group {
                            description 'Track-group name.'
                                        ;
                            type string {
                              length 1..31 ;
                            }
                            mandatory true ;
                          }
                          leaf route-map {
                            description 'Route-map name.'
                                        ;
                            type string {
                              length 1..200 ;
                            }
                          }
                        }
                        container second-withdraw {
                          description 'Withdraw routes when state of the second'
                                    + ' track-group is down.'
                                      ;
                          presence second-withdraw ;
                          leaf track-group {
                            description 'Track-group name.'
                                        ;
                            type string {
                              length 1..31 ;
                            }
                            mandatory true ;
                          }
                          leaf route-map {
                            description 'Route-map name.'
                                        ;
                            type string {
                              length 1..200 ;
                            }
                          }
                        }
                      }
                    }
                  }
                  container neighbor-ipv6 {
                    description 'Specify a IPv6 neighbor.'
                                ;
                    list neighbor {
                      description 'Specify a neighbor.'
                                  ;
                      key ipv6-address ;
                      leaf ipv6-address {
                        description 'Neighbor IPv6 address.'
                                    ;
                        type ncd:ipv6-address ;
                      }
                      leaf activate {
                        description 'Enable the address family for this neighbo'
                                  + 'r.'
                                    ;
                        type enumeration {
                          enum disable {
                            value 0 ;
                          }
                          enum enable {
                            value 1 ;
                          }
                        }
                      }
                      leaf joined-group {
                        description 'Only for read operation. The joined group '
                                  + 'name.'
                                    ;
                        type string {
                          length 1..31 ;
                        }
                      }
                      leaf monitor {
                        description 'Config BMP monitor for the address family '
                                  + 'of this neighbor.'
                                    ;
                        type enumeration {
                          enum disable {
                            value 2 ;
                          }
                          enum enable {
                            value 1 ;
                          }
                          enum inherit-global-config {
                            value 0 ;
                          }
                        }
                      }
                      leaf advertise-maximum-prefix {
                        description 'Maximum number of prefix send to this peer.'
                                    ;
                        type uint32 {
                          range 1..4294967295 ;
                        }
                      }
                      leaf allowas-in {
                        description 'Accept as-path with my AS present in it.'
                                    ;
                        type uint32 {
                          range 1..10 ;
                        }
                      }
                      leaf as-override {
                        description 'Override matching AS-number while sending '
                                  + 'update.'
                                    ;
                        type empty ;
                      }
                      leaf as-path-loopcheck {
                        description 'Check as-path sending BGP routing to EBGP '
                                  + 'neighbor.'
                                    ;
                        type empty ;
                      }
                      leaf default-originate {
                        description 'Originate default route to this neighbor.'
                                    ;
                        type empty ;
                      }
                      leaf default-originate-routemap {
                        description 'Map external entry attributes into routing'
                                  + ' table.'
                                    ;
                        type string {
                          length 1..200 ;
                        }
                      }
                      leaf default-originate-routepolicy {
                        description 'Set external entry attributes into routing'
                                  + ' table.'
                                    ;
                        type string {
                          length 1..200 ;
                        }
                        ncd:revise-date 2020-10-10 ;
                      }
                      leaf maxas-in {
                        description 'Accept as-path not exceeded maxas-in.'
                                    ;
                        type uint32 {
                          range 1..250 ;
                        }
                      }
                      leaf next-hop-self {
                        description 'Disable the next hop calculation for this '
                                  + 'neighbor.'
                                    ;
                        type enumeration {
                          enum enable {
                            value 1 ;
                            description 'Apply next-hop-self for EBGP route.'
                                        ;
                          }
                          enum all {
                            value 2 ;
                            description 'Apply next-hop-self for both EBGP and IBGP route.'
                                        ;
                          }
                        }
                      }
                      leaf remove-private-as {
                        description 'EBGP use to remove private AS number.'
                                    ;
                        type enumeration {
                          enum disable {
                            value 0 ;
                          }
                          enum enable {
                            value 1 ;
                          }
                        }
                      }
                      leaf send-community {
                        description 'Send community to this neighbor.'
                                    ;
                        type empty ;
                      }
                      leaf send-large-community {
                        description 'Send Large-community to this neighbor.'
                                    ;
                        type empty ;
                      }
                      leaf route-reflector-client {
                        description 'Set this neighbor as a client peer.'
                                    ;
                        type empty ;
                      }
                      leaf send-label {
                        description 'Send NLRI with MPLS label to this neighbor.'
                                    ;
                        type empty ;
                      }
                      leaf send-med {
                        description 'Send metric attribute to this neighbor.'
                                    ;
                        type empty ;
                      }
                      leaf inherit-igp-metric {
                        description 'Med attribute inherited from IGP metric be'
                                  + 'fore sending updates.'
                                    ;
                        type empty ;
                      }
                      leaf soft-reconfig {
                        description 'Neighbor soft reconfiguration.'
                                    ;
                        type enumeration {
                          enum soft-reconfiguration {
                            value 1 ;
                            description Soft-reconfiguration. ;
                          }
                          enum enforce-soft-reconfiguration {
                            value 2 ;
                            description 'Enforce soft-reconfiguration instead of sending route-refresh.'
                                        ;
                          }
                        }
                      }
                      leaf soo {
                        description 'Site-of-Origin extended community.'
                                    ;
                        type union {
                          type ncd:asn-nn ;
                          type ncd:asnd-nn ;
                          type ncd:ipadd-nn ;
                        }
                      }
                      leaf split-update-group {
                        description 'Split neighbor from update group.'
                                    ;
                        type empty ;
                      }
                      leaf weight {
                        description 'Set weight for routes from this neighbor.'
                                    ;
                        type uint32 {
                          range 1..65535 ;
                        }
                      }
                      leaf aigp {
                        description 'Enable AIGP for this neighbor.'
                                    ;
                        type empty ;
                      }
                      leaf announce-sid {
                        description 'Enable Prefix-SID attribute for this neigh'
                                  + 'bor.'
                                    ;
                        type enumeration {
                          enum enable {
                            value 1 ;
                            description 'Enable Prefix-SID attribute for this neighbor.'
                                        ;
                          }
                        }
                      }
                      container advertise-map {
                        description 'Specify route-map for conditional advertis'
                                  + 'ement.'
                                    ;
                        presence 'Specify route-map for conditional advertiseme'
                               + 'nt'
                                 ;
                        leaf advertise-map-name {
                          description 'Advertise route-map name.'
                                      ;
                          type string {
                            length 1..200 ;
                          }
                          mandatory true ;
                        }
                        choice advertise-map {
                          description 'Specify route-map for conditional advert'
                                    + 'isement.'
                                      ;
                          mandatory true ;
                          case exist-map {
                            description 'Advertise prefix only if prefix exists.'
                                        ;
                            leaf exist-map-name {
                              description 'Advertise prefix only if prefix exists.'
                                          ;
                              type string {
                                length 1..200 ;
                              }
                              mandatory true ;
                            }
                          }
                          case nonexist-map {
                            description 'Advertise prefix only if prefix does not exist.'
                                        ;
                            leaf nonexist-map-name {
                              description 'Advertise prefix only if prefix does not exist.'
                                          ;
                              type string {
                                length 1..200 ;
                              }
                              mandatory true ;
                            }
                          }
                        }
                      }
                      container route-filter-group {
                        description 'Specify a neighbor to join a route-filter-'
                                  + 'group.'
                                    ;
                        presence route-filter-group ;
                        leaf filter-group {
                          description 'Route filter group name (1-31 characters'
                                    + ').'
                                      ;
                          type string {
                            length 1..31 ;
                          }
                          mandatory true ;
                        }
                        leaf next-hop-self {
                          description 'Disable the next hop calculation for thi'
                                    + 's neighbor.'
                                      ;
                          type empty ;
                        }
                      }
                      container neighbor-extend {
                        description 'Specify a neighbor.'
                                    ;
                        leaf prefix-list-in-name {
                          description 'Apply prefix list to incoming routes.'
                                      ;
                          type string {
                            length 1..169 ;
                          }
                        }
                        leaf prefix-list-out-name {
                          description 'Apply prefix list to outbound routes.'
                                      ;
                          type string {
                            length 1..169 ;
                          }
                        }
                        leaf route-map-in-name {
                          description 'Apply route-map to incoming routes.'
                                      ;
                          type string {
                            length 1..200 ;
                          }
                        }
                        leaf route-map-out-name {
                          description 'Apply route-map to outbound routes.'
                                      ;
                          type string {
                            length 1..200 ;
                          }
                        }
                        container maximum-prefix {
                          description 'The action that generated when threshold'
                                    + ' value reached.'
                                      ;
                          presence 'The action that generated when threshold va'
                                 + 'lue reached'
                                   ;
                          leaf maximum-prefix-number {
                            description 'Maximum number of prefix limit.'
                                        ;
                            type uint32 {
                              range 1..4294967295 ;
                            }
                            mandatory true ;
                          }
                          leaf maximum-prefix-threshold {
                            description 'Threshold value(%) at which to generate a warning.'
                                        ;
                            type uint32 {
                              range 1..100 ;
                            }
                            mandatory true ;
                          }
                          container exceed-action {
                            description 'The action that generated when threshold value reached.'
                                        ;
                            choice exceed-action {
                              description 'The action that generated when threshold value reached.'
                                          ;
                              case peer-action {
                                description 'The action that generated when threshold value reached.'
                                            ;
                                leaf action {
                                  description 'The action that generated when threshold value reached.'
                                              ;
                                  type enumeration {
                                    enum down {
                                      value 0 ;
                                      description 'Break down BGP connection after limit is exceeded.'
                                                  ;
                                    }
                                    enum warning-only {
                                      value 1 ;
                                      description 'Only give warning message when limit is exceeded.'
                                                  ;
                                    }
                                    enum drop-routes {
                                      value 2 ;
                                      description 'Drop routes that exceed the maximum-prefix.'
                                                  ;
                                    }
                                  }
                                }
                              }
                              case restart {
                                description 'Restart BGP connection after limit is exceeded.'
                                            ;
                                leaf restart-time {
                                  description 'Restart interval in minutes.'
                                              ;
                                  type uint32 {
                                    range 1..30000 ;
                                  }
                                  units min ;
                                }
                              }
                            }
                          }
                        }
                        leaf routepolicy-in-name {
                          description 'Route policy name applied to the inbound'
                                    + ' routes.'
                                      ;
                          type string {
                            length 1..200 ;
                          }
                        }
                        leaf routepolicy-out-name {
                          description 'Route policy name applied to the outboun'
                                    + 'd routes.'
                                      ;
                          type string {
                            length 1..200 ;
                          }
                        }
                        container withdraw {
                          description 'Withdraw routes when state of track-grou'
                                    + 'p is down.'
                                      ;
                          presence withdraw ;
                          leaf track-group {
                            description 'Track-group name.'
                                        ;
                            type string {
                              length 1..31 ;
                            }
                            mandatory true ;
                          }
                          leaf route-map {
                            description 'Route-map name.'
                                        ;
                            type string {
                              length 1..200 ;
                            }
                          }
                        }
                        container second-withdraw {
                          description 'Withdraw routes when state of the second'
                                    + ' track-group is down.'
                                      ;
                          presence second-withdraw ;
                          leaf track-group {
                            description 'Track-group name.'
                                        ;
                            type string {
                              length 1..31 ;
                            }
                            mandatory true ;
                          }
                          leaf route-map {
                            description 'Route-map name.'
                                        ;
                            type string {
                              length 1..200 ;
                            }
                          }
                        }
                      }
                    }
                  }
                }
                container networks {
                  description 'Specify a network to announce via BGP.'
                              ;
                  presence networks ;
                  list network {
                    description 'Specify a network to announce via BGP.'
                                ;
                    key 'ipv6-address ipv6-mask-len'
                        ;
                    leaf ipv6-address {
                      description 'Network prefix.'
                                  ;
                      type ncd:ipv6-address ;
                    }
                    leaf ipv6-mask-len {
                      description 'Network mask length.'
                                  ;
                      type uint8 ;
                    }
                    leaf route-map {
                      description 'Route-map to modify the attributes.'
                                  ;
                      type string {
                        length 1..200 ;
                      }
                    }
                    leaf route-policy {
                      description 'Route-policy to modify the attributes.'
                                  ;
                      type string {
                        length 1..200 ;
                      }
                      ncd:revise-date 2020-10-10 ;
                    }
                  }
                }
                container redistribute-v6-vrf {
                  description 'Redistribute information from another routing pr'
                            + 'otocol.'
                              ;
                  presence redistributes ;
                  container redistribute-vrf {
                    description 'Redistribute information from another routing '
                              + 'protocol.'
                                ;
                    list redistribute {
                      description 'Redistribute information from another routin'
                                + 'g protocol.'
                                  ;
                      key protocol ;
                      leaf protocol {
                        description 'Routing protocol type.'
                                    ;
                        type enumeration {
                          enum connected {
                            value 1 ;
                            description 'Connected routes.'
                                        ;
                          }
                          enum static {
                            value 2 ;
                            description 'Static routes.'
                                        ;
                          }
                          enum rip {
                            value 3 ;
                            description 'Routing information protocol(RIP).'
                                        ;
                          }
                          enum bras-pool {
                            value 24 ;
                            description 'Broadband Remote Access Server pool routes.'
                                        ;
                          }
                          enum hagp {
                            value 26 ;
                            description 'Hybrid access gateway protocol routes.'
                                        ;
                          }
                          enum dyn-leasedline {
                            value 29 ;
                            description 'Dynamic-leased-line routes assigned by AAA.'
                                        ;
                          }
                          enum address {
                            value 9 ;
                            description 'Address routes.'
                                        ;
                          }
                          enum nptv6 {
                            value 30 ;
                            description 'IPv6-to-IPv6 Network Prefix Translation routes.'
                                        ;
                          }
                        }
                      }
                      leaf route-map {
                        description 'Apply route-map to redistribute.'
                                    ;
                        type string {
                          length 1..200 ;
                        }
                      }
                      leaf route-policy {
                        description 'Apply route-policy to redistribute.'
                                    ;
                        type string {
                          length 1..200 ;
                        }
                        ncd:revise-date 2020-10-10 ;
                      }
                      container set-metric {
                        description 'Set route metric.'
                                    ;
                        leaf metric {
                          description 'Set route metric.'
                                      ;
                          type uint32 {
                            range 0..4294967295 ;
                          }
                        }
                      }
                    }
                  }
                  container redistribute-isis-vrf {
                    description 'Redistribute information from ISIS protocol.'
                                ;
                    list redistribute-isis {
                      description 'Redistribute information from ISIS protocol.'
                                  ;
                      key 'protocol process-id'
                          ;
                      leaf protocol {
                        description 'Routing protocol type(ISIS-1,ISIS-2 or ISI'
                                  + 'S-1-2).'
                                    ;
                        type enumeration {
                          enum isis-1 {
                            value 4 ;
                            description 'IS-IS level-1 routes only.'
                                        ;
                          }
                          enum isis-2 {
                            value 5 ;
                            description 'IS-IS level-2 routes only.'
                                        ;
                          }
                        }
                      }
                      leaf process-id {
                        description 'ISIS process ID.'
                                    ;
                        type uint32 {
                          range 0..65535 ;
                        }
                      }
                      leaf route-map {
                        description 'Apply route-map to redistribute.'
                                    ;
                        type string {
                          length 1..200 ;
                        }
                      }
                      leaf route-policy {
                        description 'Apply route-policy to redistribute.'
                                    ;
                        type string {
                          length 1..200 ;
                        }
                        ncd:revise-date 2020-10-10 ;
                      }
                      container set-metric {
                        description 'Set route metric.'
                                    ;
                        leaf metric {
                          description 'Set route metric.'
                                      ;
                          type uint32 {
                            range 0..4294967295 ;
                          }
                        }
                      }
                    }
                  }
                  container redistribute-ospf-vrf {
                    description 'Redistribute information from OSPF protocol.'
                                ;
                    list redistribute-ospf {
                      description 'Redistribute information from OSPF protocol.'
                                  ;
                      key 'protocol process-id'
                          ;
                      leaf protocol {
                        description 'Routing protocol type(OSPF-EXT or OSPF-INT'
                                  + ').'
                                    ;
                        type enumeration {
                          enum ospf-ext {
                            value 7 ;
                            description 'Open shortest path first(OSPF) external routes.'
                                        ;
                          }
                          enum ospf-int {
                            value 8 ;
                            description 'Open shortest path first(OSPF) internal routes.'
                                        ;
                          }
                        }
                      }
                      leaf process-id {
                        description 'OSPF process ID.'
                                    ;
                        type uint32 {
                          range 1..65535 ;
                        }
                      }
                      leaf route-map {
                        description 'Apply route-map to redistribute.'
                                    ;
                        type string {
                          length 1..200 ;
                        }
                      }
                      leaf route-policy {
                        description 'Apply route-policy to redistribute.'
                                    ;
                        type string {
                          length 1..200 ;
                        }
                        ncd:revise-date 2020-10-10 ;
                      }
                      container set-metric {
                        description 'Set route metric.'
                                    ;
                        leaf metric {
                          description 'Set route metric.'
                                      ;
                          type uint32 {
                            range 0..4294967295 ;
                          }
                        }
                      }
                    }
                  }
                }
                leaf slow-peer-detection {
                  description 'Set slow peer detection.'
                              ;
                  type enumeration {
                    enum disable {
                      value 0 ;
                      description 'Disable slow peer detection'
                                  ;
                    }
                    enum enable {
                      value 1 ;
                      description 'Enable slow peer detection'
                                  ;
                    }
                  }
                  default disable ;
                  ncd:revise-date 2020-09-08 ;
                }
                leaf slow-peer-detection-threshold {
                  description 'Set threshold time for slow peer.Default value i'
                            + 's 300.'
                              ;
                  type uint32 {
                    range 120..3600 {
                      description 'Threshold time range.'
                                  ;
                    }
                  }
                  units s ;
                  default 300 ;
                  ncd:revise-date 2020-09-08 ;
                }
                leaf slow-peer-detection-recover {
                  description 'Set recover time for slow peer.Default value is '
                            + '300.'
                              ;
                  type uint32 {
                    range 120..3600 {
                      description 'Recover time range.'
                                  ;
                    }
                  }
                  units s ;
                  default 300 ;
                  ncd:revise-date 2020-09-08 ;
                }
                leaf bestpath-external {
                  description 'Routes from external peer or RR client are prefe'
                            + 'rred in bestpath selection.'
                              ;
                  type enumeration {
                    enum inherit {
                      value 0 ;
                      description 'Inherit from address family VPNv6 or L2VPN E'
                                + 'VPN'
                                  ;
                    }
                    enum enable {
                      value 1 ;
                    }
                    enum disable {
                      value 2 ;
                    }
                  }
                  default inherit ;
                  ncd:revise-date 2020-11-23 ;
                }
                leaf bestpath-igp-metric-compare {
                  description 'Compare IGP metric in maximum-paths.'
                              ;
                  type enumeration {
                    enum inherit {
                      value 0 ;
                      description 'Inherit from address family VPNv6 or L2VPN E'
                                + 'VPN'
                                  ;
                    }
                    enum enable {
                      value 1 ;
                    }
                    enum disable {
                      value 2 ;
                    }
                  }
                  default inherit ;
                  ncd:revise-date 2020-11-23 ;
                }
                leaf bestpath-igp-metric-ignore {
                  description 'Ignore IGP metric in bestpath selection.'
                              ;
                  type enumeration {
                    enum inherit {
                      value 0 ;
                      description 'Inherit from address family VPNv6 or L2VPN E'
                                + 'VPN'
                                  ;
                    }
                    enum enable {
                      value 1 ;
                    }
                    enum disable {
                      value 2 ;
                    }
                  }
                  default inherit ;
                  ncd:revise-date 2020-11-23 ;
                }
              }
              container safi-ipv6-multicast {
                description 'Specify parameters for IPv6 multicast VRF.'
                            ;
                presence safi-ipv6-multicast ;
                leaf default-metric {
                  description 'Set metric of BGP routes without MED.'
                              ;
                  type uint32 {
                    range 0..4294967295 ;
                  }
                  default 0 ;
                }
                container neighbors {
                  description 'Specify a neighbor.'
                              ;
                  container neigbhor-ipv6 {
                    description 'Specify a IPv6 neighbor.'
                                ;
                    list neighbor {
                      description 'Specify a neighbor.'
                                  ;
                      key ipv6-address ;
                      leaf ipv6-address {
                        description 'Neighbor IPv6 address.'
                                    ;
                        type ncd:ipv6-address-none-zero ;
                      }
                      leaf activate {
                        description 'Enable the address family for this neighbo'
                                  + 'r.'
                                    ;
                        type enumeration {
                          enum disable {
                            value 0 ;
                          }
                          enum enable {
                            value 1 ;
                          }
                        }
                      }
                      leaf joined-group {
                        description 'Only for read operation. The joined group '
                                  + 'name.'
                                    ;
                        type string {
                          length 1..31 ;
                        }
                      }
                      leaf as-path-loopback {
                        description 'Check as-path sending BGP routing to EBGP '
                                  + 'neighbor.'
                                    ;
                        type empty ;
                      }
                      leaf split-update-group {
                        description 'Split neighbor from update group.'
                                    ;
                        type empty ;
                      }
                    }
                  }
                }
                container network {
                  description 'Specify a network to announce via BGP.'
                              ;
                  list network {
                    description 'Specify a network to announce via BGP.'
                                ;
                    key 'ipv6-address ipv6-mask-len'
                        ;
                    leaf ipv6-address {
                      description 'Network prefix.'
                                  ;
                      type ncd:ipv6-address ;
                    }
                    leaf ipv6-mask-len {
                      description 'Network mask length.'
                                  ;
                      type uint8 ;
                    }
                    leaf route-map {
                      description 'Route-map to modify the attributes.'
                                  ;
                      type string {
                        length 1..200 ;
                      }
                    }
                    leaf route-policy {
                      description 'Route-policy to modify the attributes.'
                                  ;
                      type string {
                        length 1..200 ;
                      }
                      ncd:revise-date 2020-10-10 ;
                    }
                  }
                }
                container redistribute-v6-vrf {
                  description 'Redistribute information from another routing pr'
                            + 'otocol.'
                              ;
                  presence redistribute ;
                  container redistribute-vrf {
                    description 'Redistribute information from another routing '
                              + 'protocol.'
                                ;
                    list redistribute {
                      description 'Redistribute information from another routin'
                                + 'g protocol.'
                                  ;
                      key protocol ;
                      leaf protocol {
                        description 'Routing protocol type.'
                                    ;
                        type enumeration {
                          enum connected {
                            value 1 ;
                            description 'Connected routes.'
                                        ;
                          }
                          enum static {
                            value 2 ;
                            description 'Static routes.'
                                        ;
                          }
                          enum rip {
                            value 3 ;
                            description 'Routing information protocol(RIP).'
                                        ;
                          }
                          enum bras-pool {
                            value 24 ;
                            description 'Broadband Remote Access Server pool routes.'
                                        ;
                          }
                          enum hagp {
                            value 26 ;
                            description 'Hybrid access gateway protocol routes.'
                                        ;
                          }
                          enum dyn-leasedline {
                            value 29 ;
                            description 'Dynamic-leased-line routes assigned by AAA.'
                                        ;
                          }
                          enum address {
                            value 9 ;
                            description 'Address routes.'
                                        ;
                          }
                        }
                      }
                      leaf route-map {
                        description 'Apply route-map to redistribute.'
                                    ;
                        type string {
                          length 1..200 ;
                        }
                      }
                      leaf route-policy {
                        description 'Apply route-policy to redistribute.'
                                    ;
                        type string {
                          length 1..200 ;
                        }
                        ncd:revise-date 2020-10-10 ;
                      }
                      container set-metric {
                        description 'Set route metric.'
                                    ;
                        leaf metric {
                          description 'Set route metric.'
                                      ;
                          type uint32 {
                            range 0..4294967295 ;
                          }
                        }
                      }
                    }
                  }
                  container redistribute-isis-vrf {
                    description 'Redistribute information from ISIS protocol.'
                                ;
                    list redistribute-isis {
                      description 'Redistribute information from ISIS protocol.'
                                  ;
                      key 'protocol process-id'
                          ;
                      leaf protocol {
                        description 'Routing protocol type(ISIS-1,ISIS-2 or ISI'
                                  + 'S-1-2).'
                                    ;
                        type enumeration {
                          enum isis-1 {
                            value 4 ;
                            description 'IS-IS level-1 routes only.'
                                        ;
                          }
                          enum isis-2 {
                            value 5 ;
                            description 'IS-IS level-2 routes only.'
                                        ;
                          }
                        }
                      }
                      leaf process-id {
                        description 'ISIS process ID.'
                                    ;
                        type uint32 {
                          range 0..65535 ;
                        }
                      }
                      leaf route-map {
                        description 'Apply route-map to redistribute.'
                                    ;
                        type string {
                          length 1..200 ;
                        }
                      }
                      leaf route-policy {
                        description 'Apply route-policy to redistribute.'
                                    ;
                        type string {
                          length 1..200 ;
                        }
                        ncd:revise-date 2020-10-10 ;
                      }
                      container set-metric {
                        description 'Set route metric.'
                                    ;
                        leaf metric {
                          description 'Set route metric.'
                                      ;
                          type uint32 {
                            range 0..4294967295 ;
                          }
                        }
                      }
                    }
                  }
                  container redistribute-ospf-vrf {
                    description 'Redistribute information from OSPF protocol.'
                                ;
                    list redistribute-ospf {
                      description 'Redistribute information from OSPF protocol.'
                                  ;
                      key 'protocol process-id'
                          ;
                      leaf protocol {
                        description 'Routing protocol type(OSPF-EXT or OSPF-INT'
                                  + ').'
                                    ;
                        type enumeration {
                          enum ospf-ext {
                            value 7 ;
                            description 'Open shortest path first(OSPF) external routes.'
                                        ;
                          }
                          enum ospf-int {
                            value 8 ;
                            description 'Open shortest path first(OSPF) internal routes.'
                                        ;
                          }
                        }
                      }
                      leaf process-id {
                        description 'OSPF process ID.'
                                    ;
                        type uint32 {
                          range 1..65535 ;
                        }
                      }
                      leaf route-map {
                        description 'Apply route-map to redistribute.'
                                    ;
                        type string {
                          length 1..200 ;
                        }
                      }
                      leaf route-policy {
                        description 'Apply route-policy to redistribute.'
                                    ;
                        type string {
                          length 1..200 ;
                        }
                        ncd:revise-date 2020-10-10 ;
                      }
                      container set-metric {
                        description 'Set route metric.'
                                    ;
                        leaf metric {
                          description 'Set route metric.'
                                      ;
                          type uint32 {
                            range 0..4294967295 ;
                          }
                        }
                      }
                    }
                  }
                }
              }
              container safi-link-state {
                description 'Specify parameters for link state VRF.'
                            ;
                presence safi-link-state ;
                container neighbors {
                  description 'Specify a neighbor.'
                              ;
                  container neighbor-group {
                    description 'Specify a neighbor.'
                                ;
                    list neighbor-peergroup {
                      description 'Specify a neighbor.'
                                  ;
                      key neighbor-group ;
                      leaf neighbor-group {
                        description 'Peer group name (1-31 characters).'
                                    ;
                        type string {
                          length 1..31 ;
                        }
                      }
                      leaf activate {
                        description 'Enable the address family for this neighbo'
                                  + 'r.'
                                    ;
                        type enumeration {
                          enum disable {
                            value 0 ;
                          }
                          enum enable {
                            value 1 ;
                          }
                        }
                      }
                      leaf route-reflector-client {
                        description 'Set this neighbor as a client peer.'
                                    ;
                        type empty ;
                      }
                    }
                  }
                  container neighbor-ipv4 {
                    description 'Specify a IPv4 neighbor.'
                                ;
                    list neighbor {
                      description 'Specify a neighbor.'
                                  ;
                      key ipv4-address ;
                      leaf ipv4-address {
                        description 'Neighbor IPv4 address.'
                                    ;
                        type ncd:ipv4-address ;
                      }
                      leaf activate {
                        description 'Enable the address family for this neighbo'
                                  + 'r.'
                                    ;
                        type enumeration {
                          enum disable {
                            value 0 ;
                          }
                          enum enable {
                            value 1 ;
                          }
                        }
                      }
                      leaf route-reflector-client {
                        description 'Set this neighbor as a client peer.'
                                    ;
                        type empty ;
                      }
                    }
                  }
                  container neighbor-ipv6 {
                    description 'Specify a IPv6 neighbor.'
                                ;
                    list neighbor {
                      description 'Specify a neighbor.'
                                  ;
                      key ipv6-address ;
                      leaf ipv6-address {
                        description 'Neighbor IPv6 address.'
                                    ;
                        type ncd:ipv6-address-none-zero ;
                      }
                      leaf activate {
                        description 'Enable the address family for this neighbo'
                                  + 'r.'
                                    ;
                        type enumeration {
                          enum disable {
                            value 0 ;
                          }
                          enum enable {
                            value 1 ;
                          }
                        }
                      }
                      leaf route-reflector-client {
                        description 'Set this neighbor as a client peer.'
                                    ;
                        type empty ;
                      }
                    }
                  }
                }
                ncd:revise-date 2021-03-01 ;
              }
              container safi-link-state-vpn {
                description 'Specify parameters for link state vpn VRF.'
                            ;
                presence safi-link-state-vpn ;
                container neighbors {
                  description 'Specify a neighbor.'
                              ;
                  container neighbor-group {
                    description 'Specify a neighbor.'
                                ;
                    list neighbor-peergroup {
                      description 'Specify a neighbor.'
                                  ;
                      key neighbor-group ;
                      leaf neighbor-group {
                        description 'Peer group name (1-31 characters).'
                                    ;
                        type string {
                          length 1..31 ;
                        }
                      }
                      leaf activate {
                        description 'Enable the address family for this neighbo'
                                  + 'r.'
                                    ;
                        type enumeration {
                          enum disable {
                            value 0 ;
                          }
                          enum enable {
                            value 1 ;
                          }
                        }
                      }
                      leaf route-reflector-client {
                        description 'Set this neighbor as a client peer.'
                                    ;
                        type empty ;
                      }
                    }
                  }
                  container neighbor-ipv4 {
                    description 'Specify a IPv4 neighbor.'
                                ;
                    list neighbor {
                      description 'Specify a neighbor.'
                                  ;
                      key ipv4-address ;
                      leaf ipv4-address {
                        description 'Neighbor IPv4 address.'
                                    ;
                        type ncd:ipv4-address ;
                      }
                      leaf activate {
                        description 'Enable the address family for this neighbo'
                                  + 'r.'
                                    ;
                        type enumeration {
                          enum disable {
                            value 0 ;
                          }
                          enum enable {
                            value 1 ;
                          }
                        }
                      }
                      leaf route-reflector-client {
                        description 'Set this neighbor as a client peer.'
                                    ;
                        type empty ;
                      }
                    }
                  }
                  container neighbor-ipv6 {
                    description 'Specify a IPv6 neighbor.'
                                ;
                    list neighbor {
                      description 'Specify a neighbor.'
                                  ;
                      key ipv6-address ;
                      leaf ipv6-address {
                        description 'Neighbor IPv6 address.'
                                    ;
                        type ncd:ipv6-address-none-zero ;
                      }
                      leaf activate {
                        description 'Enable the address family for this neighbo'
                                  + 'r.'
                                    ;
                        type enumeration {
                          enum disable {
                            value 0 ;
                          }
                          enum enable {
                            value 1 ;
                          }
                        }
                      }
                      leaf route-reflector-client {
                        description 'Set this neighbor as a client peer.'
                                    ;
                        type empty ;
                      }
                    }
                  }
                }
                ncd:revise-date 2021-03-01 ;
              }
            }
            ncd:revise-date 2020-07-28 ;
          }
        }
      }
      container bgp-load-mode {
        description 'BGP load mode.'
                    ;
        leaf load-mode {
          description 'BGP load mode.'
                      ;
          type enumeration {
            enum as {
              value 1 ;
              description 'Based on as.'
                          ;
            }
            enum peer {
              value 2 ;
              description 'Based on peer.'
                          ;
            }
          }
          default as ;
        }
        ncd:revise-date 2018-01-10 ;
      }
      container error-packet {
        description 'Record error packets.'
                    ;
        leaf record-state {
          description 'The state for recording error packets.'
                      ;
          type enumeration {
            enum enable {
              value 1 ;
              description 'Enable error packets recording.'
                          ;
            }
            enum disable {
              value 0 ;
              description 'Disable error packets recording.'
                          ;
            }
          }
          default enable ;
        }
        leaf record-num {
          description 'The maximum number of error messages recorded.'
                      ;
          type uint32 {
            range 1..200 ;
          }
          default 70 ;
        }
        ncd:revise-date 2018-01-10 ;
      }
      container bgp-remote-prefixsid {
        description 'Config remote prefix-sid delete delay time.'
                    ;
        leaf bgp-remote-prefixsid-delete-delay {
          description 'Config remote prefix-sid delete delay time.'
                      ;
          type uint32 {
            range 1..65535 {
              description 'Delay time(s)'
                          ;
            }
          }
          units s ;
        }
        ncd:revise-date 2021-03-01 ;
      }
      container bgp-as-notation {
        leaf bgp-as-notation-plain {
          description 'As plain notation'
                      ;
          type enumeration {
            enum enable {
              value 1 ;
              description 'Enable as notation plain'
                          ;
            }
            enum disable {
              value 0 ;
              description 'Disable as notation plain'
                          ;
            }
          }
        }
        ncd:revise-date 2018-04-16 ;
      }
    }
  }
  container operation {
    config false ;
    container bgp {
      description 'BGP operation.'
                  ;
      container clear {
        description 'Bgp clear command.'
                    ;
        container dampening {
          description 'Clear route flap dampening information.'
                      ;
          container common {
            description 'Address family command mode except IPv4/IPv6 vrf unica'
                      + 'st/multicast mode .'
                        ;
            container v4-network {
              description 'IPv4 network to clear damping information.'
                          ;
              list network {
                description 'IPv4 route.'
                            ;
                key 'afi v4-address v4-mask'
                    ;
                leaf afi {
                  description 'Address family command mode.'
                              ;
                  type enumeration {
                    enum ipv4-unicast {
                      value 11 ;
                    }
                  }
                }
                leaf v4-address {
                  description 'IPv4 network prefix.'
                              ;
                  type ncd:ipv4-address ;
                }
                leaf v4-mask {
                  description 'IPv4 network mask.'
                              ;
                  type ncd:ipv4-mask ;
                }
                leaf local-as {
                  description 'the Autonomy system number of BGP in local equip'
                            + 'ment.'
                              ;
                  type ncd:asn-dot ;
                  ncd:revise-date 2018-01-10 ;
                }
              }
            }
            container v6-network {
              description 'IPv6 network to clear damping information.'
                          ;
              list network {
                description 'IPv6 route.'
                            ;
                key 'afi v6-address v6-prefixlen'
                    ;
                leaf afi {
                  description 'Address family command mode.'
                              ;
                  type enumeration {
                    enum ipv6-unicast {
                      value 25 ;
                    }
                  }
                }
                leaf v6-address {
                  description 'IPv6 network prefix.'
                              ;
                  type ncd:ipv6-address ;
                }
                leaf v6-prefixlen {
                  description 'IPv6 network prefix length.'
                              ;
                  type uint8 ;
                }
                leaf local-as {
                  description 'the Autonomy system number of BGP in local equip'
                            + 'ment.'
                              ;
                  type ncd:asn-dot ;
                  ncd:revise-date 2018-01-10 ;
                }
              }
            }
            container vpnv4-network {
              description 'VPNv4 network to clear damping information.'
                          ;
              list network {
                description 'VPNv4 route.'
                            ;
                key 'afi rd v4-address v4-mask'
                    ;
                leaf afi {
                  description 'Address family command mode.'
                              ;
                  type enumeration {
                    enum vpnv4-unicast {
                      value 12 ;
                    }
                  }
                }
                leaf rd {
                  description 'VPN Route Distinguisher.'
                              ;
                  type union {
                    type ncd:asn-nn ;
                    type ncd:asnd-nn ;
                    type ncd:ipadd-nn ;
                  }
                }
                leaf v4-address {
                  description 'VPNv4 network prefix.'
                              ;
                  type ncd:ipv4-address ;
                }
                leaf v4-mask {
                  description 'VPNv4 network mask.'
                              ;
                  type ncd:ipv4-mask ;
                }
                leaf local-as {
                  description 'the Autonomy system number of BGP in local equip'
                            + 'ment.'
                              ;
                  type ncd:asn-dot ;
                  ncd:revise-date 2018-01-10 ;
                }
              }
            }
            container vpnv6-network {
              description 'VPNv6 network to clear damping information.'
                          ;
              list network {
                description 'VPNv6 route.'
                            ;
                key 'afi rd v6-address v6-prefixlen'
                    ;
                leaf afi {
                  description 'Address family command mode.'
                              ;
                  type enumeration {
                    enum vpnv6-unicast {
                      value 26 ;
                    }
                  }
                }
                leaf rd {
                  description 'VPN Route Distinguisher.'
                              ;
                  type union {
                    type ncd:asn-nn ;
                    type ncd:asnd-nn ;
                    type ncd:ipadd-nn ;
                  }
                }
                leaf v6-address {
                  description 'VPNv6 network prefix.'
                              ;
                  type ncd:ipv6-address ;
                }
                leaf v6-prefixlen {
                  description 'VPNv6 network prefix length.'
                              ;
                  type uint8 ;
                }
                leaf local-as {
                  description 'the Autonomy system number of BGP in local equip'
                            + 'ment.'
                              ;
                  type ncd:asn-dot ;
                  ncd:revise-date 2018-01-10 ;
                }
              }
            }
            container evpn-network {
              description 'EVPN network to clear damping information.'
                          ;
              list network {
                description 'EVPN route.'
                            ;
                key 'afi rd evpn-network'
                    ;
                leaf afi {
                  description 'Address family command mode.'
                              ;
                  type enumeration {
                    enum l2vpn-evpn {
                      value 90 ;
                    }
                  }
                }
                leaf rd {
                  description 'VPN Route Distinguisher.'
                              ;
                  type union {
                    type ncd:asn-nn ;
                    type ncd:asnd-nn ;
                    type ncd:ipadd-nn ;
                  }
                }
                leaf evpn-network {
                  description 'EVPN network string.'
                              ;
                  type ncd:string-all ;
                }
                leaf local-as {
                  description 'the Autonomy system number of BGP in local equip'
                            + 'ment.'
                              ;
                  type ncd:asn-dot ;
                }
              }
              ncd:revise-date 2019-06-25 ;
            }
            container all {
              description 'Clear all network damping information of the address'
                        + ' family mode.'
                          ;
              list mode {
                description 'Address family command mode.'
                            ;
                key afi ;
                leaf afi {
                  description 'Address family command mode.'
                              ;
                  type enumeration {
                    enum ipv4-unicast {
                      value 11 ;
                    }
                    enum vpnv4-unicast {
                      value 12 ;
                    }
                    enum ipv6-unicast {
                      value 25 ;
                    }
                    enum vpnv6-unicast {
                      value 26 ;
                    }
                    enum l2vpn-evpn {
                      value 90 ;
                    }
                  }
                }
                leaf local-as {
                  description 'the Autonomy system number of BGP in local equip'
                            + 'ment.'
                              ;
                  type ncd:asn-dot ;
                  ncd:revise-date 2018-01-10 ;
                }
              }
            }
          }
          container vrf {
            description 'IPv4/IPv6 vrf unicast address family command mode.'
                        ;
            container v4-network {
              description 'IPv4 network to clear damping information.'
                          ;
              list network {
                description 'IPv4 route.'
                            ;
                key 'afi vrf-name v4-address v4-mask'
                    ;
                leaf afi {
                  description 'Address family command mode.'
                              ;
                  type enumeration {
                    enum ipv4-vrf-unicast {
                      value 11 ;
                    }
                  }
                }
                leaf vrf-name {
                  description 'VPN Routing/Forwarding instance name.'
                              ;
                  type string {
                    length 1..32 ;
                  }
                }
                leaf v4-address {
                  description 'IPv4 network prefix.'
                              ;
                  type ncd:ipv4-address ;
                }
                leaf v4-mask {
                  description 'IPv4 network mask.'
                              ;
                  type ncd:ipv4-mask ;
                }
                leaf local-as {
                  description 'the Autonomy system number of BGP in local equip'
                            + 'ment.'
                              ;
                  type ncd:asn-dot ;
                  ncd:revise-date 2018-01-10 ;
                }
              }
            }
            container v6-network {
              description 'IPv6 network to clear damping information.'
                          ;
              list network {
                description 'IPv6 route.'
                            ;
                key 'afi vrf-name v6-address v6-prefixlen'
                    ;
                leaf afi {
                  description 'Address family command mode.'
                              ;
                  type enumeration {
                    enum ipv6-vrf-unicast {
                      value 25 ;
                    }
                  }
                }
                leaf vrf-name {
                  description 'VPN Routing/Forwarding instance name.'
                              ;
                  type string {
                    length 1..32 ;
                  }
                }
                leaf v6-address {
                  description 'IPv6 network prefix.'
                              ;
                  type ncd:ipv6-address ;
                }
                leaf v6-prefixlen {
                  description 'IPv6 prefix length.'
                              ;
                  type uint8 ;
                }
                leaf local-as {
                  description 'the Autonomy system number of BGP in local equip'
                            + 'ment.'
                              ;
                  type ncd:asn-dot ;
                  ncd:revise-date 2018-01-10 ;
                }
              }
            }
            container all {
              description 'Clear all network damping information of the address'
                        + ' family mode.'
                          ;
              list mode {
                description 'Address family command mode.'
                            ;
                key afi ;
                leaf afi {
                  description 'Address family command mode.'
                              ;
                  type enumeration {
                    enum ipv4-vrf-unicast {
                      value 11 ;
                    }
                    enum ipv6-vrf-unicast {
                      value 25 ;
                    }
                  }
                }
                leaf local-as {
                  description 'the Autonomy system number of BGP in local equip'
                            + 'ment.'
                              ;
                  type ncd:asn-dot ;
                  ncd:revise-date 2018-01-10 ;
                }
              }
            }
          }
        }
        container flap-statistics {
          description 'Clear route flap statistics.'
                      ;
          container common {
            description 'Address family command mode except IPv4/IPv6 vrf unica'
                      + 'st/multicast mode .'
                        ;
            container v4-peer-address {
              description 'Neighbor IPv4 address.'
                          ;
              list peer {
                description 'IPv4 Neighbor.'
                            ;
                key 'afi v4-address'
                    ;
                leaf afi {
                  description 'Address family command mode.'
                              ;
                  type enumeration {
                    enum v4-unicast {
                      value 10 ;
                      description 'IPv4 unicast address family.'
                                  ;
                    }
                    enum ipv6-unicast {
                      value 27 ;
                      description 'IPv6 unicast address family.'
                                  ;
                    }
                    enum vpnv4-unicast {
                      value 13 ;
                      description 'VPNv4 address family.'
                                  ;
                    }
                    enum vpnv6-unicast {
                      value 28 ;
                      description 'VPNv6 address family.'
                                  ;
                    }
                  }
                }
                leaf v4-address {
                  description 'Neighbor IPv4 address.'
                              ;
                  type ncd:ipv4-address ;
                }
                leaf local-as {
                  description 'the Autonomy system number of BGP in local equip'
                            + 'ment.'
                              ;
                  type ncd:asn-dot ;
                  ncd:revise-date 2018-01-10 ;
                }
              }
            }
            container v6-peer-address {
              description 'Neighbor IPv6 address.'
                          ;
              list peer {
                description 'IPv6 Neighbor.'
                            ;
                key 'afi v6-address'
                    ;
                leaf afi {
                  description 'Address family command mode.'
                              ;
                  type enumeration {
                    enum ipv6-unicast {
                      value 27 ;
                      description 'IPv6 unicast address family.'
                                  ;
                    }
                    enum ipv4-unicast {
                      value 10 ;
                      description 'IPv4 unicast address family.'
                                  ;
                    }
                  }
                }
                leaf v6-address {
                  description 'Neighbor IPv6 address.'
                              ;
                  type ncd:ipv6-address ;
                }
                leaf local-as {
                  description 'the Autonomy system number of BGP in local equip'
                            + 'ment.'
                              ;
                  type ncd:asn-dot ;
                  ncd:revise-date 2018-01-10 ;
                }
              }
            }
            container v4-network {
              description 'IPv4 network to clear flap statistics.'
                          ;
              list network {
                description 'IPv4 route.'
                            ;
                key 'afi v4-address v4-mask'
                    ;
                leaf afi {
                  description 'Address family command mode.'
                              ;
                  type enumeration {
                    enum ipv4-unicast {
                      value 10 ;
                      description 'IPv4 unicast address family.'
                                  ;
                    }
                  }
                }
                leaf v4-address {
                  description 'IPv4 network prefix.'
                              ;
                  type ncd:ipv4-address ;
                }
                leaf v4-mask {
                  description 'IPv4 network mask.'
                              ;
                  type ncd:ipv4-mask ;
                }
                leaf local-as {
                  description 'the Autonomy system number of BGP in local equip'
                            + 'ment.'
                              ;
                  type ncd:asn-dot ;
                  ncd:revise-date 2018-01-10 ;
                }
              }
            }
            container v6-network {
              description 'IPv6 network to clear flap statistics.'
                          ;
              list network {
                description 'IPv6 route.'
                            ;
                key 'afi v6-address v6-prefixlen'
                    ;
                leaf afi {
                  description 'Address family command mode.'
                              ;
                  type enumeration {
                    enum ipv6-unicast {
                      value 27 ;
                      description 'IPv6 unicast address family.'
                                  ;
                    }
                  }
                }
                leaf v6-address {
                  description 'IPv6 network prefix.'
                              ;
                  type ncd:ipv6-address ;
                }
                leaf v6-prefixlen {
                  description 'IPv6 prefix length.'
                              ;
                  type uint8 ;
                }
                leaf local-as {
                  description 'the Autonomy system number of BGP in local equip'
                            + 'ment.'
                              ;
                  type ncd:asn-dot ;
                  ncd:revise-date 2018-01-10 ;
                }
              }
            }
            container vpnv4-network {
              description 'VPNv4 network to clear flap statistics.'
                          ;
              list network {
                description 'VPNv4 route.'
                            ;
                key 'afi rd v4-address v4-mask'
                    ;
                leaf afi {
                  description 'Address family command mode.'
                              ;
                  type enumeration {
                    enum vpnv4-unicast {
                      value 13 ;
                      description 'VPNv4 address family.'
                                  ;
                    }
                  }
                }
                leaf rd {
                  description 'VPN Route Distinguisher.'
                              ;
                  type union {
                    type ncd:asn-nn ;
                    type ncd:asnd-nn ;
                    type ncd:ipadd-nn ;
                  }
                }
                leaf v4-address {
                  description 'VPNv4 network prefix.'
                              ;
                  type ncd:ipv4-address ;
                }
                leaf v4-mask {
                  description 'VPNv4 network mask.'
                              ;
                  type ncd:ipv4-mask ;
                }
                leaf local-as {
                  description 'the Autonomy system number of BGP in local equip'
                            + 'ment.'
                              ;
                  type ncd:asn-dot ;
                  ncd:revise-date 2018-01-10 ;
                }
              }
            }
            container vpnv6-network {
              description 'VPNv6 network to clear flap statistics.'
                          ;
              list network {
                description 'VPNv6 route.'
                            ;
                key 'afi rd v6-address v6-prefixlen'
                    ;
                leaf afi {
                  description 'Address family command mode.'
                              ;
                  type enumeration {
                    enum vpnv6-unicast {
                      value 28 ;
                      description 'VPNv6 address family.'
                                  ;
                    }
                  }
                }
                leaf rd {
                  description 'VPN Route Distinguisher.'
                              ;
                  type union {
                    type ncd:asn-nn ;
                    type ncd:asnd-nn ;
                    type ncd:ipadd-nn ;
                  }
                }
                leaf v6-address {
                  description 'VPNv6 network prefix.'
                              ;
                  type ncd:ipv6-address ;
                }
                leaf v6-prefixlen {
                  description 'VPNv6 network prefix length.'
                              ;
                  type uint8 ;
                }
                leaf local-as {
                  description 'the Autonomy system number of BGP in local equip'
                            + 'ment.'
                              ;
                  type ncd:asn-dot ;
                  ncd:revise-date 2018-01-10 ;
                }
              }
            }
            container evpn-network {
              description 'EVPN network to clear damping information.'
                          ;
              list network {
                description 'EVPN route.'
                            ;
                key 'afi rd evpn-network'
                    ;
                leaf afi {
                  description 'Address family command mode.'
                              ;
                  type enumeration {
                    enum l2vpn-evpn {
                      value 91 ;
                    }
                  }
                }
                leaf rd {
                  description 'VPN Route Distinguisher.'
                              ;
                  type union {
                    type ncd:asn-nn ;
                    type ncd:asnd-nn ;
                    type ncd:ipadd-nn ;
                  }
                }
                leaf evpn-network {
                  description 'EVPN network string.'
                              ;
                  type ncd:string-all ;
                }
                leaf local-as {
                  description 'the Autonomy system number of BGP in local equip'
                            + 'ment.'
                              ;
                  type ncd:asn-dot ;
                }
              }
              ncd:revise-date 2019-06-25 ;
            }
            container all {
              description 'Clear all route flap statistics of the address famil'
                        + 'y mode.'
                          ;
              list mode {
                description 'Address family command mode.'
                            ;
                key afi ;
                leaf afi {
                  description 'Address family command mode.'
                              ;
                  type enumeration {
                    enum ipv4-unicast {
                      value 10 ;
                      description 'IPv4 unicast address family.'
                                  ;
                    }
                    enum ipv6-unicast {
                      value 27 ;
                      description 'IPv6 unicast address family.'
                                  ;
                    }
                    enum vpnv4-unicast {
                      value 13 ;
                      description 'VPNv4 address family.'
                                  ;
                    }
                    enum vpnv6-unicast {
                      value 28 ;
                      description 'VPNv6 address family.'
                                  ;
                    }
                    enum l2vpn-evpn {
                      value 91 ;
                      description 'EVPN address family.'
                                  ;
                    }
                  }
                }
                leaf local-as {
                  description 'the Autonomy system number of BGP in local equip'
                            + 'ment.'
                              ;
                  type ncd:asn-dot ;
                  ncd:revise-date 2018-01-10 ;
                }
              }
            }
          }
          container vrf {
            description 'IPv4/IPv6 vrf unicst address family command mode.'
                        ;
            container v4-peer-address {
              description 'Neighbor IPv4 address.'
                          ;
              list peer {
                description 'IPv4 Neighbor.'
                            ;
                key 'afi vrf-name v4-address'
                    ;
                leaf afi {
                  description 'Address family command mode.'
                              ;
                  type enumeration {
                    enum ipv4-vrf {
                      value 10 ;
                      description 'IPv4 vrf unicst address family.'
                                  ;
                    }
                  }
                }
                leaf vrf-name {
                  description 'VPN Routing/Forwarding instance name.'
                              ;
                  type string {
                    length 1..32 ;
                  }
                }
                leaf v4-address {
                  description 'Neighbor IPv4 address.'
                              ;
                  type ncd:ipv4-address ;
                }
                leaf local-as {
                  description 'the Autonomy system number of BGP in local equip'
                            + 'ment.'
                              ;
                  type ncd:asn-dot ;
                  ncd:revise-date 2018-01-10 ;
                }
              }
            }
            container v6-peer-address {
              description 'Neighbor IPv6 address.'
                          ;
              list peer {
                description 'IPv6 Neighbor.'
                            ;
                key 'afi vrf-name v6-address'
                    ;
                leaf afi {
                  description 'Address family command mode.'
                              ;
                  type enumeration {
                    enum ipv6-vrf {
                      value 27 ;
                      description 'IPv6 vrf unicst address family.'
                                  ;
                    }
                  }
                }
                leaf vrf-name {
                  description 'VPN Routing/Forwarding instance name.'
                              ;
                  type string {
                    length 1..32 ;
                  }
                }
                leaf v6-address {
                  description 'Neighbor IPv6 address.'
                              ;
                  type ncd:ipv6-address ;
                }
                leaf local-as {
                  description 'the Autonomy system number of BGP in local equip'
                            + 'ment.'
                              ;
                  type ncd:asn-dot ;
                  ncd:revise-date 2018-01-10 ;
                }
              }
            }
            container v4-network {
              description 'IPv4 network to clear flap statistics.'
                          ;
              list network {
                description 'IPv4 network.'
                            ;
                key 'afi vrf-name v4-address v4-mask'
                    ;
                leaf afi {
                  description 'Address family command mode.'
                              ;
                  type enumeration {
                    enum ipv4-vrf-unicast {
                      value 10 ;
                      description 'IPv4 vrf unicast address family.'
                                  ;
                    }
                  }
                }
                leaf vrf-name {
                  description 'VPN Routing/Forwarding instance name.'
                              ;
                  type string {
                    length 1..32 ;
                  }
                }
                leaf v4-address {
                  description 'IPv4 network prefix.'
                              ;
                  type ncd:ipv4-address ;
                }
                leaf v4-mask {
                  description 'IPv4 network mask.'
                              ;
                  type ncd:ipv4-mask ;
                }
                leaf local-as {
                  description 'the Autonomy system number of BGP in local equip'
                            + 'ment.'
                              ;
                  type ncd:asn-dot ;
                  ncd:revise-date 2018-01-10 ;
                }
              }
            }
            container v6-network {
              description 'IPv6 network to clear flap statistics.'
                          ;
              list network {
                description 'IPv6 route.'
                            ;
                key 'afi vrf-name v6-address v6-prefixlen'
                    ;
                leaf afi {
                  description 'Address family command mode.'
                              ;
                  type enumeration {
                    enum ipv6-vrf-unicast {
                      value 27 ;
                      description 'IPv6 vrf unicst address family.'
                                  ;
                    }
                  }
                }
                leaf vrf-name {
                  description 'VPN Routing/Forwarding instance name.'
                              ;
                  type string {
                    length 1..32 ;
                  }
                }
                leaf v6-address {
                  description 'IPv6 network prefix.'
                              ;
                  type ncd:ipv6-address ;
                }
                leaf v6-prefixlen {
                  description 'IPv6 prefix length.'
                              ;
                  type uint8 ;
                }
                leaf local-as {
                  description 'the Autonomy system number of BGP in local equip'
                            + 'ment.'
                              ;
                  type ncd:asn-dot ;
                  ncd:revise-date 2018-01-10 ;
                }
              }
            }
            container all {
              description 'Clear all route flap statistics of the address famil'
                        + 'y mode.'
                          ;
              list mode {
                description 'Address family command mode.'
                            ;
                key 'afi vrf-name'
                    ;
                leaf afi {
                  description 'Address family command mode.'
                              ;
                  type enumeration {
                    enum ipv4-vrf-unicast {
                      value 10 ;
                      description 'IPv4 vrf unicast address family.'
                                  ;
                    }
                    enum ipv6-vrf-unicast {
                      value 27 ;
                      description 'IPv6 vrf unicast address family.'
                                  ;
                    }
                  }
                }
                leaf vrf-name {
                  description 'VPN Routing/Forwarding instance name.'
                              ;
                  type string {
                    length 1..32 ;
                  }
                }
                leaf local-as {
                  description 'the Autonomy system number of BGP in local equip'
                            + 'ment.'
                              ;
                  type ncd:asn-dot ;
                  ncd:revise-date 2018-01-10 ;
                }
              }
            }
          }
        }
        container in-prefix-list {
          description 'Push out prefix-list ORF and do inbound soft reconfig.'
                      ;
          container common {
            description 'Address family command mode except IPv4/IPv6 vrf unica'
                      + 'st/multicast mode .'
                        ;
            container v4-peer-address {
              description 'IPv4 Neighbor to push out prefix-list ORF and do inb'
                        + 'ound soft reconfig.'
                          ;
              list peer {
                description 'Neighbor IPv4.'
                            ;
                key 'v4-address afi'
                    ;
                leaf afi {
                  description 'Address family command mode.'
                              ;
                  type enumeration {
                    enum ipv4-unicast {
                      value 23 ;
                      description 'IPv4 unicast address family.'
                                  ;
                    }
                    enum vpnv4-unicast {
                      value 24 ;
                      description 'VPNv4 unicast address family.'
                                  ;
                    }
                    enum l2vpn-evpn {
                      value 57 ;
                      description 'L2VPN EVPN address family.'
                                  ;
                    }
                  }
                }
                leaf v4-address {
                  description 'Neighbor IPv4 address.'
                              ;
                  type ncd:ipv4-address ;
                }
                leaf local-as {
                  description 'the Autonomy system number of BGP in local equip'
                            + 'ment.'
                              ;
                  type ncd:asn-dot ;
                  ncd:revise-date 2018-01-10 ;
                }
              }
            }
            container v6-peer-address {
              description 'IPv6 Neighbor to push out prefix-list ORF and do inb'
                        + 'ound soft reconfig.'
                          ;
              list peer {
                description 'Neighbor IPv6.'
                            ;
                key 'afi v6-address'
                    ;
                leaf afi {
                  description 'Address family command mode.'
                              ;
                  type enumeration {
                    enum l2vpn-evpn {
                      value 57 ;
                      description 'L2VPN EVPN address family.'
                                  ;
                    }
                    enum ipv4-unicast {
                      value 23 ;
                      description 'IPv4 unicast address family.'
                                  ;
                    }
                  }
                }
                leaf v6-address {
                  description 'Neighbor IPv6 address.'
                              ;
                  type ncd:ipv6-address ;
                }
                leaf local-as {
                  description 'the Autonomy system number of BGP in local equip'
                            + 'ment.'
                              ;
                  type ncd:asn-dot ;
                  ncd:revise-date 2018-01-10 ;
                }
              }
              ncd:revise-date 2017-11-28 ;
            }
          }
          container vrf {
            description 'IPv4 vrf unicst address family command mode.'
                        ;
            container v4-peer-address {
              description 'IPv4 Neighbor to push out prefix-list ORF and do inb'
                        + 'ound soft reconfig.'
                          ;
              list peer {
                description 'Neighbor IPv4.'
                            ;
                key 'v4-address afi vrf-name'
                    ;
                leaf afi {
                  description 'Address family command mode.'
                              ;
                  type enumeration {
                    enum ipv4-vrf-unicast {
                      value 23 ;
                      description 'IPv4 vrf unicast address family.'
                                  ;
                    }
                  }
                }
                leaf vrf-name {
                  description 'VPN Routing/Forwarding instance name.'
                              ;
                  type string {
                    length 1..32 ;
                  }
                }
                leaf v4-address {
                  description 'Neighbor IPv4 address.'
                              ;
                  type ncd:ipv4-address ;
                }
                leaf local-as {
                  description 'the Autonomy system number of BGP in local equip'
                            + 'ment.'
                              ;
                  type ncd:asn-dot ;
                  ncd:revise-date 2018-01-10 ;
                }
              }
            }
          }
        }
        container soft {
          description 'Soft reconfig inbound and outbound updates.'
                      ;
          container common {
            description 'Address family command mode except IPv4/IPv6 vrf unica'
                      + 'st/multicast mode.'
                        ;
            container v4-peer-address {
              description 'IPv4 Neighbor to do soft reconfiguration.'
                          ;
              list peer {
                description 'IPv4 Neighbor.'
                            ;
                key 'direction v4-address'
                    ;
                leaf direction {
                  description 'Direction of soft reconfiguration.'
                              ;
                  type enumeration {
                    enum ipv4-unicast-both {
                      value 1 ;
                      description 'Soft reconfig inbound and outbound updates i'
                                + 'n IPv4 unicast address family.'
                                  ;
                    }
                    enum ipv4-multicast-both {
                      value 3 ;
                      description 'Soft reconfig inbound and outbound updates i'
                                + 'n IPv4 multicast address family.'
                                  ;
                    }
                    enum vpnv4-unicast-both {
                      value 4 ;
                      description 'Soft reconfig inbound and outbound updates i'
                                + 'n VPNv4 unicast address family.'
                                  ;
                    }
                    enum ipv6-unicast-both {
                      value 5 ;
                      description 'Soft reconfig inbound and outbound updates i'
                                + 'n IPv6 unicast address family.'
                                  ;
                    }
                    enum vpnv6-unicast-both {
                      value 8 ;
                      description 'Soft reconfig inbound and outbound updates i'
                                + 'n VPNv6 unicast address family.'
                                  ;
                    }
                    enum ipv4-mdt-both {
                      value 9 ;
                      description 'Soft reconfig inbound and outbound updates i'
                                + 'n IPv4 mdt address family.'
                                  ;
                    }
                    enum ipv4-mdt-out {
                      value 31 ;
                      description 'Soft reconfig outbound updates in IPv4 mdt a'
                                + 'ddress family.'
                                  ;
                    }
                    enum ipv4-multicast-out {
                      value 32 ;
                      description 'Soft reconfig outbound updates in IPv4 multi'
                                + 'cast address family.'
                                  ;
                    }
                    enum ipv4-unicast-out {
                      value 33 ;
                      description 'Soft reconfig outbound updates in IPv4 unica'
                                + 'st address family.'
                                  ;
                    }
                    enum ipv6-unicast-out {
                      value 36 ;
                      description 'Soft reconfig outbound updates in IPv6 unica'
                                + 'st address family.'
                                  ;
                    }
                    enum vpnv4-unicast-out {
                      value 38 ;
                      description 'Soft reconfig outbound updates in VPNv4 unic'
                                + 'ast address family.'
                                  ;
                    }
                    enum vpnv6-unicast-out {
                      value 39 ;
                      description 'Soft reconfig outbound updates in VPNv6 unic'
                                + 'ast address family.'
                                  ;
                    }
                    enum ipv4-mdt-in {
                      value 40 ;
                      description 'Soft reconfig inbound updates in IPv4 mdt ad'
                                + 'dress family.'
                                  ;
                    }
                    enum ipv4-multicast-in {
                      value 41 ;
                      description 'Soft reconfig inbound updates in IPv4 multic'
                                + 'ast address family.'
                                  ;
                    }
                    enum ipv4-unicast-in {
                      value 42 ;
                      description 'Soft reconfig inbound updates in IPv4 unicas'
                                + 't address family.'
                                  ;
                    }
                    enum ipv6-unicast-in {
                      value 45 ;
                      description 'Soft reconfig inbound updates in IPv6 unicas'
                                + 't address family.'
                                  ;
                    }
                    enum vpnv4-unicast-in {
                      value 47 ;
                      description 'Soft reconfig inbound updates in VPNv4 unica'
                                + 'st address family.'
                                  ;
                    }
                    enum vpnv6-unicast-in {
                      value 48 ;
                      description 'Soft reconfig inbound updates in VPNv6 unica'
                                + 'st address family.'
                                  ;
                    }
                    enum ipv4-flowspec-in {
                      value 51 ;
                      description 'Soft reconfig inbound updates in IPv4 Flowsp'
                                + 'ec address family.'
                                  ;
                    }
                    enum ipv4-flowspec-out {
                      value 52 ;
                      description 'Soft reconfig outbound updates in IPv4 Flows'
                                + 'pec address family.'
                                  ;
                    }
                    enum ipv4-flowspec-both {
                      value 53 ;
                      description 'Soft reconfig inbound and outbound updates i'
                                + 'n IPv4 Flowspec address family.'
                                  ;
                    }
                    enum ipv6-flowspec-in {
                      value 60 ;
                      description 'Soft reconfig inbound updates in IPv6 Flowsp'
                                + 'ec address family.'
                                  ;
                    }
                    enum ipv6-flowspec-out {
                      value 61 ;
                      description 'Soft reconfig outbound updates in IPv6 Flows'
                                + 'pec address family.'
                                  ;
                    }
                    enum ipv6-flowspec-both {
                      value 62 ;
                      description 'Soft reconfig inbound and outbound updates i'
                                + 'n IPv6 Flowspec address family.'
                                  ;
                    }
                    enum vpnv4-flowspec-in {
                      value 54 ;
                      description 'Soft reconfig inbound updates in VPNv4 Flows'
                                + 'pec address family.'
                                  ;
                    }
                    enum vpnv4-flowspec-out {
                      value 55 ;
                      description 'Soft reconfig outbound updates in VPNv4 Flow'
                                + 'spec address family.'
                                  ;
                    }
                    enum vpnv4-flowspec-both {
                      value 56 ;
                      description 'Soft reconfig inbound and outbound updates i'
                                + 'n VPNv4 Flowspec address family.'
                                  ;
                    }
                    enum vpnv6-flowspec-in {
                      value 63 ;
                      description 'Soft reconfig inbound updates in VPNv6 Flows'
                                + 'pec address family.'
                                  ;
                    }
                    enum vpnv6-flowspec-out {
                      value 64 ;
                      description 'Soft reconfig outbound updates in VPNv6 Flow'
                                + 'spec address family.'
                                  ;
                    }
                    enum vpnv6-flowspec-both {
                      value 65 ;
                      description 'Soft reconfig inbound and outbound updates i'
                                + 'n VPNv6 Flowspec address family.'
                                  ;
                    }
                    enum ipv4-rt-in {
                      value 66 ;
                      description 'Soft reconfig inbound updates in IPv4 route-'
                                + 'target address family.'
                                  ;
                    }
                    enum ipv4-rt-out {
                      value 67 ;
                      description 'Soft reconfig outbound updates in IPv4 route'
                                + '-target address family.'
                                  ;
                    }
                    enum ipv4-rt-both {
                      value 68 ;
                      description 'Soft reconfig inbound and outbound updates i'
                                + 'n IPv4 route-target address family.'
                                  ;
                    }
                    enum link-state-in {
                      value 69 ;
                      description 'Soft reconfig inbound updates in link-state '
                                + 'address family.'
                                  ;
                    }
                    enum link-state-out {
                      value 70 ;
                      description 'Soft reconfig outbound updates in link-state'
                                + ' address family.'
                                  ;
                    }
                    enum link-state-both {
                      value 71 ;
                      description 'Soft reconfig inbound and outbound updates i'
                                + 'n link-state address family.'
                                  ;
                    }
                    enum l2vpn-evpn-in {
                      value 72 ;
                      description 'Soft reconfig inbound updates in L2VPN EVPN '
                                + 'address family.'
                                  ;
                    }
                    enum l2vpn-evpn-out {
                      value 73 ;
                      description 'Soft reconfig outbound updates in L2VPN EVPN'
                                + ' address family.'
                                  ;
                    }
                    enum l2vpn-evpn-both {
                      value 74 ;
                      description 'Soft reconfig inbound and outbound updates i'
                                + 'n L2VPN EVPN address family.'
                                  ;
                    }
                    enum l2vpn-vpls-in {
                      value 75 ;
                      description 'Soft reconfig inbound updates in L2VPN VPLS '
                                + 'address family.'
                                  ;
                    }
                    enum l2vpn-vpls-out {
                      value 76 ;
                      description 'Soft reconfig outbound updates in L2VPN VPLS'
                                + ' address family.'
                                  ;
                    }
                    enum l2vpn-vpls-both {
                      value 77 ;
                      description 'Soft reconfig inbound and outbound updates i'
                                + 'n L2VPN VPLS address family.'
                                  ;
                    }
                    enum vpnv4-mcast-in {
                      value 78 ;
                      description 'Soft reconfig inbound updates in VPNV4 MCAST'
                                + ' address family.'
                                  ;
                    }
                    enum vpnv4-mcast-out {
                      value 79 ;
                      description 'Soft reconfig outbound updates in VPNV4 MCAS'
                                + 'T address family.'
                                  ;
                    }
                    enum vpnv4-mcast-both {
                      value 80 ;
                      description 'Soft reconfig inbound and outbound updates i'
                                + 'n VPNV4 MCAST address family.'
                                  ;
                    }
                    enum vpnv4-multi-in {
                      value 81 ;
                      description 'Soft reconfig inbound updates in VPNV4 multi'
                                + 'cast address family.'
                                  ;
                    }
                    enum vpnv4-multi-out {
                      value 82 ;
                      description 'Soft reconfig outbound updates in VPNV4 mult'
                                + 'icast address family.'
                                  ;
                    }
                    enum vpnv4-multi-both {
                      value 83 ;
                      description 'Soft reconfig inbound and outbound updates i'
                                + 'n VPNV4 multicast address family.'
                                  ;
                    }
                    enum vpnv6-mcast-in {
                      value 84 ;
                      description 'Soft reconfig inbound updates in VPNV6 MCAST'
                                + ' address family.'
                                  ;
                    }
                    enum vpnv6-mcast-out {
                      value 85 ;
                      description 'Soft reconfig outbound updates in VPNV6 MCAS'
                                + 'T address family.'
                                  ;
                    }
                    enum vpnv6-mcast-both {
                      value 86 ;
                      description 'Soft reconfig inbound and outbound updates i'
                                + 'n VPNV6 MCAST address family.'
                                  ;
                    }
                    enum vpnv6-multi-in {
                      value 87 ;
                      description 'Soft reconfig inbound updates in VPNV6 multi'
                                + 'cast address family.'
                                  ;
                    }
                    enum vpnv6-multi-out {
                      value 88 ;
                      description 'Soft reconfig outbound updates in VPNV6 mult'
                                + 'icast address family.'
                                  ;
                    }
                    enum vpnv6-multi-both {
                      value 89 ;
                      description 'Soft reconfig inbound and outbound updates i'
                                + 'n VPNV6 multicast address family.'
                                  ;
                    }
                    enum ipv4-sr-policy-in {
                      value 92 ;
                      description 'Soft reconfig inbound updates in IPv4 SR pol'
                                + 'icy address family.'
                                  ;
                    }
                    enum ipv4-sr-policy-out {
                      value 93 ;
                      description 'Soft reconfig outbound updates in IPv4 SR po'
                                + 'licy address family.'
                                  ;
                    }
                    enum ipv4-sr-policy-both {
                      value 94 ;
                      description 'Soft reconfig inbound and outbound updates i'
                                + 'n IPv4 SR policy address family.'
                                  ;
                    }
                    enum ipv6-sr-policy-in {
                      value 95 ;
                      description 'Soft reconfig inbound updates in IPv6 SR pol'
                                + 'icy address family.'
                                  ;
                    }
                    enum ipv6-sr-policy-out {
                      value 96 ;
                      description 'Soft reconfig outbound updates in IPv6 SR po'
                                + 'licy address family.'
                                  ;
                    }
                    enum ipv6-sr-policy-both {
                      value 97 ;
                      description 'Soft reconfig inbound and outbound updates i'
                                + 'n IPv6 SR policy address family.'
                                  ;
                    }
                    enum link-state-vpn-in {
                      value 100 ;
                      description 'Soft reconfig inbound updates in link-state '
                                + 'vpn address family.'
                                  ;
                    }
                    enum link-state-vpn-out {
                      value 101 ;
                      description 'Soft reconfig outbound updates in link-state'
                                + ' vpn address family.'
                                  ;
                    }
                    enum link-state-vpn-both {
                      value 102 ;
                      description 'Soft reconfig inbound and outbound updates i'
                                + 'n link-state vpn address family.'
                                  ;
                    }
                  }
                }
                leaf v4-address {
                  description 'Neighbor IPv4 address.'
                              ;
                  type ncd:ipv4-address ;
                }
                leaf local-as {
                  description 'the Autonomy system number of BGP in local equip'
                            + 'ment.'
                              ;
                  type ncd:asn-dot ;
                  ncd:revise-date 2018-01-10 ;
                }
              }
            }
            container v6-peer-address {
              description 'IPv6 Neighbor to do soft reconfiguration.'
                          ;
              list peer {
                description 'IPv6 Neighbor.'
                            ;
                key 'direction v6-address'
                    ;
                leaf direction {
                  description 'Direction of soft reconfiguration.'
                              ;
                  type enumeration {
                    enum ipv6-unicast-both {
                      value 5 ;
                      description 'Soft reconfig inbound and outbound updates i'
                                + 'n IPv6 unicast address family.'
                                  ;
                    }
                    enum ipv6-multicast-both {
                      value 7 ;
                      description 'Soft reconfig inbound and outbound updates i'
                                + 'n IPv6 multicast address family.'
                                  ;
                    }
                    enum vpnv6-unicast-both {
                      value 8 ;
                      description 'Soft reconfig inbound and outbound updates i'
                                + 'n VPNv6 unicast address family.'
                                  ;
                    }
                    enum ipv6-multicast-out {
                      value 35 ;
                      description 'Soft reconfig outbound updates in IPv6 multi'
                                + 'cast address family.'
                                  ;
                    }
                    enum ipv6-unicast-out {
                      value 36 ;
                      description 'Soft reconfig outbound updates in IPv6 unica'
                                + 'st address family.'
                                  ;
                    }
                    enum vpnv6-unicast-out {
                      value 39 ;
                      description 'Soft reconfig outbound updates in VPNv6 unic'
                                + 'ast address family.'
                                  ;
                    }
                    enum ipv6-multicast-in {
                      value 44 ;
                      description 'Soft reconfig inbound updates in IPv6 multic'
                                + 'ast address family.'
                                  ;
                    }
                    enum ipv6-unicast-in {
                      value 45 ;
                      description 'Soft reconfig inbound updates in IPv6 unicas'
                                + 't address family.'
                                  ;
                    }
                    enum vpnv6-unicast-in {
                      value 48 ;
                      description 'Soft reconfig inbound updates in VPNv6 unica'
                                + 'st address family.'
                                  ;
                    }
                    enum vpnv4-unicast-in {
                      value 47 ;
                      description 'Soft reconfig inbound updates in VPNv4 unica'
                                + 'st address family.'
                                  ;
                    }
                    enum vpnv4-unicast-out {
                      value 38 ;
                      description 'Soft reconfig outbound updates in VPNv4 unic'
                                + 'ast address family.'
                                  ;
                    }
                    enum vpnv4-unicast-both {
                      value 4 ;
                      description 'Soft reconfig inbound and outbound updates i'
                                + 'n VPNv4 unicast address family.'
                                  ;
                    }
                    enum vpnv6-flowspec-in {
                      value 63 ;
                      description 'Soft reconfig inbound updates in VPNv6 Flows'
                                + 'pec address family.'
                                  ;
                    }
                    enum vpnv6-flowspec-out {
                      value 64 ;
                      description 'Soft reconfig outbound updates in VPNv6 Flow'
                                + 'spec address family.'
                                  ;
                    }
                    enum vpnv6-flowspec-both {
                      value 65 ;
                      description 'Soft reconfig inbound and outbound updates i'
                                + 'n VPNv6 Flowspec address family.'
                                  ;
                    }
                    enum ipv6-flowspec-in {
                      value 60 ;
                      description 'Soft reconfig inbound updates in IPv6 Flowsp'
                                + 'ec address family.'
                                  ;
                    }
                    enum ipv6-flowspec-out {
                      value 61 ;
                      description 'Soft reconfig outbound updates in IPv6 Flows'
                                + 'pec address family.'
                                  ;
                    }
                    enum ipv6-flowspec-both {
                      value 62 ;
                      description 'Soft reconfig inbound and outbound updates i'
                                + 'n IPv6 Flowspec address family.'
                                  ;
                    }
                    enum link-state-in {
                      value 69 ;
                      description 'Soft reconfig inbound updates in link-state '
                                + 'address family.'
                                  ;
                    }
                    enum link-state-out {
                      value 70 ;
                      description 'Soft reconfig outbound updates in link-state'
                                + ' address family.'
                                  ;
                    }
                    enum link-state-both {
                      value 71 ;
                      description 'Soft reconfig inbound and outbound updates i'
                                + 'n link-state address family.'
                                  ;
                    }
                    enum l2vpn-evpn-in {
                      value 72 ;
                      description 'Soft reconfig inbound updates in L2VPN EVPN '
                                + 'address family.'
                                  ;
                    }
                    enum l2vpn-evpn-out {
                      value 73 ;
                      description 'Soft reconfig outbound updates in L2VPN EVPN'
                                + ' address family.'
                                  ;
                    }
                    enum l2vpn-evpn-both {
                      value 74 ;
                      description 'Soft reconfig inbound and outbound updates i'
                                + 'n L2VPN EVPN address family.'
                                  ;
                    }
                    enum l2vpn-vpls-in {
                      value 75 ;
                      description 'Soft reconfig inbound updates in L2VPN VPLS '
                                + 'address family.'
                                  ;
                    }
                    enum l2vpn-vpls-out {
                      value 76 ;
                      description 'Soft reconfig outbound updates in L2VPN VPLS'
                                + ' address family.'
                                  ;
                    }
                    enum l2vpn-vpls-both {
                      value 77 ;
                      description 'Soft reconfig inbound and outbound updates i'
                                + 'n L2VPN VPLS address family.'
                                  ;
                    }
                    enum ipv4-sr-policy-in {
                      value 92 ;
                      description 'Soft reconfig inbound updates in IPv4 SR pol'
                                + 'icy address family.'
                                  ;
                    }
                    enum ipv4-sr-policy-out {
                      value 93 ;
                      description 'Soft reconfig outbound updates in IPv4 SR po'
                                + 'licy address family.'
                                  ;
                    }
                    enum ipv4-sr-policy-both {
                      value 94 ;
                      description 'Soft reconfig inbound and outbound updates i'
                                + 'n IPv4 SR policy address family.'
                                  ;
                    }
                    enum ipv6-sr-policy-in {
                      value 95 ;
                      description 'Soft reconfig inbound updates in IPv6 SR pol'
                                + 'icy address family.'
                                  ;
                    }
                    enum ipv6-sr-policy-out {
                      value 96 ;
                      description 'Soft reconfig outbound updates in IPv6 SR po'
                                + 'licy address family.'
                                  ;
                    }
                    enum ipv6-sr-policy-both {
                      value 97 ;
                      description 'Soft reconfig inbound and outbound updates i'
                                + 'n IPv6 SR policy address family.'
                                  ;
                    }
                    enum link-state-vpn-in {
                      value 100 ;
                      description 'Soft reconfig inbound updates in link-state '
                                + 'vpn address family.'
                                  ;
                    }
                    enum link-state-vpn-out {
                      value 101 ;
                      description 'Soft reconfig outbound updates in link-state'
                                + ' vpn address family.'
                                  ;
                    }
                    enum link-state-vpn-both {
                      value 102 ;
                      description 'Soft reconfig inbound and outbound updates i'
                                + 'n link-state vpn address family.'
                                  ;
                    }
                    enum ipv4-rt-in {
                      value 66 ;
                      description 'Soft reconfig inbound updates in IPv4 route-'
                                + 'target address family.'
                                  ;
                    }
                    enum ipv4-rt-out {
                      value 67 ;
                      description 'Soft reconfig outbound updates in IPv4 route'
                                + '-target address family.'
                                  ;
                    }
                    enum ipv4-rt-both {
                      value 68 ;
                      description 'Soft reconfig inbound and outbound updates i'
                                + 'n IPv4 route-target address family.'
                                  ;
                    }
                    enum ipv4-unicast-both {
                      value 1 ;
                      description 'Soft reconfig inbound and outbound updates i'
                                + 'n IPv4 unicast address family.'
                                  ;
                    }
                    enum ipv4-unicast-in {
                      value 42 ;
                      description 'Soft reconfig inbound updates in IPv4 unicas'
                                + 't address family.'
                                  ;
                    }
                    enum ipv4-unicast-out {
                      value 33 ;
                      description 'Soft reconfig outbound updates in IPv4 unica'
                                + 'st address family.'
                                  ;
                    }
                  }
                }
                leaf v6-address {
                  description 'Neighbor IPv6 address.'
                              ;
                  type ncd:ipv6-address ;
                }
                leaf local-as {
                  description 'the Autonomy system number of BGP in local equip'
                            + 'ment.'
                              ;
                  type ncd:asn-dot ;
                  ncd:revise-date 2018-01-10 ;
                }
              }
            }
            container peer-groups {
              description 'Peer group to do soft reconfiguration.'
                          ;
              list peer-group {
                description 'Peer group.'
                            ;
                key 'peer-group-name direction'
                    ;
                leaf direction {
                  description 'Direction of soft reconfiguration.'
                              ;
                  type enumeration {
                    enum ipv4-unicast-both {
                      value 1 ;
                      description 'Soft reconfig inbound and outbound updates i'
                                + 'n IPv4 unicast address family.'
                                  ;
                    }
                    enum ipv4-multicast-both {
                      value 3 ;
                      description 'Soft reconfig inbound and outbound updates i'
                                + 'n IPv4 multicast address family.'
                                  ;
                    }
                    enum vpnv4-unicast-both {
                      value 4 ;
                      description 'Soft reconfig inbound and outbound updates i'
                                + 'n VPNv4 unicast address family.'
                                  ;
                    }
                    enum ipv6-unicast-both {
                      value 5 ;
                      description 'Soft reconfig inbound and outbound updates i'
                                + 'n IPv6 unicast address family.'
                                  ;
                    }
                    enum ipv6-multicast-both {
                      value 7 ;
                      description 'Soft reconfig inbound and outbound updates i'
                                + 'n IPv6 multicast address family.'
                                  ;
                    }
                    enum vpnv6-unicast-both {
                      value 8 ;
                      description 'Soft reconfig inbound and outbound updates i'
                                + 'n VPNv6 unicast address family.'
                                  ;
                    }
                    enum ipv4-mdt-both {
                      value 9 ;
                      description 'Soft reconfig inbound and outbound updates i'
                                + 'n IPv4 mdt address family.'
                                  ;
                    }
                    enum ipv4-mdt-out {
                      value 31 ;
                      description 'Soft reconfig outbound updates in IPv4 mdt a'
                                + 'ddress family.'
                                  ;
                    }
                    enum ipv4-multicast-out {
                      value 32 ;
                      description 'Soft reconfig outbound updates in IPv4 multi'
                                + 'cast address family.'
                                  ;
                    }
                    enum ipv4-unicast-out {
                      value 33 ;
                      description 'Soft reconfig outbound updates in IPv4 unica'
                                + 'st address family.'
                                  ;
                    }
                    enum ipv6-multicast-out {
                      value 35 ;
                      description 'Soft reconfig outbound updates in IPv6 multi'
                                + 'cast address family.'
                                  ;
                    }
                    enum ipv6-unicast-out {
                      value 36 ;
                      description 'Soft reconfig outbound updates in IPv6 unica'
                                + 'st address family.'
                                  ;
                    }
                    enum vpnv4-unicast-out {
                      value 38 ;
                      description 'Soft reconfig outbound updates in VPNv4 unic'
                                + 'ast address family.'
                                  ;
                    }
                    enum vpnv6-unicast-out {
                      value 39 ;
                      description 'Soft reconfig outbound updates in VPNv6 unic'
                                + 'ast address family.'
                                  ;
                    }
                    enum ipv4-mdt-in {
                      value 40 ;
                      description 'Soft reconfig inbound updates in IPv4 mdt ad'
                                + 'dress family.'
                                  ;
                    }
                    enum ipv4-multicast-in {
                      value 41 ;
                      description 'Soft reconfig inbound updates in IPv4 multic'
                                + 'ast address family.'
                                  ;
                    }
                    enum ipv4-unicast-in {
                      value 42 ;
                      description 'Soft reconfig inbound updates in IPv4 unicas'
                                + 't address family.'
                                  ;
                    }
                    enum ipv6-multicast-in {
                      value 44 ;
                      description 'Soft reconfig inbound updates in IPv6 multic'
                                + 'ast address family.'
                                  ;
                    }
                    enum ipv6-unicast-in {
                      value 45 ;
                      description 'Soft reconfig inbound updates in IPv6 unicas'
                                + 't address family.'
                                  ;
                    }
                    enum vpnv4-unicast-in {
                      value 47 ;
                      description 'Soft reconfig inbound updates in VPNv4 unica'
                                + 'st address family.'
                                  ;
                    }
                    enum vpnv6-unicast-in {
                      value 48 ;
                      description 'Soft reconfig inbound updates in VPNv6 unica'
                                + 'st address family.'
                                  ;
                    }
                    enum ipv4-flowspec-in {
                      value 51 ;
                      description 'Soft reconfig inbound updates in IPv4 Flowsp'
                                + 'ec address family.'
                                  ;
                    }
                    enum ipv4-flowspec-out {
                      value 52 ;
                      description 'Soft reconfig outbound updates in IPv4 Flows'
                                + 'pec address family.'
                                  ;
                    }
                    enum ipv4-flowspec-both {
                      value 53 ;
                      description 'Soft reconfig inbound and outbound updates i'
                                + 'n IPv4 Flowspec address family.'
                                  ;
                    }
                    enum ipv6-flowspec-in {
                      value 60 ;
                      description 'Soft reconfig inbound updates in IPv6 Flowsp'
                                + 'ec address family.'
                                  ;
                    }
                    enum ipv6-flowspec-out {
                      value 61 ;
                      description 'Soft reconfig outbound updates in IPv6 Flows'
                                + 'pec address family.'
                                  ;
                    }
                    enum ipv6-flowspec-both {
                      value 62 ;
                      description 'Soft reconfig inbound and outbound updates i'
                                + 'n IPv6 Flowspec address family.'
                                  ;
                    }
                    enum vpnv4-flowspec-in {
                      value 54 ;
                      description 'Soft reconfig inbound updates in VPNv4 Flows'
                                + 'pec address family.'
                                  ;
                    }
                    enum vpnv4-flowspec-out {
                      value 55 ;
                      description 'Soft reconfig outbound updates in VPNv4 Flow'
                                + 'spec address family.'
                                  ;
                    }
                    enum vpnv4-flowspec-both {
                      value 56 ;
                      description 'Soft reconfig inbound and outbound updates i'
                                + 'n VPNv4 Flowspec address family.'
                                  ;
                    }
                    enum vpnv6-flowspec-in {
                      value 63 ;
                      description 'Soft reconfig inbound updates in VPNv6 Flows'
                                + 'pec address family.'
                                  ;
                    }
                    enum vpnv6-flowspec-out {
                      value 64 ;
                      description 'Soft reconfig outbound updates in VPNv6 Flow'
                                + 'spec address family.'
                                  ;
                    }
                    enum vpnv6-flowspec-both {
                      value 65 ;
                      description 'Soft reconfig inbound and outbound updates i'
                                + 'n VPNv6 Flowspec address family.'
                                  ;
                    }
                    enum ipv4-rt-in {
                      value 66 ;
                      description 'Soft reconfig inbound updates in IPv4 route-'
                                + 'target address family.'
                                  ;
                    }
                    enum ipv4-rt-out {
                      value 67 ;
                      description 'Soft reconfig outbound updates in IPv4 route'
                                + '-target address family.'
                                  ;
                    }
                    enum ipv4-rt-both {
                      value 68 ;
                      description 'Soft reconfig inbound and outbound updates i'
                                + 'n IPv4 route-target address family.'
                                  ;
                    }
                    enum link-state-in {
                      value 69 ;
                      description 'Soft reconfig inbound updates in link-state '
                                + 'address family.'
                                  ;
                    }
                    enum link-state-out {
                      value 70 ;
                      description 'Soft reconfig outbound updates in link-state'
                                + ' address family.'
                                  ;
                    }
                    enum link-state-both {
                      value 71 ;
                      description 'Soft reconfig inbound and outbound updates i'
                                + 'n link-state address family.'
                                  ;
                    }
                    enum l2vpn-evpn-in {
                      value 72 ;
                      description 'Soft reconfig inbound updates in L2VPN EVPN '
                                + 'address family.'
                                  ;
                    }
                    enum l2vpn-evpn-out {
                      value 73 ;
                      description 'Soft reconfig outbound updates in L2VPN EVPN'
                                + ' address family.'
                                  ;
                    }
                    enum l2vpn-evpn-both {
                      value 74 ;
                      description 'Soft reconfig inbound and outbound updates i'
                                + 'n L2VPN EVPN address family.'
                                  ;
                    }
                    enum l2vpn-vpls-in {
                      value 75 ;
                      description 'Soft reconfig inbound updates in L2VPN VPLS '
                                + 'address family.'
                                  ;
                    }
                    enum l2vpn-vpls-out {
                      value 76 ;
                      description 'Soft reconfig outbound updates in L2VPN VPLS'
                                + ' address family.'
                                  ;
                    }
                    enum l2vpn-vpls-both {
                      value 77 ;
                      description 'Soft reconfig inbound and outbound updates i'
                                + 'n L2VPN VPLS address family.'
                                  ;
                    }
                    enum ipv4-sr-policy-in {
                      value 92 ;
                      description 'Soft reconfig inbound updates in IPv4 SR pol'
                                + 'icy address family.'
                                  ;
                    }
                    enum ipv4-sr-policy-out {
                      value 93 ;
                      description 'Soft reconfig outbound updates in IPv4 SR po'
                                + 'licy address family.'
                                  ;
                    }
                    enum ipv4-sr-policy-both {
                      value 94 ;
                      description 'Soft reconfig inbound and outbound updates i'
                                + 'n IPv4 SR policy address family.'
                                  ;
                    }
                    enum ipv6-sr-policy-in {
                      value 95 ;
                      description 'Soft reconfig inbound updates in IPv6 SR pol'
                                + 'icy address family.'
                                  ;
                    }
                    enum ipv6-sr-policy-out {
                      value 96 ;
                      description 'Soft reconfig outbound updates in IPv6 SR po'
                                + 'licy address family.'
                                  ;
                    }
                    enum ipv6-sr-policy-both {
                      value 97 ;
                      description 'Soft reconfig inbound and outbound updates i'
                                + 'n IPv6 SR policy address family.'
                                  ;
                    }
                    enum link-state-vpn-in {
                      value 100 ;
                      description 'Soft reconfig inbound updates in link-state '
                                + 'vpn address family.'
                                  ;
                    }
                    enum link-state-vpn-out {
                      value 101 ;
                      description 'Soft reconfig outbound updates in link-state'
                                + ' vpn address family.'
                                  ;
                    }
                    enum link-state-vpn-both {
                      value 102 ;
                      description 'Soft reconfig inbound and outbound updates i'
                                + 'n link-state vpn address family.'
                                  ;
                    }
                  }
                }
                leaf peer-group-name {
                  description 'Peer group name.'
                              ;
                  type string {
                    length 1..31 ;
                  }
                }
                leaf local-as {
                  description 'the Autonomy system number of BGP in local equip'
                            + 'ment.'
                              ;
                  type ncd:asn-dot ;
                  ncd:revise-date 2018-01-10 ;
                }
              }
            }
            container all {
              description 'All neighbors of the address family mode to do soft '
                        + 'reconfiguration.'
                          ;
              list mode {
                description 'Address family command mode.'
                            ;
                key direction ;
                leaf direction {
                  description 'Direction of soft reconfiguration.'
                              ;
                  type enumeration {
                    enum ipv4-unicast-both {
                      value 1 ;
                      description 'Soft reconfig inbound and outbound updates i'
                                + 'n IPv4 unicast address family.'
                                  ;
                    }
                    enum ipv4-multicast-both {
                      value 3 ;
                      description 'Soft reconfig inbound and outbound updates i'
                                + 'n IPv4 multicast address family.'
                                  ;
                    }
                    enum vpnv4-unicast-both {
                      value 4 ;
                      description 'Soft reconfig inbound and outbound updates i'
                                + 'n VPNv4 unicast address family.'
                                  ;
                    }
                    enum ipv6-unicast-both {
                      value 5 ;
                      description 'Soft reconfig inbound and outbound updates i'
                                + 'n IPv6 unicast address family.'
                                  ;
                    }
                    enum ipv6-multicast-both {
                      value 7 ;
                      description 'Soft reconfig inbound and outbound updates i'
                                + 'n IPv6 multicast address family.'
                                  ;
                    }
                    enum vpnv6-unicast-both {
                      value 8 ;
                      description 'Soft reconfig inbound and outbound updates i'
                                + 'n VPNv6 unicast address family.'
                                  ;
                    }
                    enum ipv4-mdt-both {
                      value 9 ;
                      description 'Soft reconfig inbound and outbound updates i'
                                + 'n IPv4 mdt address family.'
                                  ;
                    }
                    enum ipv4-mdt-out {
                      value 31 ;
                      description 'Soft reconfig outbound updates in IPv4 mdt a'
                                + 'ddress family.'
                                  ;
                    }
                    enum ipv4-multicast-out {
                      value 32 ;
                      description 'Soft reconfig outbound updates in IPv4 multi'
                                + 'cast address family.'
                                  ;
                    }
                    enum ipv4-unicast-out {
                      value 33 ;
                      description 'Soft reconfig outbound updates in IPv4 unica'
                                + 'st address family.'
                                  ;
                    }
                    enum ipv6-multicast-out {
                      value 35 ;
                      description 'Soft reconfig outbound updates in IPv6 multi'
                                + 'cast address family.'
                                  ;
                    }
                    enum ipv6-unicast-out {
                      value 36 ;
                      description 'Soft reconfig outbound updates in IPv6 unica'
                                + 'st address family.'
                                  ;
                    }
                    enum vpnv4-unicast-out {
                      value 38 ;
                      description 'Soft reconfig outbound updates in VPNv4 unic'
                                + 'ast address family.'
                                  ;
                    }
                    enum vpnv6-unicast-out {
                      value 39 ;
                      description 'Soft reconfig outbound updates in VPNv6 unic'
                                + 'ast address family.'
                                  ;
                    }
                    enum ipv4-mdt-in {
                      value 40 ;
                      description 'Soft reconfig inbound updates in IPv4 mdt ad'
                                + 'dress family.'
                                  ;
                    }
                    enum ipv4-multicast-in {
                      value 41 ;
                      description 'Soft reconfig inbound updates in IPv4 multic'
                                + 'ast address family.'
                                  ;
                    }
                    enum ipv4-unicast-in {
                      value 42 ;
                      description 'Soft reconfig inbound updates in IPv4 unicas'
                                + 't address family.'
                                  ;
                    }
                    enum ipv6-multicast-in {
                      value 44 ;
                      description 'Soft reconfig inbound updates in IPv6 multic'
                                + 'ast address family.'
                                  ;
                    }
                    enum ipv6-unicast-in {
                      value 45 ;
                      description 'Soft reconfig inbound updates in IPv6 unicas'
                                + 't address family.'
                                  ;
                    }
                    enum vpnv4-unicast-in {
                      value 47 ;
                      description 'Soft reconfig inbound updates in VPNv4 unica'
                                + 'st address family.'
                                  ;
                    }
                    enum vpnv6-unicast-in {
                      value 48 ;
                      description 'Soft reconfig inbound updates in VPNv6 unica'
                                + 'st address family.'
                                  ;
                    }
                    enum ipv4-flowspec-in {
                      value 51 ;
                      description 'Soft reconfig inbound updates in IPv4 Flowsp'
                                + 'ec address family.'
                                  ;
                    }
                    enum ipv4-flowspec-out {
                      value 52 ;
                      description 'Soft reconfig outbound updates in IPv4 Flows'
                                + 'pec address family.'
                                  ;
                    }
                    enum ipv4-flowspec-both {
                      value 53 ;
                      description 'Soft reconfig inbound and outbound updates i'
                                + 'n IPv4 Flowspec address family.'
                                  ;
                    }
                    enum vpnv4-flowspec-in {
                      value 54 ;
                      description 'Soft reconfig inbound updates in VPNv4 Flows'
                                + 'pec address family.'
                                  ;
                    }
                    enum vpnv4-flowspec-out {
                      value 55 ;
                      description 'Soft reconfig outbound updates in VPNv4 Flow'
                                + 'spec address family.'
                                  ;
                    }
                    enum vpnv4-flowspec-both {
                      value 56 ;
                      description 'Soft reconfig inbound and outbound updates i'
                                + 'n VPNv4 Flowspec address family.'
                                  ;
                    }
                    enum ipv4-rt-in {
                      value 66 ;
                      description 'Soft reconfig inbound updates in IPv4 route-'
                                + 'target address family.'
                                  ;
                    }
                    enum ipv4-rt-out {
                      value 67 ;
                      description 'Soft reconfig outbound updates in IPv4 route'
                                + '-target address family.'
                                  ;
                    }
                    enum ipv4-rt-both {
                      value 68 ;
                      description 'Soft reconfig inbound and outbound updates i'
                                + 'n IPv4 route-target address family.'
                                  ;
                    }
                    enum vpnv6-flowspec-in {
                      value 63 ;
                      description 'Soft reconfig inbound updates in VPNv6 Flows'
                                + 'pec address family.'
                                  ;
                    }
                    enum vpnv6-flowspec-out {
                      value 64 ;
                      description 'Soft reconfig outbound updates in VPNv6 Flow'
                                + 'spec address family.'
                                  ;
                    }
                    enum vpnv6-flowspec-both {
                      value 65 ;
                      description 'Soft reconfig inbound and outbound updates i'
                                + 'n VPNv6 Flowspec address family.'
                                  ;
                    }
                    enum ipv6-flowspec-in {
                      value 60 ;
                      description 'Soft reconfig inbound updates in IPv6 Flowsp'
                                + 'ec address family.'
                                  ;
                    }
                    enum ipv6-flowspec-out {
                      value 61 ;
                      description 'Soft reconfig outbound updates in IPv6 Flows'
                                + 'pec address family.'
                                  ;
                    }
                    enum ipv6-flowspec-both {
                      value 62 ;
                      description 'Soft reconfig inbound and outbound updates i'
                                + 'n IPv6 Flowspec address family.'
                                  ;
                    }
                    enum link-state-in {
                      value 69 ;
                      description 'Soft reconfig inbound updates in link-state '
                                + 'address family.'
                                  ;
                    }
                    enum link-state-out {
                      value 70 ;
                      description 'Soft reconfig outbound updates in link-state'
                                + ' address family.'
                                  ;
                    }
                    enum link-state-both {
                      value 71 ;
                      description 'Soft reconfig inbound and outbound updates i'
                                + 'n link-state address family.'
                                  ;
                    }
                    enum l2vpn-evpn-in {
                      value 72 ;
                      description 'Soft reconfig inbound updates in L2VPN EVPN '
                                + 'address family.'
                                  ;
                    }
                    enum l2vpn-evpn-out {
                      value 73 ;
                      description 'Soft reconfig outbound updates in L2VPN EVPN'
                                + ' address family.'
                                  ;
                    }
                    enum l2vpn-evpn-both {
                      value 74 ;
                      description 'Soft reconfig inbound and outbound updates i'
                                + 'n L2VPN EVPN address family.'
                                  ;
                    }
                    enum l2vpn-vpls-in {
                      value 75 ;
                      description 'Soft reconfig inbound updates in L2VPN VPLS '
                                + 'address family.'
                                  ;
                    }
                    enum l2vpn-vpls-out {
                      value 76 ;
                      description 'Soft reconfig outbound updates in L2VPN VPLS'
                                + ' address family.'
                                  ;
                    }
                    enum l2vpn-vpls-both {
                      value 77 ;
                      description 'Soft reconfig inbound and outbound updates i'
                                + 'n L2VPN VPLS address family.'
                                  ;
                    }
                    enum vpnv4-mcast-in {
                      value 78 ;
                      description 'Soft reconfig inbound updates in VPNV4 MCAST'
                                + ' address family.'
                                  ;
                    }
                    enum vpnv4-mcast-out {
                      value 79 ;
                      description 'Soft reconfig outbound updates in VPNV4 MCAS'
                                + 'T address family.'
                                  ;
                    }
                    enum vpnv4-mcast-both {
                      value 80 ;
                      description 'Soft reconfig inbound and outbound updates i'
                                + 'n VPNV4 MCAST address family.'
                                  ;
                    }
                    enum vpnv4-multi-in {
                      value 81 ;
                      description 'Soft reconfig inbound updates in VPNV4 multi'
                                + 'cast address family.'
                                  ;
                    }
                    enum vpnv4-multi-out {
                      value 82 ;
                      description 'Soft reconfig outbound updates in VPNV4 mult'
                                + 'icast address family.'
                                  ;
                    }
                    enum vpnv4-multi-both {
                      value 83 ;
                      description 'Soft reconfig inbound and outbound updates i'
                                + 'n VPNV4 multicast address family.'
                                  ;
                    }
                    enum vpnv6-mcast-in {
                      value 84 ;
                      description 'Soft reconfig inbound updates in VPNV6 MCAST'
                                + ' address family.'
                                  ;
                    }
                    enum vpnv6-mcast-out {
                      value 85 ;
                      description 'Soft reconfig outbound updates in VPNV6 MCAS'
                                + 'T address family.'
                                  ;
                    }
                    enum vpnv6-mcast-both {
                      value 86 ;
                      description 'Soft reconfig inbound and outbound updates i'
                                + 'n VPNV6 MCAST address family.'
                                  ;
                    }
                    enum vpnv6-multi-in {
                      value 87 ;
                      description 'Soft reconfig inbound updates in VPNV6 multi'
                                + 'cast address family.'
                                  ;
                    }
                    enum vpnv6-multi-out {
                      value 88 ;
                      description 'Soft reconfig outbound updates in VPNV6 mult'
                                + 'icast address family.'
                                  ;
                    }
                    enum vpnv6-multi-both {
                      value 89 ;
                      description 'Soft reconfig inbound and outbound updates i'
                                + 'n VPNV6 multicast address family.'
                                  ;
                    }
                    enum ipv4-sr-policy-in {
                      value 92 ;
                      description 'Soft reconfig inbound updates in IPv4 SR pol'
                                + 'icy address family.'
                                  ;
                    }
                    enum ipv4-sr-policy-out {
                      value 93 ;
                      description 'Soft reconfig outbound updates in IPv4 SR po'
                                + 'licy address family.'
                                  ;
                    }
                    enum ipv4-sr-policy-both {
                      value 94 ;
                      description 'Soft reconfig inbound and outbound updates i'
                                + 'n IPv4 SR policy address family.'
                                  ;
                    }
                    enum ipv6-sr-policy-in {
                      value 95 ;
                      description 'Soft reconfig inbound updates in IPv6 SR pol'
                                + 'icy address family.'
                                  ;
                    }
                    enum ipv6-sr-policy-out {
                      value 96 ;
                      description 'Soft reconfig outbound updates in IPv6 SR po'
                                + 'licy address family.'
                                  ;
                    }
                    enum ipv6-sr-policy-both {
                      value 97 ;
                      description 'Soft reconfig inbound and outbound updates i'
                                + 'n IPv6 SR policy address family.'
                                  ;
                    }
                    enum link-state-vpn-in {
                      value 100 ;
                      description 'Soft reconfig inbound updates in link-state '
                                + 'vpn address family.'
                                  ;
                    }
                    enum link-state-vpn-out {
                      value 101 ;
                      description 'Soft reconfig outbound updates in link-state'
                                + ' vpn address family.'
                                  ;
                    }
                    enum link-state-vpn-both {
                      value 102 ;
                      description 'Soft reconfig inbound and outbound updates i'
                                + 'n link-state vpn address family.'
                                  ;
                    }
                  }
                }
                leaf local-as {
                  description 'the Autonomy system number of BGP in local equip'
                            + 'ment.'
                              ;
                  type ncd:asn-dot ;
                  ncd:revise-date 2018-01-10 ;
                }
              }
            }
          }
          container vrf {
            description 'IPv4/IPv6 vrf unicst address family command mode.'
                        ;
            container v4-peer-address {
              description 'IPv4 Neighbor to do soft reconfiguration.'
                          ;
              list peer {
                description 'IPv4 neighbor.'
                            ;
                key 'direction v4-address vrf-name'
                    ;
                leaf direction {
                  description 'Direction of soft reconfiguration.'
                              ;
                  type enumeration {
                    enum ipv4-vrf-both {
                      value 2 ;
                      description 'Soft reconfig inbound and outbound updates i'
                                + 'n IPv4 vrf address family.'
                                  ;
                    }
                    enum ipv4-vrf-out {
                      value 34 ;
                      description 'Soft reconfig outbound updates in IPv4 vrf a'
                                + 'ddress family.'
                                  ;
                    }
                    enum ipv4-vrf-in {
                      value 43 ;
                      description 'Soft reconfig inbound updates in IPv4 vrf ad'
                                + 'dress family.'
                                  ;
                    }
                  }
                }
                leaf vrf-name {
                  description 'VPN Routing/Forwarding instance name.'
                              ;
                  type string {
                    length 1..32 ;
                  }
                }
                leaf v4-address {
                  description 'Neighbor IPv4 address.'
                              ;
                  type ncd:ipv4-address ;
                }
                leaf local-as {
                  description 'the Autonomy system number of BGP in local equip'
                            + 'ment.'
                              ;
                  type ncd:asn-dot ;
                  ncd:revise-date 2018-01-10 ;
                }
              }
            }
            container v6-peer-address {
              description 'IPv6 Neighbor to do soft reconfiguration.'
                          ;
              list peer {
                description 'IPv6 neighbor.'
                            ;
                key 'direction v6-address vrf-name'
                    ;
                leaf direction {
                  description 'Direction of soft reconfiguration.'
                              ;
                  type enumeration {
                    enum ipv6-vrf-both {
                      value 6 ;
                      description 'Soft reconfig inbound and outbound updates i'
                                + 'n IPv6 vrf address family.'
                                  ;
                    }
                    enum ipv6-vrf-out {
                      value 37 ;
                      description 'Soft reconfig outbound updates in IPv6 vrf a'
                                + 'ddress family.'
                                  ;
                    }
                    enum ipv6-vrf-in {
                      value 46 ;
                      description 'Soft reconfig inbound updates in IPv6 vrf ad'
                                + 'dress family.'
                                  ;
                    }
                  }
                }
                leaf vrf-name {
                  description 'VPN Routing/Forwarding instance name.'
                              ;
                  type string {
                    length 1..32 ;
                  }
                }
                leaf v6-address {
                  description 'Neighbor IPv6 address.'
                              ;
                  type ncd:ipv6-address ;
                }
                leaf local-as {
                  description 'the Autonomy system number of BGP in local equip'
                            + 'ment.'
                              ;
                  type ncd:asn-dot ;
                  ncd:revise-date 2018-01-10 ;
                }
              }
            }
            container peer-groups {
              description 'Peer group to do soft reconfiguration.'
                          ;
              list peer-group {
                description 'Peer group.'
                            ;
                key 'peer-group-name direction vrf-name'
                    ;
                leaf direction {
                  description 'Direction of soft reconfiguration.'
                              ;
                  type enumeration {
                    enum ipv4-vrf-both {
                      value 2 ;
                      description 'Soft reconfig inbound and outbound updates i'
                                + 'n IPv4 vrf address family.'
                                  ;
                    }
                    enum ipv6-vrf-both {
                      value 6 ;
                      description 'Soft reconfig inbound and outbound updates i'
                                + 'n IPv6 vrf address family.'
                                  ;
                    }
                    enum ipv4-vrf-out {
                      value 34 ;
                      description 'Soft reconfig outbound updates in IPv4 vrf a'
                                + 'ddress family.'
                                  ;
                    }
                    enum ipv6-vrf-out {
                      value 37 ;
                      description 'Soft reconfig outbound updates in IPv6 vrf a'
                                + 'ddress family.'
                                  ;
                    }
                    enum ipv4-vrf-in {
                      value 43 ;
                      description 'Soft reconfig inbound updates in IPv4 vrf ad'
                                + 'dress family.'
                                  ;
                    }
                    enum ipv6-vrf-in {
                      value 46 ;
                      description 'Soft reconfig inbound updates in IPv6 vrf ad'
                                + 'dress family.'
                                  ;
                    }
                  }
                }
                leaf vrf-name {
                  description 'VPN Routing/Forwarding instance name.'
                              ;
                  type string {
                    length 1..32 ;
                  }
                }
                leaf peer-group-name {
                  description 'Peer group name.'
                              ;
                  type string {
                    length 1..31 ;
                  }
                }
                leaf local-as {
                  description 'the Autonomy system number of BGP in local equip'
                            + 'ment.'
                              ;
                  type ncd:asn-dot ;
                  ncd:revise-date 2018-01-10 ;
                }
              }
            }
            container all {
              description 'All neighbors of the address family mode to do soft '
                        + 'reconfiguration.'
                          ;
              list mode {
                description 'Address family command mode.'
                            ;
                key 'direction vrf-name'
                    ;
                leaf direction {
                  description 'Direction of soft reconfiguration.'
                              ;
                  type enumeration {
                    enum ipv4-vrf-both {
                      value 2 ;
                      description 'Soft reconfig inbound and outbound updates i'
                                + 'n IPv4 vrf address family.'
                                  ;
                    }
                    enum ipv6-vrf-both {
                      value 6 ;
                      description 'Soft reconfig inbound and outbound updates i'
                                + 'n IPv6 vrf address family.'
                                  ;
                    }
                    enum ipv4-vrf-out {
                      value 34 ;
                      description 'Soft reconfig outbound updates in IPv4 vrf a'
                                + 'ddress family.'
                                  ;
                    }
                    enum ipv6-vrf-out {
                      value 37 ;
                      description 'Soft reconfig outbound updates in IPv6 vrf a'
                                + 'ddress family.'
                                  ;
                    }
                    enum ipv4-vrf-in {
                      value 43 ;
                      description 'Soft reconfig inbound updates in IPv4 vrf ad'
                                + 'dress family.'
                                  ;
                    }
                    enum ipv6-vrf-in {
                      value 46 ;
                      description 'Soft reconfig inbound updates in IPv6 vrf ad'
                                + 'dress family.'
                                  ;
                    }
                  }
                }
                leaf vrf-name {
                  description 'VPN Routing/Forwarding instance name.'
                              ;
                  type string {
                    length 1..32 ;
                  }
                }
                leaf local-as {
                  description 'the Autonomy system number of BGP in local equip'
                            + 'ment.'
                              ;
                  type ncd:asn-dot ;
                  ncd:revise-date 2018-01-10 ;
                }
              }
            }
          }
        }
        container update-group {
          description 'Clear information on update-groups.'
                      ;
          container common {
            description 'Address family command mode.'
                        ;
            container v4-peer-address {
              description 'Clear information on update-group of the IPv4 Neighb'
                        + 'or.'
                          ;
              list peer {
                description 'IPv4 neighbor.'
                            ;
                key 'afi v4-address'
                    ;
                leaf afi {
                  description 'Address family command mode.'
                              ;
                  type enumeration {
                    enum v4-unicast {
                      value 14 ;
                      description 'IPv4 unicast address family.'
                                  ;
                    }
                    enum ipv6-unicast {
                      value 15 ;
                      description 'IPv6 unicast address family.'
                                  ;
                    }
                    enum v4-multicast {
                      value 16 ;
                      description 'IPv4 multicast address family.'
                                  ;
                    }
                    enum vpnv4-unicast {
                      value 18 ;
                      description 'VPNv4 address family.'
                                  ;
                    }
                    enum vpnv6-unicast {
                      value 19 ;
                      description 'VPNv6 address family.'
                                  ;
                    }
                    enum vpnv4-multicast {
                      value 20 ;
                      description 'VPNv4 multicast address family.'
                                  ;
                    }
                    enum vpnv4-mcast {
                      value 21 ;
                      description 'VPNv4 mcast address family.'
                                  ;
                    }
                    enum l2vpn-vpls {
                      value 22 ;
                      description 'L2VPN VPLS address family.'
                                  ;
                    }
                    enum ipv4-mdt {
                      value 29 ;
                      description 'IPv4 mdt address family.'
                                  ;
                    }
                    enum ipv4-flowspec {
                      value 49 ;
                      description 'IPv4 Flowspec address family.'
                                  ;
                    }
                    enum vpnv4-flowspec {
                      value 50 ;
                      description 'VPNv4 Flowspec address family.'
                                  ;
                    }
                    enum ipv6-flowspec {
                      value 58 ;
                      description 'IPv6 Flowspec address family.'
                                  ;
                    }
                    enum vpnv6-flowspec {
                      value 59 ;
                      description 'VPNv6 Flowspec address family.'
                                  ;
                    }
                    enum l2vpn-evpn {
                      value 103 ;
                      description 'L2VPN EVPN address family.'
                                  ;
                    }
                  }
                }
                leaf v4-address {
                  description 'Neighbor IPv4 address.'
                              ;
                  type ncd:ipv4-address ;
                }
                leaf local-as {
                  description 'the Autonomy system number of BGP in local equip'
                            + 'ment.'
                              ;
                  type ncd:asn-dot ;
                  ncd:revise-date 2018-01-10 ;
                }
              }
            }
            container v6-peer-address {
              description 'Clear information on update-group of the IPv6 Neighb'
                        + 'or.'
                          ;
              list peer {
                description 'IPv6 neighbor.'
                            ;
                key 'afi v6-address'
                    ;
                leaf afi {
                  description 'Address family command mode.'
                              ;
                  type enumeration {
                    enum ipv6-unicast {
                      value 15 ;
                      description 'IPv6 unicast address family.'
                                  ;
                    }
                    enum ipv6-multicast {
                      value 17 ;
                      description 'IPv6 multicast address family.'
                                  ;
                    }
                    enum vpnv6-unicast {
                      value 19 ;
                      description 'VPNv6 address family.'
                                  ;
                    }
                    enum ipv6-flowspec {
                      value 58 ;
                      description 'IPv6 Flowspec address family.'
                                  ;
                    }
                    enum vpnv6-flowspec {
                      value 59 ;
                      description 'VPNv6 Flowspec address family.'
                                  ;
                    }
                    enum ipv4-unicast {
                      value 14 ;
                      description 'IPv4 unicast address family.'
                                  ;
                    }
                    enum l2vpn-evpn {
                      value 103 ;
                      description 'L2VPN EVPN address family.'
                                  ;
                    }
                  }
                }
                leaf v6-address {
                  description 'Neighbor IPv6 address.'
                              ;
                  type ncd:ipv6-address ;
                }
                leaf local-as {
                  description 'the Autonomy system number of BGP in local equip'
                            + 'ment.'
                              ;
                  type ncd:asn-dot ;
                  ncd:revise-date 2018-01-10 ;
                }
              }
            }
            container indexes {
              description 'Clear information on update-group of the index.'
                          ;
              list index {
                description 'Index of update-group.'
                            ;
                key 'afi update-group-index'
                    ;
                leaf afi {
                  description 'Address family command mode.'
                              ;
                  type enumeration {
                    enum v4-unicast {
                      value 14 ;
                      description 'IPv4 unicast address family.'
                                  ;
                    }
                    enum ipv6-unicast {
                      value 15 ;
                      description 'IPv6 unicast address family.'
                                  ;
                    }
                    enum v4-multicast {
                      value 16 ;
                      description 'IPv4 multicast address family.'
                                  ;
                    }
                    enum ipv6-multicast {
                      value 17 ;
                      description 'IPv6 multicast address family.'
                                  ;
                    }
                    enum vpnv4-unicast {
                      value 18 ;
                      description 'VPNv4 address family.'
                                  ;
                    }
                    enum vpnv6-unicast {
                      value 19 ;
                      description 'VPNv6 address family.'
                                  ;
                    }
                    enum vpnv4-multicast {
                      value 20 ;
                      description 'VPNv4 multicast address family.'
                                  ;
                    }
                    enum vpnv4-mcast {
                      value 21 ;
                      description 'VPNv4 mcast address family.'
                                  ;
                    }
                    enum l2vpn-vpls {
                      value 22 ;
                      description 'L2VPN VPLS address family.'
                                  ;
                    }
                    enum ipv4-mdt {
                      value 29 ;
                      description 'IPv4 mdt address family.'
                                  ;
                    }
                    enum ipv4-flowspec {
                      value 49 ;
                      description 'IPv4 Flowspec address family.'
                                  ;
                    }
                    enum vpnv4-flowspec {
                      value 50 ;
                      description 'VPNv4 Flowspec address family.'
                                  ;
                    }
                    enum ipv6-flowspec {
                      value 58 ;
                      description 'IPv6 Flowspec address family.'
                                  ;
                    }
                    enum vpnv6-flowspec {
                      value 59 ;
                      description 'VPNv6 Flowspec address family.'
                                  ;
                    }
                    enum l2vpn-evpn {
                      value 103 ;
                      description 'L2VPN EVPN address family.'
                                  ;
                    }
                  }
                }
                leaf update-group-index {
                  description 'Index of update-group.'
                              ;
                  type uint32 ;
                }
                leaf local-as {
                  description 'the Autonomy system number of BGP in local equip'
                            + 'ment.'
                              ;
                  type ncd:asn-dot ;
                  ncd:revise-date 2018-01-10 ;
                }
              }
            }
            container all {
              description 'Clear all update-groups information of the address f'
                        + 'amily mode.'
                          ;
              list mode {
                description 'Address family command mode.'
                            ;
                key afi ;
                leaf afi {
                  description 'Address family command mode.'
                              ;
                  type enumeration {
                    enum v4-unicast {
                      value 14 ;
                      description 'IPv4 unicast address family.'
                                  ;
                    }
                    enum ipv6-unicast {
                      value 15 ;
                      description 'IPv6 unicast address family.'
                                  ;
                    }
                    enum v4-multicast {
                      value 16 ;
                      description 'IPv4 multicast address family.'
                                  ;
                    }
                    enum ipv6-multicast {
                      value 17 ;
                      description 'IPv6 multicast address family.'
                                  ;
                    }
                    enum vpnv4-unicast {
                      value 18 ;
                      description 'VPNv4 address family.'
                                  ;
                    }
                    enum vpnv6-unicast {
                      value 19 ;
                      description 'VPNv6 address family.'
                                  ;
                    }
                    enum vpnv4-multicast {
                      value 20 ;
                      description 'VPNv4 multicast address family.'
                                  ;
                    }
                    enum vpnv4-mcast {
                      value 21 ;
                      description 'VPNv4 mcast address family.'
                                  ;
                    }
                    enum l2vpn-vpls {
                      value 22 ;
                      description 'L2VPN VPLS address family.'
                                  ;
                    }
                    enum ipv4-mdt {
                      value 29 ;
                      description 'IPv4 mdt address family.'
                                  ;
                    }
                    enum ipv4-flowspec {
                      value 49 ;
                      description 'IPv4 Flowspec address family.'
                                  ;
                    }
                    enum vpnv4-flowspec {
                      value 50 ;
                      description 'VPNv4 Flowspec address family.'
                                  ;
                    }
                    enum ipv6-flowspec {
                      value 58 ;
                      description 'IPv6 Flowspec address family.'
                                  ;
                    }
                    enum vpnv6-flowspec {
                      value 59 ;
                      description 'VPNv6 Flowspec address family.'
                                  ;
                    }
                    enum l2vpn-evpn {
                      value 103 ;
                      description 'L2VPN EVPN address family.'
                                  ;
                    }
                  }
                }
                leaf local-as {
                  description 'the Autonomy system number of BGP in local equip'
                            + 'ment.'
                              ;
                  type ncd:asn-dot ;
                  ncd:revise-date 2018-01-10 ;
                }
              }
            }
          }
          container vrf {
            description 'IPv4/IPv6 vrf unicast address family command mode.'
                        ;
            container v4-peer-address {
              description 'Clear information on update-group of the IPv4 Neighb'
                        + 'or.'
                          ;
              list peer {
                description 'IPv4 Neighbor.'
                            ;
                key 'afi vrf-name v4-address'
                    ;
                leaf afi {
                  description 'Address family command mode.'
                              ;
                  type enumeration {
                    enum ipv4-vrf {
                      value 14 ;
                      description 'IPv4 vrf address family.'
                                  ;
                    }
                    enum v4-vrf-multicast {
                      value 16 ;
                      description 'IPv4 vrf multicast address family.'
                                  ;
                    }
                  }
                }
                leaf vrf-name {
                  description 'VPN Routing/Forwarding instance name.'
                              ;
                  type string {
                    length 1..32 ;
                  }
                }
                leaf v4-address {
                  description 'Neighbor IPv4 address.'
                              ;
                  type ncd:ipv4-address ;
                }
                leaf local-as {
                  description 'the Autonomy system number of BGP in local equip'
                            + 'ment.'
                              ;
                  type ncd:asn-dot ;
                  ncd:revise-date 2018-01-10 ;
                }
              }
            }
            container v6-peer-address {
              description 'Clear information on update-group of the IPv6 Neighb'
                        + 'or.'
                          ;
              list peer {
                description 'IPv6 neighbor.'
                            ;
                key 'afi vrf-name v6-address'
                    ;
                leaf afi {
                  description 'Address family command mode.'
                              ;
                  type enumeration {
                    enum ipv6-vrf {
                      value 15 ;
                      description 'IPv6 vrf address family.'
                                  ;
                    }
                  }
                }
                leaf vrf-name {
                  description 'VPN Routing/Forwarding instance name.'
                              ;
                  type string {
                    length 1..32 ;
                  }
                }
                leaf v6-address {
                  description 'Neighbor IPv6 address.'
                              ;
                  type ncd:ipv6-address ;
                }
                leaf local-as {
                  description 'the Autonomy system number of BGP in local equip'
                            + 'ment.'
                              ;
                  type ncd:asn-dot ;
                  ncd:revise-date 2018-01-10 ;
                }
              }
            }
            container indexes {
              description 'Clear information on update-group of the index.'
                          ;
              list index {
                description 'Index of update-group.'
                            ;
                key 'afi vrf-name update-group-index'
                    ;
                leaf afi {
                  description 'Address family command mode.'
                              ;
                  type enumeration {
                    enum ipv4-vrf {
                      value 14 ;
                      description 'IPv4 vrf address family.'
                                  ;
                    }
                    enum ipv6-vrf {
                      value 15 ;
                      description 'IPv6 vrf address family.'
                                  ;
                    }
                    enum v4-vrf-multicast {
                      value 16 ;
                      description 'IPv4 vrf multicast address family.'
                                  ;
                    }
                  }
                }
                leaf vrf-name {
                  description 'VPN Routing/Forwarding instance name.'
                              ;
                  type string {
                    length 1..32 ;
                  }
                }
                leaf update-group-index {
                  description 'Index of update-group.'
                              ;
                  type uint32 ;
                }
                leaf local-as {
                  description 'the Autonomy system number of BGP in local equip'
                            + 'ment.'
                              ;
                  type ncd:asn-dot ;
                  ncd:revise-date 2018-01-10 ;
                }
              }
            }
            container all {
              description 'Clear all update-group information of the address fa'
                        + 'mily mode.'
                          ;
              list mode {
                description 'Address family command mode.'
                            ;
                key 'afi vrf-name'
                    ;
                leaf afi {
                  description 'Address family command mode.'
                              ;
                  type enumeration {
                    enum ipv4-vrf {
                      value 14 ;
                      description 'IPv4 vrf address family.'
                                  ;
                    }
                    enum ipv6-vrf {
                      value 15 ;
                      description 'IPv6 vrf address family.'
                                  ;
                    }
                  }
                }
                leaf vrf-name {
                  description 'VPN Routing/Forwarding instance name.'
                              ;
                  type string {
                    length 1..32 ;
                  }
                }
                leaf local-as {
                  description 'the Autonomy system number of BGP in local equip'
                            + 'ment.'
                              ;
                  type ncd:asn-dot ;
                  ncd:revise-date 2018-01-10 ;
                }
              }
            }
          }
        }
      }
      container reset {
        description 'The reset operation.'
                    ;
        leaf bgp-instance {
          status obsolete {
            ncd:revise-date 2018-01-10 ;
          }
          description 'The BGP instance.'
                      ;
          type empty ;
        }
        container common {
          description 'Public network.'
                      ;
          container v4-peers {
            description 'IPv4 Neighbor.'
                        ;
            list v4-peer {
              description 'IPv4 Neighbor.'
                          ;
              key v4-address ;
              leaf v4-address {
                description 'Neighbor IPv4 address.'
                            ;
                type ncd:ipv4-address ;
              }
              leaf local-as {
                description 'the Autonomy system number of BGP in local equipme'
                          + 'nt.'
                            ;
                type ncd:asn-dot ;
                ncd:revise-date 2018-01-10 ;
              }
            }
          }
          container v6-peers {
            description 'IPv6 Neighbor.'
                        ;
            list v6-peer {
              description 'IPv6 Neighbor.'
                          ;
              key v6-address ;
              leaf v6-address {
                description 'Neighbor IPv6 address.'
                            ;
                type ncd:ipv6-address ;
              }
              leaf local-as {
                description 'the Autonomy system number of BGP in local equipme'
                          + 'nt.'
                            ;
                type ncd:asn-dot ;
                ncd:revise-date 2018-01-10 ;
              }
            }
          }
          container peer-groups {
            description 'The peer group.'
                        ;
            list peer-group {
              description 'The peer group.'
                          ;
              key peer-group-name ;
              leaf peer-group-name {
                description 'Peer group name.'
                            ;
                type ncd:string-all {
                  length 1..31 ;
                }
              }
              leaf local-as {
                description 'the Autonomy system number of BGP in local equipme'
                          + 'nt.'
                            ;
                type ncd:asn-dot ;
                ncd:revise-date 2018-01-10 ;
              }
            }
          }
        }
        container ipv4-vrf {
          description 'IPv4 vrf address family mode.'
                      ;
          container v4-peers {
            description 'IPv4 Neighbor.'
                        ;
            list v4-peer {
              description 'IPv4 Neighbor.'
                          ;
              key 'vrf-name v4-address'
                  ;
              leaf vrf-name {
                description 'VPN Routing/Forwarding instance name.'
                            ;
                type string {
                  length 1..32 ;
                }
              }
              leaf v4-address {
                description 'Neighbor IPv4 address.'
                            ;
                type ncd:ipv4-address ;
              }
              leaf local-as {
                description 'the Autonomy system number of BGP in local equipme'
                          + 'nt.'
                            ;
                type ncd:asn-dot ;
                ncd:revise-date 2018-01-10 ;
              }
            }
          }
          container peer-groups {
            description 'The peer group.'
                        ;
            list peer-group {
              description 'The peer group.'
                          ;
              key 'vrf-name peer-group-name'
                  ;
              leaf vrf-name {
                description 'VPN Routing/Forwarding instance name.'
                            ;
                type string {
                  length 1..32 ;
                }
              }
              leaf peer-group-name {
                description 'Peer group name.'
                            ;
                type ncd:string-all {
                  length 1..31 ;
                }
              }
              leaf local-as {
                description 'the Autonomy system number of BGP in local equipme'
                          + 'nt.'
                            ;
                type ncd:asn-dot ;
                ncd:revise-date 2018-01-10 ;
              }
            }
          }
          container vrf-all {
            description 'All peers in vrf address family mode.'
                        ;
            list vrf {
              description 'VPN Routing/Forwarding instance.'
                          ;
              key vrf-name ;
              leaf vrf-name {
                description 'VPN Routing/Forwarding instance name.'
                            ;
                type string {
                  length 1..32 ;
                }
              }
              leaf local-as {
                description 'the Autonomy system number of BGP in local equipme'
                          + 'nt.'
                            ;
                type ncd:asn-dot ;
                ncd:revise-date 2018-01-10 ;
              }
            }
          }
        }
        container ipv6-vrf {
          description 'IPv6 vrf address family mode.'
                      ;
          container v6-peers {
            description 'IPv6 Neighbor.'
                        ;
            list v6-peer {
              description 'IPv6 Neighbor.'
                          ;
              key 'vrf-name v6-address'
                  ;
              leaf vrf-name {
                description 'VPN Routing/Forwarding instance name.'
                            ;
                type string {
                  length 1..32 ;
                }
              }
              leaf v6-address {
                description 'Neighbor IPv6 address.'
                            ;
                type ncd:ipv6-address ;
              }
              leaf local-as {
                description 'the Autonomy system number of BGP in local equipme'
                          + 'nt.'
                            ;
                type ncd:asn-dot ;
                ncd:revise-date 2018-01-10 ;
              }
            }
          }
          container peer-groups {
            description 'The peer group.'
                        ;
            list peer-group {
              description 'The peer group.'
                          ;
              key 'vrf-name peer-group-name'
                  ;
              leaf vrf-name {
                description 'VPN Routing/Forwarding instance name.'
                            ;
                type string {
                  length 1..32 ;
                }
              }
              leaf peer-group-name {
                description 'Peer group name.'
                            ;
                type ncd:string-all {
                  length 1..31 ;
                }
              }
              leaf local-as {
                description 'the Autonomy system number of BGP in local equipme'
                          + 'nt.'
                            ;
                type ncd:asn-dot ;
                ncd:revise-date 2018-01-10 ;
              }
            }
          }
          container vrf-all {
            description 'All peers in vrf address family mode.'
                        ;
            list vrf {
              description 'VPN Routing/Forwarding instance.'
                          ;
              key vrf-name ;
              leaf vrf-name {
                description 'VPN Routing/Forwarding instance name.'
                            ;
                type string {
                  length 1..32 ;
                }
              }
              leaf local-as {
                description 'the Autonomy system number of BGP in local equipme'
                          + 'nt.'
                            ;
                type ncd:asn-dot ;
                ncd:revise-date 2018-01-10 ;
              }
            }
          }
        }
        container all {
          description 'All peers.'
                      ;
          presence "'enable all'"
                   ;
          leaf peer-type {
            description 'The peer type.'
                        ;
            type enumeration {
              enum ipv4-common-peer {
                value 4 ;
                description 'IPv4 public peers.'
                            ;
              }
              enum ipv4-peer {
                value 5 ;
                description 'IPv4 public peers and IPv4 vrf peers.'
                            ;
              }
              enum ipv6-common-peer {
                value 6 ;
                description 'IPv6 public peers.'
                            ;
              }
              enum ipv6-peer {
                value 7 ;
                description 'IPv6 public peers and IPv6 vrf peers.'
                            ;
              }
            }
            mandatory true ;
          }
          leaf local-as {
            description 'the Autonomy system number of BGP in local equipment.'
                        ;
            type ncd:asn-dot ;
            ncd:revise-date 2018-01-10 ;
          }
        }
        container ip {
          description 'IP protocol'
                      ;
          presence "'enable ip'"
                   ;
          leaf bgp-instance {
            description 'The BGP instance.'
                        ;
            type empty ;
            mandatory true ;
          }
          leaf local-as {
            description 'the Autonomy system number of BGP in local equipment.'
                        ;
            type ncd:asn-dot ;
          }
          ncd:revise-date 2018-01-10 ;
        }
        container rpki-rtr {
          description 'RPKI RTR process.'
                      ;
          container all {
            description 'All peers in RPKI-RTR mode.'
                        ;
            presence all-rpki-peer ;
            leaf rpki-rtr {
              description 'The RPKI RTR instance.'
                          ;
              type empty ;
              mandatory true ;
            }
            leaf local-as {
              description 'the Autonomy system number of BGP in local equipment.'
                          ;
              type ncd:asn-dot ;
            }
          }
          container v4-peers {
            description 'IPv4 Neighbor.'
                        ;
            list v4-peer {
              description 'IPv4 Neighbor.'
                          ;
              key v4-address ;
              leaf v4-address {
                description 'Neighbor IPv4 address.'
                            ;
                type ncd:ipv4-address ;
              }
              leaf local-as {
                description 'the Autonomy system number of BGP in local equipme'
                          + 'nt.'
                            ;
                type ncd:asn-dot ;
              }
            }
          }
          container v6-peers {
            description 'IPv6 Neighbor.'
                        ;
            list v6-peer {
              description 'IPv6 Neighbor.'
                          ;
              key v6-address ;
              leaf v6-address {
                description 'Neighbor IPv6 address.'
                            ;
                type ncd:ipv6-address ;
              }
              leaf local-as {
                description 'the Autonomy system number of BGP in local equipme'
                          + 'nt.'
                            ;
                type ncd:asn-dot ;
              }
            }
          }
          ncd:revise-date 2020-12-20 ;
        }
        ncd:revise-date 2015-07-24 ;
      }
      container set {
        description 'The set operation.'
                    ;
        presence "'enable the set operation.'"
                 ;
        leaf local-as {
          description 'the Autonomy system number of BGP in local equipment.'
                      ;
          type ncd:asn-dot ;
          ncd:revise-date 2018-01-10 ;
        }
        choice bgp-state {
          description 'The BGP state.'
                      ;
          mandatory true ;
          case disable-state {
            description 'The disable state.'
                        ;
            leaf disable {
              description 'The disable state.'
                          ;
              type empty ;
              mandatory true ;
            }
          }
          case enable-state {
            description 'The enable state.'
                        ;
            leaf enable {
              description 'The enable state.'
                          ;
              type empty ;
              mandatory true ;
            }
          }
        }
        ncd:revise-date 2015-07-24 ;
      }
      container controller-notify {
        description 'Controller notify BGP some events.'
                    ;
        leaf arp-finish {
          description 'Controller notify BGP the ARP synchronized event.'
                      ;
          type empty ;
        }
        ncd:revise-date 2016-03-07 ;
      }
    }
  }
  container state {
    config false ;
    description 'Bgp maintenance command.'
                ;
    container bgp {
      description 'BGP state.'
                  ;
      container peer-session {
        description 'Show peer session information.'
                    ;
        list peer {
          description 'Show peer session information.'
                      ;
          key 'local-as remote-address vrf-name'
              ;
          leaf local-as {
            description 'The local AS of the neighbor.'
                        ;
            type ncd:asn-dot ;
          }
          leaf remote-address {
            description 'The remote address of the neighbor.'
                        ;
            type string {
              length 1..46 ;
            }
          }
          leaf vrf-name {
            description 'VPN Routing/Forwarding instance name.'
                        ;
            type string {
              length 0..32 ;
            }
          }
          leaf state {
            description 'Fsm state of neighbor.'
                        ;
            type enumeration {
              enum idle {
                value 1 ;
              }
              enum connect {
                value 2 ;
              }
              enum active {
                value 3 ;
              }
              enum opensent {
                value 4 ;
              }
              enum openconfirm {
                value 5 ;
              }
              enum established {
                value 6 ;
              }
            }
          }
          leaf admin-status {
            description 'Administrative state of the neighbor.'
                        ;
            type enumeration {
              enum stop {
                value 1 ;
              }
              enum start {
                value 2 ;
              }
            }
          }
          leaf negotiation-version {
            description 'The negotiation version of the neighbor.'
                        ;
            type uint32 ;
          }
          leaf local-address {
            description 'The local address of the neighbor.'
                        ;
            type string {
              length 1..46 ;
            }
          }
          leaf local-port {
            description 'The local port of the neighbor.'
                        ;
            type uint32 ;
          }
          leaf local-router-id {
            description 'The local router-id of the neighbor.'
                        ;
            type ncd:ipv4-address ;
          }
          leaf remote-port {
            description 'The remote port of the neighbor.'
                        ;
            type uint32 ;
          }
          leaf remote-as {
            description 'The remote AS of the neighbor.'
                        ;
            type ncd:asn-dot ;
          }
          leaf remote-router-id {
            description 'The remote router-id of the neighbor.'
                        ;
            type ncd:ipv4-address ;
          }
          leaf in-updates {
            description 'The number of updates received from the neighbor.'
                        ;
            type uint32 ;
          }
          leaf out-updates {
            description 'The number of updates sent to the neighbor.'
                        ;
            type uint32 ;
          }
          leaf in-total-messages {
            description 'The number of all messages received from the neighbor.'
                        ;
            type uint32 ;
          }
          leaf out-total-messages {
            description 'The number of all messages sent to the neighbor.'
                        ;
            type uint32 ;
          }
          leaf last-error-code {
            description 'The last error code and last error subcode.'
                        ;
            type ncd:string-with-blank {
              length 0..8 ;
            }
          }
          leaf established-transitions {
            description 'The number that the neighbor transit to established st'
                      + 'ate.'
                        ;
            type uint32 ;
          }
          leaf established-time {
            description 'The elapsed time after the neighbor transited into est'
                      + 'ablished state.'
                        ;
            type uint32 ;
            units s ;
          }
          leaf connect-retry-interval {
            description 'The time that next connection will start.'
                        ;
            type uint32 ;
            units s ;
          }
          leaf hold-time {
            description 'The hold time.'
                        ;
            type uint32 ;
            units s ;
          }
          leaf keepalive-time {
            description 'The keepalive time.'
                        ;
            type uint32 ;
            units s ;
          }
          leaf configured-hold-time {
            description 'The configured hold time.'
                        ;
            type uint32 ;
            units s ;
          }
          leaf configured-keepalive-time {
            description 'The configured keepalive time.'
                        ;
            type uint32 ;
            units s ;
          }
          leaf originate-interval {
            description 'The interval time that the route originated in the AS '
                      + 'advertised.'
                        ;
            type uint32 ;
            units s ;
          }
          leaf advertisement-interval {
            description 'The interval time that the route originated out the AS'
                      + ' advertised.'
                        ;
            type uint32 ;
            units s ;
          }
          leaf in-update-elapsed-time {
            description 'The elapsed time after the neighbor received messages '
                      + 'last.'
                        ;
            type uint32 ;
            units s ;
          }
          leaf last-error-text {
            description 'The text infomation of last error.'
                        ;
            type ncd:string-all {
              length 0..128 ;
            }
          }
          leaf last-state {
            description 'The last state.'
                        ;
            type enumeration {
              enum idle {
                value 1 ;
              }
              enum connect {
                value 2 ;
              }
              enum active {
                value 3 ;
              }
              enum opensent {
                value 4 ;
              }
              enum openconfirm {
                value 5 ;
              }
              enum established {
                value 6 ;
              }
            }
          }
          ncd:select 'local-as remote-address'
                     ;
          ncd:select 'local-as remote-address vrf-name'
                     ;
        }
      }
      container peer-afi {
        description 'Show peer address family information.'
                    ;
        list peer {
          description 'Show peer address family information.'
                      ;
          key 'local-as remote-address afi vrf-name'
              ;
          leaf local-as {
            description 'The local AS of the neighbor.'
                        ;
            type ncd:asn-dot ;
          }
          leaf remote-address {
            description 'The remote address of the neighbor.'
                        ;
            type string {
              length 1..46 ;
            }
          }
          leaf afi {
            description 'Address family mode.'
                        ;
            type enumeration {
              enum ipv4-unicast {
                value 0 ;
                description 'IPv4 unicast address family.'
                            ;
              }
              enum ipv6-unicast {
                value 1 ;
                description 'IPv6 unicast address family.'
                            ;
              }
              enum ipv4-multicast {
                value 2 ;
                description 'IPv4 multicast address family.'
                            ;
              }
              enum ipv6-multicast {
                value 3 ;
                description 'IPv6 multicast address family.'
                            ;
              }
              enum vpnv4-unicast {
                value 4 ;
                description 'VPNv4 unicast address family.'
                            ;
              }
              enum vpnv6-unicast {
                value 5 ;
                description 'VPNv6 unicast address family.'
                            ;
              }
              enum vpnv4-mcast {
                value 6 ;
                description 'VPNv4 mcast address family.'
                            ;
              }
              enum vpnv4-multicast {
                value 7 ;
                description 'VPNv4 multicast address family.'
                            ;
              }
              enum l2vpn-vpls {
                value 8 ;
                description 'L2VPN VPLS address family.'
                            ;
              }
              enum route-target {
                value 9 ;
                description 'Route-target address family.'
                            ;
              }
              enum ipv4-mdt {
                value 10 ;
                description 'ipv4 multicast distribution tree address family.'
                            ;
              }
              enum vpnv6-multicast {
                value 11 ;
                description 'VPNv6 multicast address family.'
                            ;
              }
              enum vpnv6-mcast {
                value 12 ;
                description 'VPNv6 mcast address family.'
                            ;
              }
              enum l2vpn-evpn {
                value 13 ;
                description 'L2VPN EVPN address family.'
                            ;
              }
              enum link-state {
                value 14 ;
                description 'Link state address family.'
                            ;
              }
              enum ipv4-flowspec {
                value 15 ;
                description 'IPv4 Flowspec address family.'
                            ;
              }
              enum vpnv4-flowspec {
                value 16 ;
                description 'VPNv4 Flowspec address family.'
                            ;
              }
              enum ipv6-flowspec {
                value 17 ;
                description 'IPv6 Flowspec address family.'
                            ;
              }
              enum vpnv6-flowspec {
                value 18 ;
                description 'VPNv6 Flowspec address family.'
                            ;
              }
              enum ipv4-sr-policy {
                value 19 ;
                description 'IPv4 SR policy address family.'
                            ;
              }
              enum ipv6-sr-policy {
                value 20 ;
                description 'IPv6 SR policy address family.'
                            ;
              }
              enum link-state-vpn {
                value 21 ;
                description 'Link state vpn address family.'
                            ;
              }
            }
          }
          leaf vrf-name {
            description 'VPN Routing/Forwarding instance name.'
                        ;
            type string {
              length 0..32 ;
            }
          }
          leaf activate {
            description 'Enable the address family for this neighbor.'
                        ;
            type enumeration {
              enum false {
                value 0 ;
              }
              enum true {
                value 1 ;
              }
            }
          }
          leaf accepted-prefix {
            description 'The number of prefixes that the neighbor has accepted.'
                        ;
            type uint32 ;
          }
          leaf denied-prefix {
            description 'The number of prefixes that the neighbor has denied.'
                        ;
            type uint32 ;
          }
          leaf accepte-limit {
            description 'The limit of prefixes that the neighbor can accept.'
                        ;
            type uint32 ;
          }
          leaf sent-nlri {
            description 'The number of nlri that the neighbor has sent.'
                        ;
            type uint32 ;
          }
          leaf sent-unnlri {
            description 'The number of nlri that the neighbor has withdrawn.'
                        ;
            type uint32 ;
          }
          leaf route-map-in {
            description 'Apply route-map to receive routes from neighbor.'
                        ;
            type string {
              length 0..204 ;
            }
          }
          leaf route-map-out {
            description 'Apply route-map to send routes from neighbor.'
                        ;
            type string {
              length 0..204 ;
            }
          }
          leaf prefix-list-in {
            description 'Filter updates from this neighbor.'
                        ;
            type string {
              length 0..172 ;
            }
          }
          leaf prefix-list-out {
            description 'Filter updates to this neighbor.'
                        ;
            type string {
              length 0..172 ;
            }
          }
          leaf allow-as-in {
            description 'Accept as-path with my AS present in it.'
                        ;
            type uint32 {
              range 0..10 ;
            }
          }
          leaf max-as-in {
            description 'Accept as-path not exceeded maxas-in.'
                        ;
            type uint32 {
              range 1..250 ;
            }
          }
          leaf weight {
            description 'Set weight for routes from this neighbor.'
                        ;
            type uint32 {
              range 0..65535 ;
            }
          }
          leaf as-path-loopcheck {
            description 'Check as-path sending BGP routing to EBGP neighbor.'
                        ;
            type enumeration {
              enum false {
                value 0 ;
              }
              enum true {
                value 1 ;
              }
            }
          }
          leaf next-hop-self {
            description 'Disable the next hop calculation for this neighbor.'
                        ;
            type enumeration {
              enum false {
                value 0 ;
              }
              enum true {
                value 1 ;
              }
            }
          }
          leaf next-hop-self-all {
            description 'Apply next-hop-self for both EBGP and IBGP route.'
                        ;
            type enumeration {
              enum false {
                value 0 ;
              }
              enum true {
                value 1 ;
              }
            }
          }
          leaf next-hop-unchanged {
            description 'Propagate next hop unchanged for IBGP paths to this ne'
                      + 'ighbor.'
                        ;
            type enumeration {
              enum false {
                value 0 ;
              }
              enum true {
                value 1 ;
              }
            }
          }
          leaf remove-private-as {
            description 'EBGP use to remove private AS number.'
                        ;
            type enumeration {
              enum false {
                value 0 ;
              }
              enum true {
                value 1 ;
              }
            }
          }
          leaf route-reflector-client {
            description 'Set this neighbor as a client peer.'
                        ;
            type enumeration {
              enum false {
                value 0 ;
              }
              enum true {
                value 1 ;
              }
            }
          }
          leaf send-community {
            description 'Send community to this neighbor.'
                        ;
            type enumeration {
              enum false {
                value 0 ;
              }
              enum true {
                value 1 ;
              }
            }
          }
          leaf send-med {
            description 'Send metric attribute to this neighbor.'
                        ;
            type enumeration {
              enum false {
                value 0 ;
              }
              enum true {
                value 1 ;
              }
            }
          }
          leaf split-update-group {
            description 'Split neighbor from update group.'
                        ;
            type enumeration {
              enum false {
                value 0 ;
              }
              enum true {
                value 1 ;
              }
            }
          }
          leaf cap-send-add-paths {
            description 'The capability of Sending additional paths to this nei'
                      + 'ghbor.'
                        ;
            type enumeration {
              enum false {
                value 0 ;
              }
              enum true {
                value 1 ;
              }
            }
          }
          leaf cap-recv-add-paths {
            description 'The capability of receiving additional paths from this'
                      + ' neighbor.'
                        ;
            type enumeration {
              enum false {
                value 0 ;
              }
              enum true {
                value 1 ;
              }
            }
          }
          leaf send-add-paths-num {
            description 'Number of additional paths for a prefix.'
                        ;
            type uint32 ;
          }
          leaf adv-diverse-backup {
            description 'Advertise backup path to this neighbor.'
                        ;
            type enumeration {
              enum false {
                value 0 ;
              }
              enum true {
                value 1 ;
              }
            }
          }
          leaf adv-diverse-mpath {
            description 'Advertise the multipath to this neighbor.'
                        ;
            type uint32 ;
          }
          leaf diverse-map {
            description 'The route-map that applied to advertise diverse path.'
                        ;
            type string {
              length 0..204 ;
            }
          }
          leaf cap-orf-prefix-list {
            description 'Advertise prefixlist ORF capability to this neighbor.'
                        ;
            type enumeration {
              enum receive {
                value 1 ;
              }
              enum send {
                value 2 ;
              }
              enum both {
                value 3 ;
              }
              enum none {
                value 0 ;
              }
            }
          }
          leaf advertise-map {
            description 'Specify route-map for conditional advertisement.'
                        ;
            type string {
              length 0..204 ;
            }
          }
          leaf exist-map {
            description 'Advertise prefix only if prefix exists.'
                        ;
            type string {
              length 0..204 ;
            }
          }
          leaf non-exist-map {
            description 'Advertise prefix only if prefix does not exist.'
                        ;
            type string {
              length 0..204 ;
            }
          }
          leaf default-originate {
            description 'Originate default route to this neighbor.'
                        ;
            type enumeration {
              enum false {
                value 0 ;
              }
              enum true {
                value 1 ;
              }
            }
          }
          leaf send-label {
            description 'Send NLRI and MPLS label to this peer.'
                        ;
            type enumeration {
              enum false {
                value 0 ;
              }
              enum true {
                value 1 ;
              }
            }
          }
          leaf soft-reconfiguration {
            description 'Per neighbor soft reconfiguration.'
                        ;
            type enumeration {
              enum false {
                value 0 ;
              }
              enum true {
                value 1 ;
              }
            }
          }
          leaf as-override {
            description 'Override matching AS-number while sending update.'
                        ;
            type enumeration {
              enum false {
                value 0 ;
              }
              enum true {
                value 1 ;
              }
            }
          }
          ncd:select 'local-as remote-address afi'
                     ;
          ncd:select 'local-as remote-address afi vrf-name'
                     ;
        }
      }
      container routes {
        status obsolete {
          ncd:revise-date 2018-01-10 ;
        }
        description 'Show route information.'
                    ;
        container ipv4-unicast {
          description 'Show IPv4 unicast route information.'
                      ;
          list route {
            description 'IPv4 unicast route.'
                        ;
            key 'prefix vrf'
                ;
            leaf vrf {
              description 'VPN Routing/Forwarding instance name.'
                          ;
              type string {
                length 0..32 ;
              }
            }
            leaf prefix {
              description 'Network address and mask.'
                          ;
              type string {
                length 0..50 ;
              }
            }
            leaf from-peer {
              description 'Neighbor remote address that the route is received f'
                        + 'rom.'
                          ;
              type string {
                length 0..46 ;
              }
            }
            leaf path-id {
              description 'The path-id.'
                          ;
              type uint32 ;
            }
            leaf best {
              description 'Mark for the best.'
                          ;
              type enumeration {
                enum false {
                  value 1 ;
                  description 'Not chosen as best route.'
                              ;
                }
                enum true {
                  value 2 ;
                  description 'Chosen as best route.'
                              ;
                }
              }
            }
            leaf origin {
              description 'Origin attribute.'
                          ;
              type enumeration {
                enum igp {
                  value 1 ;
                  description 'Networks are interior.'
                              ;
                }
                enum egp {
                  value 2 ;
                  description 'Networks learned via EGP.'
                              ;
                }
                enum incomplete {
                  value 3 ;
                  description Undetermined. ;
                }
              }
            }
            leaf as-path {
              description 'As path attribute.'
                          ;
              type ncd:string-with-blank {
                length 0..256 ;
              }
            }
            leaf nexthop {
              description 'Nexthop attribute.'
                          ;
              type string {
                length 0..46 ;
              }
            }
            leaf med {
              description 'MED attribute.'
                          ;
              type uint32 ;
            }
            leaf local-preference {
              description 'Local preference attribute.'
                          ;
              type uint32 ;
            }
            leaf atomic {
              description 'The atomic-aggregate attribute.'
                          ;
              type enumeration {
                enum no-select {
                  value 1 ;
                }
                enum select {
                  value 2 ;
                }
              }
            }
            leaf aggregator {
              description 'The aggregator attribute.'
                          ;
              type ncd:string-with-blank {
                length 0..28 ;
              }
            }
            leaf community {
              description 'The community attribute.'
                          ;
              type ncd:string-with-blank {
                length 0..256 ;
              }
            }
            leaf originator-id {
              description 'The originator-id attribute.'
                          ;
              type string {
                length 0..16 ;
              }
            }
            leaf cluster-list {
              description 'The cluster-list attribute.'
                          ;
              type ncd:string-with-blank {
                length 0..256 ;
              }
            }
            leaf label-in {
              description 'In label.'
                          ;
              type uint32 ;
            }
            leaf label-out {
              description 'Out label.'
                          ;
              type uint32 ;
            }
            leaf unknown {
              description 'Unknown attribute.'
                          ;
              type ncd:string-with-blank {
                length 0..256 ;
              }
            }
            ncd:select prefix ;
            ncd:select 'vrf prefix'
                       ;
          }
        }
        container vpnv4-unicast {
          description 'Show VPNv4 unicast route information.'
                      ;
          list route {
            description 'VPNv4 unicast route.'
                        ;
            key 'rd prefix'
                ;
            leaf rd {
              description 'Specify route distinguisher.'
                          ;
              type string {
                length 0..22 ;
              }
            }
            leaf prefix {
              description 'Network address and mask.'
                          ;
              type string {
                length 0..50 ;
              }
            }
            leaf from-peer {
              description 'Neighbor remote address that the route is received f'
                        + 'rom.'
                          ;
              type string {
                length 0..46 ;
              }
            }
            leaf path-id {
              description 'The path-id.'
                          ;
              type uint32 ;
            }
            leaf best {
              description 'Mark for the best.'
                          ;
              type enumeration {
                enum false {
                  value 1 ;
                  description 'Not chosen as best route.'
                              ;
                }
                enum true {
                  value 2 ;
                  description 'Chosen as best route.'
                              ;
                }
              }
            }
            leaf origin {
              description 'Origin attribute.'
                          ;
              type enumeration {
                enum igp {
                  value 1 ;
                  description 'Networks are interior.'
                              ;
                }
                enum egp {
                  value 2 ;
                  description 'Networks learned via EGP.'
                              ;
                }
                enum incomplete {
                  value 3 ;
                  description Undetermined. ;
                }
              }
            }
            leaf as-path {
              description 'As path attribute.'
                          ;
              type ncd:string-with-blank {
                length 0..256 ;
              }
            }
            leaf nexthop {
              description 'Nexthop attribute.'
                          ;
              type string {
                length 0..46 ;
              }
            }
            leaf med {
              description 'MED attribute.'
                          ;
              type uint32 ;
            }
            leaf local-preference {
              description 'Local preference attribute.'
                          ;
              type uint32 ;
            }
            leaf atomic {
              description 'The atomic-aggregate attribute.'
                          ;
              type enumeration {
                enum no-select {
                  value 1 ;
                }
                enum select {
                  value 2 ;
                }
              }
            }
            leaf aggregator {
              description 'The aggregator attribute.'
                          ;
              type ncd:string-with-blank {
                length 0..28 ;
              }
            }
            leaf community {
              description 'The community attribute.'
                          ;
              type ncd:string-with-blank {
                length 0..256 ;
              }
            }
            leaf originator-id {
              description 'The originator-id attribute.'
                          ;
              type string {
                length 0..16 ;
              }
            }
            leaf cluster-list {
              description 'The cluster-list attribute.'
                          ;
              type ncd:string-with-blank {
                length 0..256 ;
              }
            }
            leaf ext-community {
              description 'The extended communtiy attribute.'
                          ;
              type ncd:string-with-blank {
                length 0..256 ;
              }
            }
            leaf label-in {
              description 'In label.'
                          ;
              type uint32 ;
            }
            leaf label-out {
              description 'Out label.'
                          ;
              type uint32 ;
            }
            leaf unknown {
              description 'Unknown attribute.'
                          ;
              type ncd:string-with-blank {
                length 0..256 ;
              }
            }
            ncd:select 'rd prefix'
                       ;
          }
        }
        container ipv6-unicast {
          description 'Show IPv6 unicast route information.'
                      ;
          list route {
            description 'IPv6 unicast route.'
                        ;
            key 'prefix vrf'
                ;
            leaf vrf {
              description 'VPN Routing/Forwarding instance name.'
                          ;
              type string {
                length 0..32 ;
              }
            }
            leaf prefix {
              description 'Network address and mask.'
                          ;
              type string {
                length 0..50 ;
              }
            }
            leaf from-peer {
              description 'Neighbor remote address that the route is received f'
                        + 'rom.'
                          ;
              type string {
                length 0..46 ;
              }
            }
            leaf path-id {
              description 'The path-id.'
                          ;
              type uint32 ;
            }
            leaf best {
              description 'Mark for the best.'
                          ;
              type enumeration {
                enum false {
                  value 1 ;
                  description 'Not chosen as best route.'
                              ;
                }
                enum true {
                  value 2 ;
                  description 'Chosen as best route.'
                              ;
                }
              }
            }
            leaf origin {
              description 'Origin attribute.'
                          ;
              type enumeration {
                enum igp {
                  value 1 ;
                  description 'Networks are interior.'
                              ;
                }
                enum egp {
                  value 2 ;
                  description 'Networks learned via EGP.'
                              ;
                }
                enum incomplete {
                  value 3 ;
                  description Undetermined. ;
                }
              }
            }
            leaf as-path {
              description 'As path attribute.'
                          ;
              type ncd:string-with-blank {
                length 0..256 ;
              }
            }
            leaf nexthop {
              description 'Nexthop attribute.'
                          ;
              type string {
                length 0..46 ;
              }
            }
            leaf med {
              description 'MED attribute.'
                          ;
              type uint32 ;
            }
            leaf local-preference {
              description 'Local preference attribute.'
                          ;
              type uint32 ;
            }
            leaf atomic {
              description 'The atomic-aggregate attribute.'
                          ;
              type enumeration {
                enum no-select {
                  value 1 ;
                }
                enum select {
                  value 2 ;
                }
              }
            }
            leaf aggregator {
              description 'The aggregator attribute.'
                          ;
              type ncd:string-with-blank {
                length 0..28 ;
              }
            }
            leaf community {
              description 'The community attribute.'
                          ;
              type ncd:string-with-blank {
                length 0..256 ;
              }
            }
            leaf originator-id {
              description 'The originator-id attribute.'
                          ;
              type string {
                length 0..16 ;
              }
            }
            leaf cluster-list {
              description 'The cluster-list attribute.'
                          ;
              type ncd:string-with-blank {
                length 0..256 ;
              }
            }
            leaf label-in {
              description 'In label.'
                          ;
              type uint32 ;
            }
            leaf label-out {
              description 'Out label.'
                          ;
              type uint32 ;
            }
            leaf unknown {
              description 'Unknown attribute.'
                          ;
              type ncd:string-with-blank {
                length 0..256 ;
              }
            }
            ncd:select prefix ;
            ncd:select 'vrf prefix'
                       ;
          }
        }
        container vpnv6-unicast {
          description 'Show VPNv6 unicast route information.'
                      ;
          list route {
            description 'VPNv6 unicast route.'
                        ;
            key 'rd prefix'
                ;
            leaf rd {
              description 'Specify route distinguisher.'
                          ;
              type string {
                length 0..22 ;
              }
            }
            leaf prefix {
              description 'Network address and mask.'
                          ;
              type string {
                length 0..50 ;
              }
            }
            leaf from-peer {
              description 'Neighbor remote address that the route is received f'
                        + 'rom.'
                          ;
              type string {
                length 0..46 ;
              }
            }
            leaf path-id {
              description 'The path-id.'
                          ;
              type uint32 ;
            }
            leaf best {
              description 'Mark for the best.'
                          ;
              type enumeration {
                enum false {
                  value 1 ;
                  description 'Not chosen as best route.'
                              ;
                }
                enum true {
                  value 2 ;
                  description 'Chosen as best route.'
                              ;
                }
              }
            }
            leaf origin {
              description 'Origin attribute.'
                          ;
              type enumeration {
                enum igp {
                  value 1 ;
                  description 'Networks are interior.'
                              ;
                }
                enum egp {
                  value 2 ;
                  description 'Networks learned via EGP.'
                              ;
                }
                enum incomplete {
                  value 3 ;
                  description Undetermined. ;
                }
              }
            }
            leaf as-path {
              description 'As path attribute.'
                          ;
              type ncd:string-with-blank {
                length 0..256 ;
              }
            }
            leaf nexthop {
              description 'Nexthop attribute.'
                          ;
              type string {
                length 0..46 ;
              }
            }
            leaf med {
              description 'MED attribute.'
                          ;
              type uint32 ;
            }
            leaf local-preference {
              description 'Local preference attribute.'
                          ;
              type uint32 ;
            }
            leaf atomic {
              description 'The atomic-aggregate attribute.'
                          ;
              type enumeration {
                enum no-select {
                  value 1 ;
                }
                enum select {
                  value 2 ;
                }
              }
            }
            leaf aggregator {
              description 'The aggregator attribute.'
                          ;
              type ncd:string-with-blank {
                length 0..28 ;
              }
            }
            leaf community {
              description 'The community attribute.'
                          ;
              type ncd:string-with-blank {
                length 0..256 ;
              }
            }
            leaf originator-id {
              description 'The originator-id attribute.'
                          ;
              type string {
                length 0..16 ;
              }
            }
            leaf cluster-list {
              description 'The cluster-list attribute.'
                          ;
              type ncd:string-with-blank {
                length 0..256 ;
              }
            }
            leaf ext-community {
              description 'The extended communtiy attribute.'
                          ;
              type ncd:string-with-blank ;
            }
            leaf label-in {
              description 'In label.'
                          ;
              type uint32 ;
            }
            leaf label-out {
              description 'Out label.'
                          ;
              type uint32 ;
            }
            leaf unknown {
              description 'Unknown attribute.'
                          ;
              type ncd:string-with-blank {
                length 0..256 ;
              }
            }
            ncd:select 'rd prefix'
                       ;
          }
        }
      }
      container in-routes {
        status obsolete {
          ncd:revise-date 2018-01-10 ;
        }
        description 'Show route information from BGP neighbor.'
                    ;
        container ipv4-unicast {
          description 'Show IPv4 unicast route information.'
                      ;
          list route {
            description 'IPv4 unicast route.'
                        ;
            key 'vrf from-peer prefix path-id'
                ;
            leaf vrf {
              description 'VPN Routing/Forwarding instance name.'
                          ;
              type string {
                length 0..32 ;
              }
            }
            leaf from-peer {
              description 'Neighbor remote address that the route is received f'
                        + 'rom.'
                          ;
              type string {
                length 0..46 ;
              }
            }
            leaf prefix {
              description 'Network address and mask.'
                          ;
              type string {
                length 0..50 ;
              }
            }
            leaf path-id {
              description 'The path-id.'
                          ;
              type uint32 ;
            }
            leaf best {
              description 'Mark for the best.'
                          ;
              type enumeration {
                enum false {
                  value 1 ;
                  description 'Not chosen as best route.'
                              ;
                }
                enum true {
                  value 2 ;
                  description 'Chosen as best route.'
                              ;
                }
              }
            }
            leaf origin {
              description 'Origin attribute.'
                          ;
              type enumeration {
                enum igp {
                  value 1 ;
                  description 'Networks are interior.'
                              ;
                }
                enum egp {
                  value 2 ;
                  description 'Networks learned via EGP.'
                              ;
                }
                enum incomplete {
                  value 3 ;
                  description Undetermined. ;
                }
              }
            }
            leaf as-path {
              description 'As path attribute.'
                          ;
              type ncd:string-with-blank {
                length 0..256 ;
              }
            }
            leaf nexthop {
              description 'Nexthop attribute.'
                          ;
              type string {
                length 0..46 ;
              }
            }
            leaf med {
              description 'MED attribute.'
                          ;
              type uint32 ;
            }
            leaf local-preference {
              description 'Local preference attribute.'
                          ;
              type uint32 ;
            }
            leaf atomic {
              description 'The atomic-aggregate attribute.'
                          ;
              type enumeration {
                enum no-select {
                  value 1 ;
                }
                enum select {
                  value 2 ;
                }
              }
            }
            leaf aggregator {
              description 'The aggregator attribute.'
                          ;
              type ncd:string-with-blank {
                length 0..28 ;
              }
            }
            leaf community {
              description 'The community attribute.'
                          ;
              type ncd:string-with-blank {
                length 0..256 ;
              }
            }
            leaf originator-id {
              description 'The originator-id attribute.'
                          ;
              type string {
                length 0..16 ;
              }
            }
            leaf cluster-list {
              description 'The cluster-list attribute.'
                          ;
              type ncd:string-with-blank {
                length 0..256 ;
              }
            }
            leaf as4-path {
              description 'The as4-path attribute.'
                          ;
              type ncd:string-with-blank ;
            }
            leaf as4-aggregator {
              description 'The as4-aggregator attribute.'
                          ;
              type ncd:string-with-blank ;
            }
            leaf label-in {
              description 'Received label.'
                          ;
              type uint32 ;
            }
            leaf label-out {
              status obsolete {
                ncd:revise-date 2015-07-15 ;
              }
              description 'Out label.'
                          ;
              type uint32 ;
            }
            leaf unknown {
              description 'Unknown attribute.'
                          ;
              type ncd:string-with-blank {
                length 0..256 ;
              }
            }
            ncd:select 'vrf from-peer prefix path-id'
                       ;
            ncd:select 'from-peer prefix path-id'
                       ;
          }
        }
        container vpnv4-unicast {
          description 'Show VPNv4 unicast route information.'
                      ;
          list route {
            description 'VPNv4 unicast route.'
                        ;
            key 'from-peer rd prefix path-id'
                ;
            leaf from-peer {
              description 'Neighbor remote address that the route is received f'
                        + 'rom.'
                          ;
              type string {
                length 0..46 ;
              }
            }
            leaf rd {
              description 'Specify route distinguisher.'
                          ;
              type string {
                length 0..22 ;
              }
            }
            leaf prefix {
              description 'Network address and mask.'
                          ;
              type string {
                length 0..50 ;
              }
            }
            leaf path-id {
              description 'The path-id.'
                          ;
              type uint32 ;
            }
            leaf best {
              description 'Mark for the best.'
                          ;
              type enumeration {
                enum false {
                  value 1 ;
                  description 'Not chosen as best route.'
                              ;
                }
                enum true {
                  value 2 ;
                  description 'Chosen as best route.'
                              ;
                }
              }
            }
            leaf origin {
              description 'Origin attribute.'
                          ;
              type enumeration {
                enum igp {
                  value 1 ;
                  description 'Networks are interior.'
                              ;
                }
                enum egp {
                  value 2 ;
                  description 'Networks learned via EGP.'
                              ;
                }
                enum incomplete {
                  value 3 ;
                  description Undetermined. ;
                }
              }
            }
            leaf as-path {
              description 'As path attribute.'
                          ;
              type ncd:string-with-blank {
                length 0..256 ;
              }
            }
            leaf nexthop {
              description 'Nexthop attribute.'
                          ;
              type string {
                length 0..46 ;
              }
            }
            leaf med {
              description 'MED attribute.'
                          ;
              type uint32 ;
            }
            leaf local-preference {
              description 'Local preference attribute.'
                          ;
              type uint32 ;
            }
            leaf atomic {
              description 'The atomic-aggregate attribute.'
                          ;
              type enumeration {
                enum no-select {
                  value 1 ;
                }
                enum select {
                  value 2 ;
                }
              }
            }
            leaf aggregator {
              description 'The aggregator attribute.'
                          ;
              type ncd:string-with-blank {
                length 0..28 ;
              }
            }
            leaf community {
              description 'The community attribute.'
                          ;
              type ncd:string-with-blank {
                length 0..256 ;
              }
            }
            leaf originator-id {
              description 'The originator-id attribute.'
                          ;
              type string {
                length 0..16 ;
              }
            }
            leaf cluster-list {
              description 'The cluster-list attribute.'
                          ;
              type ncd:string-with-blank {
                length 0..256 ;
              }
            }
            leaf as4-path {
              description 'The as4-path attribute.'
                          ;
              type ncd:string-with-blank ;
            }
            leaf as4-aggregator {
              description 'The as4-aggregator attribute.'
                          ;
              type ncd:string-with-blank ;
            }
            leaf ext-community {
              description 'The extended communtiy attribute.'
                          ;
              type ncd:string-with-blank ;
            }
            leaf label-in {
              description 'Received label.'
                          ;
              type uint32 ;
            }
            leaf label-out {
              status obsolete {
                ncd:revise-date 2015-07-15 ;
              }
              description 'Out label.'
                          ;
              type uint32 ;
            }
            leaf unknown {
              description 'Unknown attribute.'
                          ;
              type ncd:string-with-blank {
                length 0..256 ;
              }
            }
            ncd:select 'from-peer rd prefix path-id'
                       ;
          }
        }
        container ipv6-unicast {
          description 'Show IPv6 unicast route information.'
                      ;
          list route {
            description 'IPv6 unicast route.'
                        ;
            key 'vrf from-peer prefix path-id'
                ;
            leaf vrf {
              description 'VPN Routing/Forwarding instance name.'
                          ;
              type string {
                length 0..32 ;
              }
            }
            leaf from-peer {
              description 'Neighbor remote address that the route is received f'
                        + 'rom.'
                          ;
              type string {
                length 0..46 ;
              }
            }
            leaf prefix {
              description 'Network address and mask.'
                          ;
              type string {
                length 0..50 ;
              }
            }
            leaf path-id {
              description 'The path-id.'
                          ;
              type uint32 ;
            }
            leaf best {
              description 'Mark for the best.'
                          ;
              type enumeration {
                enum false {
                  value 1 ;
                  description 'Not chosen as best route.'
                              ;
                }
                enum true {
                  value 2 ;
                  description 'Chosen as best route.'
                              ;
                }
              }
            }
            leaf origin {
              description 'Origin attribute.'
                          ;
              type enumeration {
                enum igp {
                  value 1 ;
                  description 'Networks are interior.'
                              ;
                }
                enum egp {
                  value 2 ;
                  description 'Networks learned via EGP.'
                              ;
                }
                enum incomplete {
                  value 3 ;
                  description Undetermined. ;
                }
              }
            }
            leaf as-path {
              description 'As path attribute.'
                          ;
              type ncd:string-with-blank {
                length 0..256 ;
              }
            }
            leaf nexthop {
              description 'Nexthop attribute.'
                          ;
              type string {
                length 0..46 ;
              }
            }
            leaf med {
              description 'MED attribute.'
                          ;
              type uint32 ;
            }
            leaf local-preference {
              description 'Local preference attribute.'
                          ;
              type uint32 ;
            }
            leaf atomic {
              description 'The atomic-aggregate attribute.'
                          ;
              type enumeration {
                enum no-select {
                  value 1 ;
                }
                enum select {
                  value 2 ;
                }
              }
            }
            leaf aggregator {
              description 'The aggregator attribute.'
                          ;
              type ncd:string-with-blank {
                length 0..28 ;
              }
            }
            leaf community {
              description 'The community attribute.'
                          ;
              type ncd:string-with-blank {
                length 0..256 ;
              }
            }
            leaf originator-id {
              description 'The originator-id attribute.'
                          ;
              type string {
                length 0..16 ;
              }
            }
            leaf cluster-list {
              description 'The cluster-list attribute.'
                          ;
              type ncd:string-with-blank {
                length 0..256 ;
              }
            }
            leaf as4-path {
              description 'The as4-path attribute.'
                          ;
              type ncd:string-with-blank ;
            }
            leaf as4-aggregator {
              description 'The as4-aggregator attribute.'
                          ;
              type ncd:string-with-blank ;
            }
            leaf label-in {
              description 'Received label.'
                          ;
              type uint32 ;
            }
            leaf label-out {
              status obsolete {
                ncd:revise-date 2015-07-15 ;
              }
              description 'Out label.'
                          ;
              type uint32 ;
            }
            leaf unknown {
              description 'Unknown attribute.'
                          ;
              type ncd:string-with-blank {
                length 0..256 ;
              }
            }
            ncd:select 'vrf from-peer prefix path-id'
                       ;
            ncd:select 'from-peer prefix path-id'
                       ;
          }
        }
        container vpnv6-unicast {
          description 'Show VPNv6 unicast route information.'
                      ;
          list route {
            description 'VPNv6 unicast route.'
                        ;
            key 'from-peer rd prefix path-id'
                ;
            leaf from-peer {
              description 'Neighbor remote address that the route is received f'
                        + 'rom.'
                          ;
              type string {
                length 0..46 ;
              }
            }
            leaf rd {
              description 'Specify route distinguisher.'
                          ;
              type string {
                length 0..22 ;
              }
            }
            leaf prefix {
              description 'Network address and mask.'
                          ;
              type string {
                length 0..50 ;
              }
            }
            leaf path-id {
              description 'The path-id.'
                          ;
              type uint32 ;
            }
            leaf best {
              description 'Mark for the best.'
                          ;
              type enumeration {
                enum false {
                  value 1 ;
                  description 'Not chosen as best route.'
                              ;
                }
                enum true {
                  value 2 ;
                  description 'Chosen as best route.'
                              ;
                }
              }
            }
            leaf origin {
              description 'Origin attribute.'
                          ;
              type enumeration {
                enum igp {
                  value 1 ;
                  description 'Networks are interior.'
                              ;
                }
                enum egp {
                  value 2 ;
                  description 'Networks learned via EGP.'
                              ;
                }
                enum incomplete {
                  value 3 ;
                  description Undetermined. ;
                }
              }
            }
            leaf as-path {
              description 'As path attribute.'
                          ;
              type ncd:string-with-blank {
                length 0..256 ;
              }
            }
            leaf nexthop {
              description 'Nexthop attribute.'
                          ;
              type string {
                length 0..46 ;
              }
            }
            leaf med {
              description 'MED attribute.'
                          ;
              type uint32 ;
            }
            leaf local-preference {
              description 'Local preference attribute.'
                          ;
              type uint32 ;
            }
            leaf atomic {
              description 'The atomic-aggregate attribute.'
                          ;
              type enumeration {
                enum no-select {
                  value 1 ;
                }
                enum select {
                  value 2 ;
                }
              }
            }
            leaf aggregator {
              description 'The aggregator attribute.'
                          ;
              type ncd:string-with-blank {
                length 0..28 ;
              }
            }
            leaf community {
              description 'The community attribute.'
                          ;
              type ncd:string-with-blank {
                length 0..256 ;
              }
            }
            leaf originator-id {
              description 'The originator-id attribute.'
                          ;
              type string {
                length 0..16 ;
              }
            }
            leaf cluster-list {
              description 'The cluster-list attribute.'
                          ;
              type ncd:string-with-blank {
                length 0..256 ;
              }
            }
            leaf as4-path {
              description 'The as4-path attribute.'
                          ;
              type ncd:string-with-blank ;
            }
            leaf as4-aggregator {
              description 'The as4-aggregator attribute.'
                          ;
              type ncd:string-with-blank ;
            }
            leaf ext-community {
              description 'The extended communtiy attribute.'
                          ;
              type ncd:string-with-blank ;
            }
            leaf label-in {
              description 'Received label.'
                          ;
              type uint32 ;
            }
            leaf label-out {
              status obsolete {
                ncd:revise-date 2015-07-15 ;
              }
              description 'Out label.'
                          ;
              type uint32 ;
            }
            leaf unknown {
              description 'Unknown attribute.'
                          ;
              type ncd:string-with-blank {
                length 0..256 ;
              }
            }
            ncd:select 'from-peer rd prefix path-id'
                       ;
          }
        }
      }
      container out-routes {
        status obsolete {
          ncd:revise-date 2018-01-10 ;
        }
        description 'Show route information to BGP neighbor.'
                    ;
        container ipv4-unicast {
          description 'Show IPv4 unicast route information.'
                      ;
          list route {
            description 'IPv4 unicast route.'
                        ;
            key 'vrf to-peer prefix path-id'
                ;
            leaf vrf {
              description 'VPN Routing/Forwarding instance name.'
                          ;
              type string {
                length 0..32 ;
              }
            }
            leaf to-peer {
              description 'Neighbor remote address that the route is sent to.'
                          ;
              type string {
                length 0..46 ;
              }
            }
            leaf prefix {
              description 'Network address and mask.'
                          ;
              type string {
                length 0..50 ;
              }
            }
            leaf path-id {
              description 'The path-id.'
                          ;
              type uint32 ;
            }
            leaf best {
              status obsolete {
                ncd:revise-date 2015-06-29 ;
              }
              description 'Mark for the best.'
                          ;
              type enumeration {
                enum false {
                  value 1 ;
                  description 'Not chosen as best route.'
                              ;
                }
                enum true {
                  value 2 ;
                  description 'Chosen as best route.'
                              ;
                }
              }
            }
            leaf origin {
              description 'Origin attribute.'
                          ;
              type enumeration {
                enum igp {
                  value 1 ;
                  description 'Networks are interior.'
                              ;
                }
                enum egp {
                  value 2 ;
                  description 'Networks learned via EGP.'
                              ;
                }
                enum incomplete {
                  value 3 ;
                  description Undetermined. ;
                }
              }
            }
            leaf as-path {
              description 'As path attribute.'
                          ;
              type ncd:string-with-blank {
                length 0..256 ;
              }
            }
            leaf nexthop {
              description 'Nexthop attribute.'
                          ;
              type string {
                length 0..46 ;
              }
            }
            leaf med {
              description 'MED attribute.'
                          ;
              type uint32 ;
            }
            leaf local-preference {
              description 'Local preference attribute.'
                          ;
              type uint32 ;
            }
            leaf atomic {
              description 'The atomic-aggregate attribute.'
                          ;
              type enumeration {
                enum no-select {
                  value 1 ;
                }
                enum select {
                  value 2 ;
                }
              }
            }
            leaf aggregator {
              description 'The aggregator attribute.'
                          ;
              type ncd:string-with-blank {
                length 0..28 ;
              }
            }
            leaf community {
              description 'The community attribute.'
                          ;
              type ncd:string-with-blank {
                length 0..256 ;
              }
            }
            leaf originator-id {
              description 'The originator-id attribute.'
                          ;
              type string {
                length 0..16 ;
              }
            }
            leaf cluster-list {
              description 'The cluster-list attribute.'
                          ;
              type ncd:string-with-blank {
                length 0..256 ;
              }
            }
            leaf as4-path {
              description 'The as4-path attribute.'
                          ;
              type ncd:string-with-blank ;
            }
            leaf as4-aggregator {
              description 'The as4-aggregator attribute.'
                          ;
              type ncd:string-with-blank ;
            }
            leaf label-in {
              status obsolete {
                ncd:revise-date 2015-07-15 ;
              }
              description 'In label.'
                          ;
              type uint32 ;
            }
            leaf label-out {
              description 'Sent label.'
                          ;
              type uint32 ;
            }
            leaf unknown {
              description 'Unknown attribute.'
                          ;
              type ncd:string-with-blank {
                length 0..256 ;
              }
            }
            ncd:select 'vrf to-peer prefix path-id'
                       ;
            ncd:select 'to-peer prefix path-id'
                       ;
          }
        }
        container vpnv4-unicast {
          description 'Show VPNv4 unicast route information.'
                      ;
          list route {
            description 'VPNv4 unicast route.'
                        ;
            key 'to-peer rd prefix path-id'
                ;
            leaf to-peer {
              description 'Neighbor remote address that the route is sent to.'
                          ;
              type string {
                length 0..46 ;
              }
            }
            leaf rd {
              description 'Specify route distinguisher.'
                          ;
              type string {
                length 0..22 ;
              }
            }
            leaf prefix {
              description 'Network address and mask.'
                          ;
              type string {
                length 0..50 ;
              }
            }
            leaf path-id {
              description 'The path-id.'
                          ;
              type uint32 ;
            }
            leaf best {
              status obsolete {
                ncd:revise-date 2015-06-29 ;
              }
              description 'Mark for the best.'
                          ;
              type enumeration {
                enum false {
                  value 1 ;
                  description 'Not chosen as best route.'
                              ;
                }
                enum true {
                  value 2 ;
                  description 'Chosen as best route.'
                              ;
                }
              }
            }
            leaf origin {
              description 'Origin attribute.'
                          ;
              type enumeration {
                enum igp {
                  value 1 ;
                  description 'Networks are interior.'
                              ;
                }
                enum egp {
                  value 2 ;
                  description 'Networks learned via EGP.'
                              ;
                }
                enum incomplete {
                  value 3 ;
                  description Undetermined. ;
                }
              }
            }
            leaf as-path {
              description 'As path attribute.'
                          ;
              type ncd:string-with-blank {
                length 0..256 ;
              }
            }
            leaf nexthop {
              description 'Nexthop attribute.'
                          ;
              type string {
                length 0..46 ;
              }
            }
            leaf med {
              description 'MED attribute.'
                          ;
              type uint32 ;
            }
            leaf local-preference {
              description 'Local preference attribute.'
                          ;
              type uint32 ;
            }
            leaf atomic {
              description 'The atomic-aggregate attribute.'
                          ;
              type enumeration {
                enum no-select {
                  value 1 ;
                }
                enum select {
                  value 2 ;
                }
              }
            }
            leaf aggregator {
              description 'The aggregator attribute.'
                          ;
              type ncd:string-with-blank {
                length 0..28 ;
              }
            }
            leaf community {
              description 'The community attribute.'
                          ;
              type ncd:string-with-blank {
                length 0..256 ;
              }
            }
            leaf originator-id {
              description 'The originator-id attribute.'
                          ;
              type string {
                length 0..16 ;
              }
            }
            leaf cluster-list {
              description 'The cluster-list attribute.'
                          ;
              type ncd:string-with-blank {
                length 0..256 ;
              }
            }
            leaf as4-path {
              description 'The as4-path attribute.'
                          ;
              type ncd:string-with-blank ;
            }
            leaf as4-aggregator {
              description 'The as4-aggregator attribute.'
                          ;
              type ncd:string-with-blank ;
            }
            leaf ext-community {
              description 'The extended communtiy attribute.'
                          ;
              type ncd:string-with-blank ;
            }
            leaf label-in {
              status obsolete {
                ncd:revise-date 2015-07-15 ;
              }
              description 'In label.'
                          ;
              type uint32 ;
            }
            leaf label-out {
              description 'Sent label.'
                          ;
              type uint32 ;
            }
            leaf unknown {
              description 'Unknown attribute.'
                          ;
              type ncd:string-with-blank {
                length 0..256 ;
              }
            }
            ncd:select 'to-peer rd prefix path-id'
                       ;
          }
        }
        container ipv6-unicast {
          description 'Show IPv6 unicast route information.'
                      ;
          list route {
            description 'IPv6 unicast route.'
                        ;
            key 'vrf to-peer prefix path-id'
                ;
            leaf vrf {
              description 'VPN Routing/Forwarding instance name.'
                          ;
              type string {
                length 0..32 ;
              }
            }
            leaf to-peer {
              description 'Neighbor remote address that the route is sent to.'
                          ;
              type string {
                length 0..46 ;
              }
            }
            leaf prefix {
              description 'Network address and mask.'
                          ;
              type string {
                length 0..50 ;
              }
            }
            leaf path-id {
              description 'The path-id.'
                          ;
              type uint32 ;
            }
            leaf best {
              status obsolete {
                ncd:revise-date 2015-06-29 ;
              }
              description 'Mark for the best.'
                          ;
              type enumeration {
                enum false {
                  value 1 ;
                  description 'Not chosen as best route.'
                              ;
                }
                enum true {
                  value 2 ;
                  description 'Chosen as best route.'
                              ;
                }
              }
            }
            leaf origin {
              description 'Origin attribute.'
                          ;
              type enumeration {
                enum igp {
                  value 1 ;
                  description 'Networks are interior.'
                              ;
                }
                enum egp {
                  value 2 ;
                  description 'Networks learned via EGP.'
                              ;
                }
                enum incomplete {
                  value 3 ;
                  description Undetermined. ;
                }
              }
            }
            leaf as-path {
              description 'As path attribute.'
                          ;
              type ncd:string-with-blank {
                length 0..256 ;
              }
            }
            leaf nexthop {
              description 'Nexthop attribute.'
                          ;
              type string {
                length 0..46 ;
              }
            }
            leaf med {
              description 'MED attribute.'
                          ;
              type uint32 ;
            }
            leaf local-preference {
              description 'Local preference attribute.'
                          ;
              type uint32 ;
            }
            leaf atomic {
              description 'The atomic-aggregate attribute.'
                          ;
              type enumeration {
                enum no-select {
                  value 1 ;
                }
                enum select {
                  value 2 ;
                }
              }
            }
            leaf aggregator {
              description 'The aggregator attribute.'
                          ;
              type ncd:string-with-blank {
                length 0..28 ;
              }
            }
            leaf community {
              description 'The community attribute.'
                          ;
              type ncd:string-with-blank {
                length 0..256 ;
              }
            }
            leaf originator-id {
              description 'The originator-id attribute.'
                          ;
              type string {
                length 0..16 ;
              }
            }
            leaf cluster-list {
              description 'The cluster-list attribute.'
                          ;
              type ncd:string-with-blank {
                length 0..256 ;
              }
            }
            leaf as4-path {
              description 'The as4-path attribute.'
                          ;
              type ncd:string-with-blank ;
            }
            leaf as4-aggregator {
              description 'The as4-aggregator attribute.'
                          ;
              type ncd:string-with-blank ;
            }
            leaf label-in {
              status obsolete {
                ncd:revise-date 2015-07-15 ;
              }
              description 'In label.'
                          ;
              type uint32 ;
            }
            leaf label-out {
              description 'Sent label.'
                          ;
              type uint32 ;
            }
            leaf unknown {
              description 'Unknown attribute.'
                          ;
              type ncd:string-with-blank {
                length 0..256 ;
              }
            }
            ncd:select 'vrf to-peer prefix path-id'
                       ;
            ncd:select 'to-peer prefix path-id'
                       ;
          }
        }
        container vpnv6-unicast {
          description 'Show VPNv6 unicast route information.'
                      ;
          list route {
            description 'VPNv6 unicast route.'
                        ;
            key 'to-peer rd prefix path-id'
                ;
            leaf to-peer {
              description 'Neighbor remote address that the route is sent to.'
                          ;
              type string {
                length 0..46 ;
              }
            }
            leaf rd {
              description 'Specify route distinguisher.'
                          ;
              type string {
                length 0..22 ;
              }
            }
            leaf prefix {
              description 'Network address and mask.'
                          ;
              type string {
                length 0..50 ;
              }
            }
            leaf path-id {
              description 'The path-id.'
                          ;
              type uint32 ;
            }
            leaf best {
              status obsolete {
                ncd:revise-date 2015-06-29 ;
              }
              description 'Mark for the best.'
                          ;
              type enumeration {
                enum false {
                  value 1 ;
                  description 'Not chosen as best route.'
                              ;
                }
                enum true {
                  value 2 ;
                  description 'Chosen as best route.'
                              ;
                }
              }
            }
            leaf origin {
              description 'Origin attribute.'
                          ;
              type enumeration {
                enum igp {
                  value 1 ;
                  description 'Networks are interior.'
                              ;
                }
                enum egp {
                  value 2 ;
                  description 'Networks learned via EGP.'
                              ;
                }
                enum incomplete {
                  value 3 ;
                  description Undetermined. ;
                }
              }
            }
            leaf as-path {
              description 'As path attribute.'
                          ;
              type ncd:string-with-blank {
                length 0..256 ;
              }
            }
            leaf nexthop {
              description 'Nexthop attribute.'
                          ;
              type string {
                length 0..46 ;
              }
            }
            leaf med {
              description 'MED attribute.'
                          ;
              type uint32 ;
            }
            leaf local-preference {
              description 'Local preference attribute.'
                          ;
              type uint32 ;
            }
            leaf atomic {
              description 'The atomic-aggregate attribute.'
                          ;
              type enumeration {
                enum no-select {
                  value 1 ;
                }
                enum select {
                  value 2 ;
                }
              }
            }
            leaf aggregator {
              description 'The aggregator attribute.'
                          ;
              type ncd:string-with-blank {
                length 0..28 ;
              }
            }
            leaf community {
              description 'The community attribute.'
                          ;
              type ncd:string-with-blank {
                length 0..256 ;
              }
            }
            leaf originator-id {
              description 'The originator-id attribute.'
                          ;
              type string {
                length 0..16 ;
              }
            }
            leaf cluster-list {
              description 'The cluster-list attribute.'
                          ;
              type ncd:string-with-blank {
                length 0..256 ;
              }
            }
            leaf as4-path {
              description 'The as4-path attribute.'
                          ;
              type ncd:string-with-blank ;
            }
            leaf as4-aggregator {
              description 'The as4-aggregator attribute.'
                          ;
              type ncd:string-with-blank ;
            }
            leaf ext-community {
              description 'The extended communtiy attribute.'
                          ;
              type ncd:string-with-blank ;
            }
            leaf label-in {
              status obsolete {
                ncd:revise-date 2015-07-15 ;
              }
              description 'In label.'
                          ;
              type uint32 ;
            }
            leaf label-out {
              description 'Sent label.'
                          ;
              type uint32 ;
            }
            leaf unknown {
              description 'Unknown attribute.'
                          ;
              type ncd:string-with-blank {
                length 0..256 ;
              }
            }
            ncd:select 'to-peer rd prefix path-id'
                       ;
          }
        }
      }
      container all-routes {
        description 'Show route information.'
                    ;
        container ipv4-unicast {
          description 'Show IPv4 unicast route information.'
                      ;
          list route {
            description 'IPv4 unicast route.'
                        ;
            key 'local-as vrf prefix sequence'
                ;
            leaf local-as {
              description 'the Autonomy system number of BGP in local equipment.'
                          ;
              type ncd:asn-dot ;
            }
            leaf vrf {
              description 'VPN Routing/Forwarding instance name.'
                          ;
              type string {
                length 0..32 ;
              }
            }
            leaf prefix {
              description 'Network address and mask.'
                          ;
              type string {
                length 0..50 ;
              }
            }
            leaf sequence {
              description 'The rib sequence.'
                          ;
              type uint32 ;
            }
            leaf from-peer {
              description 'Neighbor remote address that the route is received f'
                        + 'rom.'
                          ;
              type string {
                length 0..46 ;
              }
            }
            leaf path-id {
              description 'The path-id.'
                          ;
              type uint32 ;
            }
            leaf best {
              description 'Mark for the best.'
                          ;
              type enumeration {
                enum false {
                  value 1 ;
                  description 'Not chosen as best route.'
                              ;
                }
                enum true {
                  value 2 ;
                  description 'Chosen as best route.'
                              ;
                }
              }
            }
            leaf origin {
              description 'Origin attribute.'
                          ;
              type enumeration {
                enum igp {
                  value 1 ;
                  description 'Networks are interior.'
                              ;
                }
                enum egp {
                  value 2 ;
                  description 'Networks learned via EGP.'
                              ;
                }
                enum incomplete {
                  value 3 ;
                  description Undetermined. ;
                }
              }
            }
            leaf as-path {
              description 'As path attribute.'
                          ;
              type ncd:string-with-blank {
                length 0..256 ;
              }
            }
            leaf nexthop {
              description 'Nexthop attribute.'
                          ;
              type string {
                length 0..46 ;
              }
            }
            leaf med {
              description 'MED attribute.'
                          ;
              type uint32 ;
            }
            leaf local-preference {
              description 'Local preference attribute.'
                          ;
              type uint32 ;
            }
            leaf atomic {
              description 'The atomic-aggregate attribute.'
                          ;
              type enumeration {
                enum no-select {
                  value 1 ;
                }
                enum select {
                  value 2 ;
                }
              }
            }
            leaf aggregator {
              description 'The aggregator attribute.'
                          ;
              type ncd:string-with-blank {
                length 0..28 ;
              }
            }
            leaf community {
              description 'The community attribute.'
                          ;
              type ncd:string-with-blank {
                length 0..256 ;
              }
            }
            leaf originator-id {
              description 'The originator-id attribute.'
                          ;
              type string {
                length 0..16 ;
              }
            }
            leaf cluster-list {
              description 'The cluster-list attribute.'
                          ;
              type ncd:string-with-blank {
                length 0..256 ;
              }
            }
            leaf label-in {
              description 'In label.'
                          ;
              type uint32 ;
            }
            leaf label-out {
              description 'Out label.'
                          ;
              type uint32 ;
            }
            leaf unknown {
              description 'Unknown attribute.'
                          ;
              type ncd:string-with-blank {
                length 0..256 ;
              }
            }
            ncd:select 'local-as prefix sequence'
                       ;
            ncd:select 'local-as vrf prefix sequence'
                       ;
          }
        }
        container vpnv4-unicast {
          description 'Show VPNv4 unicast route information.'
                      ;
          list route {
            description 'VPNv4 unicast route.'
                        ;
            key 'local-as rd prefix sequence'
                ;
            leaf local-as {
              description 'the Autonomy system number of BGP in local equipment.'
                          ;
              type ncd:asn-dot ;
            }
            leaf rd {
              description 'Specify route distinguisher.'
                          ;
              type string {
                length 0..22 ;
              }
            }
            leaf prefix {
              description 'Network address and mask.'
                          ;
              type string {
                length 0..50 ;
              }
            }
            leaf sequence {
              description 'The route sequence.'
                          ;
              type uint32 ;
            }
            leaf from-peer {
              description 'Neighbor remote address that the route is received f'
                        + 'rom.'
                          ;
              type string {
                length 0..46 ;
              }
            }
            leaf path-id {
              description 'The path-id.'
                          ;
              type uint32 ;
            }
            leaf best {
              description 'Mark for the best.'
                          ;
              type enumeration {
                enum false {
                  value 1 ;
                  description 'Not chosen as best route.'
                              ;
                }
                enum true {
                  value 2 ;
                  description 'Chosen as best route.'
                              ;
                }
              }
            }
            leaf origin {
              description 'Origin attribute.'
                          ;
              type enumeration {
                enum igp {
                  value 1 ;
                  description 'Networks are interior.'
                              ;
                }
                enum egp {
                  value 2 ;
                  description 'Networks learned via EGP.'
                              ;
                }
                enum incomplete {
                  value 3 ;
                  description Undetermined. ;
                }
              }
            }
            leaf as-path {
              description 'As path attribute.'
                          ;
              type ncd:string-with-blank {
                length 0..256 ;
              }
            }
            leaf nexthop {
              description 'Nexthop attribute.'
                          ;
              type string {
                length 0..46 ;
              }
            }
            leaf med {
              description 'MED attribute.'
                          ;
              type uint32 ;
            }
            leaf local-preference {
              description 'Local preference attribute.'
                          ;
              type uint32 ;
            }
            leaf atomic {
              description 'The atomic-aggregate attribute.'
                          ;
              type enumeration {
                enum no-select {
                  value 1 ;
                }
                enum select {
                  value 2 ;
                }
              }
            }
            leaf aggregator {
              description 'The aggregator attribute.'
                          ;
              type ncd:string-with-blank {
                length 0..28 ;
              }
            }
            leaf community {
              description 'The community attribute.'
                          ;
              type ncd:string-with-blank {
                length 0..256 ;
              }
            }
            leaf originator-id {
              description 'The originator-id attribute.'
                          ;
              type string {
                length 0..16 ;
              }
            }
            leaf cluster-list {
              description 'The cluster-list attribute.'
                          ;
              type ncd:string-with-blank {
                length 0..256 ;
              }
            }
            leaf ext-community {
              description 'The extended communtiy attribute.'
                          ;
              type ncd:string-with-blank {
                length 0..256 ;
              }
            }
            leaf label-in {
              description 'In label.'
                          ;
              type uint32 ;
            }
            leaf label-out {
              description 'Out label.'
                          ;
              type uint32 ;
            }
            leaf unknown {
              description 'Unknown attribute.'
                          ;
              type ncd:string-with-blank {
                length 0..256 ;
              }
            }
            ncd:select 'local-as rd prefix sequence'
                       ;
          }
        }
        container ipv6-unicast {
          description 'Show IPv6 unicast route information.'
                      ;
          list route {
            description 'IPv6 unicast route.'
                        ;
            key 'local-as vrf prefix sequence'
                ;
            leaf local-as {
              description 'the Autonomy system number of BGP in local equipment.'
                          ;
              type ncd:asn-dot ;
            }
            leaf vrf {
              description 'VPN Routing/Forwarding instance name.'
                          ;
              type string {
                length 0..32 ;
              }
            }
            leaf prefix {
              description 'Network address and mask.'
                          ;
              type string {
                length 0..50 ;
              }
            }
            leaf sequence {
              description 'The route sequence.'
                          ;
              type uint32 ;
            }
            leaf from-peer {
              description 'Neighbor remote address that the route is received f'
                        + 'rom.'
                          ;
              type string {
                length 0..46 ;
              }
            }
            leaf path-id {
              description 'The path-id.'
                          ;
              type uint32 ;
            }
            leaf best {
              description 'Mark for the best.'
                          ;
              type enumeration {
                enum false {
                  value 1 ;
                  description 'Not chosen as best route.'
                              ;
                }
                enum true {
                  value 2 ;
                  description 'Chosen as best route.'
                              ;
                }
              }
            }
            leaf origin {
              description 'Origin attribute.'
                          ;
              type enumeration {
                enum igp {
                  value 1 ;
                  description 'Networks are interior.'
                              ;
                }
                enum egp {
                  value 2 ;
                  description 'Networks learned via EGP.'
                              ;
                }
                enum incomplete {
                  value 3 ;
                  description Undetermined. ;
                }
              }
            }
            leaf as-path {
              description 'As path attribute.'
                          ;
              type ncd:string-with-blank {
                length 0..256 ;
              }
            }
            leaf nexthop {
              description 'Nexthop attribute.'
                          ;
              type string {
                length 0..46 ;
              }
            }
            leaf med {
              description 'MED attribute.'
                          ;
              type uint32 ;
            }
            leaf local-preference {
              description 'Local preference attribute.'
                          ;
              type uint32 ;
            }
            leaf atomic {
              description 'The atomic-aggregate attribute.'
                          ;
              type enumeration {
                enum no-select {
                  value 1 ;
                }
                enum select {
                  value 2 ;
                }
              }
            }
            leaf aggregator {
              description 'The aggregator attribute.'
                          ;
              type ncd:string-with-blank {
                length 0..28 ;
              }
            }
            leaf community {
              description 'The community attribute.'
                          ;
              type ncd:string-with-blank {
                length 0..256 ;
              }
            }
            leaf originator-id {
              description 'The originator-id attribute.'
                          ;
              type string {
                length 0..16 ;
              }
            }
            leaf cluster-list {
              description 'The cluster-list attribute.'
                          ;
              type ncd:string-with-blank {
                length 0..256 ;
              }
            }
            leaf label-in {
              description 'In label.'
                          ;
              type uint32 ;
            }
            leaf label-out {
              description 'Out label.'
                          ;
              type uint32 ;
            }
            leaf unknown {
              description 'Unknown attribute.'
                          ;
              type ncd:string-with-blank {
                length 0..256 ;
              }
            }
            ncd:select 'local-as prefix sequence'
                       ;
            ncd:select 'local-as vrf prefix sequence'
                       ;
          }
        }
        container vpnv6-unicast {
          description 'Show VPNv6 unicast route information.'
                      ;
          list route {
            description 'VPNv6 unicast route.'
                        ;
            key 'local-as rd prefix sequence'
                ;
            leaf local-as {
              description 'the Autonomy system number of BGP in local equipment.'
                          ;
              type ncd:asn-dot ;
            }
            leaf rd {
              description 'Specify route distinguisher.'
                          ;
              type string {
                length 0..22 ;
              }
            }
            leaf prefix {
              description 'Network address and mask.'
                          ;
              type string {
                length 0..50 ;
              }
            }
            leaf sequence {
              description 'The route sequence.'
                          ;
              type uint32 ;
            }
            leaf from-peer {
              description 'Neighbor remote address that the route is received f'
                        + 'rom.'
                          ;
              type string {
                length 0..46 ;
              }
            }
            leaf path-id {
              description 'The path-id.'
                          ;
              type uint32 ;
            }
            leaf best {
              description 'Mark for the best.'
                          ;
              type enumeration {
                enum false {
                  value 1 ;
                  description 'Not chosen as best route.'
                              ;
                }
                enum true {
                  value 2 ;
                  description 'Chosen as best route.'
                              ;
                }
              }
            }
            leaf origin {
              description 'Origin attribute.'
                          ;
              type enumeration {
                enum igp {
                  value 1 ;
                  description 'Networks are interior.'
                              ;
                }
                enum egp {
                  value 2 ;
                  description 'Networks learned via EGP.'
                              ;
                }
                enum incomplete {
                  value 3 ;
                  description Undetermined. ;
                }
              }
            }
            leaf as-path {
              description 'As path attribute.'
                          ;
              type ncd:string-with-blank {
                length 0..256 ;
              }
            }
            leaf nexthop {
              description 'Nexthop attribute.'
                          ;
              type string {
                length 0..46 ;
              }
            }
            leaf med {
              description 'MED attribute.'
                          ;
              type uint32 ;
            }
            leaf local-preference {
              description 'Local preference attribute.'
                          ;
              type uint32 ;
            }
            leaf atomic {
              description 'The atomic-aggregate attribute.'
                          ;
              type enumeration {
                enum no-select {
                  value 1 ;
                }
                enum select {
                  value 2 ;
                }
              }
            }
            leaf aggregator {
              description 'The aggregator attribute.'
                          ;
              type ncd:string-with-blank {
                length 0..28 ;
              }
            }
            leaf community {
              description 'The community attribute.'
                          ;
              type ncd:string-with-blank {
                length 0..256 ;
              }
            }
            leaf originator-id {
              description 'The originator-id attribute.'
                          ;
              type string {
                length 0..16 ;
              }
            }
            leaf cluster-list {
              description 'The cluster-list attribute.'
                          ;
              type ncd:string-with-blank {
                length 0..256 ;
              }
            }
            leaf ext-community {
              description 'The extended communtiy attribute.'
                          ;
              type ncd:string-with-blank ;
            }
            leaf label-in {
              description 'In label.'
                          ;
              type uint32 ;
            }
            leaf label-out {
              description 'Out label.'
                          ;
              type uint32 ;
            }
            leaf unknown {
              description 'Unknown attribute.'
                          ;
              type ncd:string-with-blank {
                length 0..256 ;
              }
            }
            ncd:select 'local-as rd prefix sequence'
                       ;
          }
        }
        container l2vpn-evpn {
          description 'Show EVPN route information.'
                      ;
          container evpn-vpls {
            description 'Show EVPN route information of L2VPN VPLS instances.'
                        ;
            container route {
              description 'EVPN route.'
                          ;
              list RT-1 {
                description 'Ethernet Auto-Discovery (A-D) route.'
                            ;
                key 'name eti esi sequence'
                    ;
                leaf name {
                  description 'Name of instance.'
                              ;
                  type string {
                    length 1..32 ;
                  }
                }
                leaf eti {
                  description 'Ethernet Tag ID.'
                              ;
                  type uint32 ;
                }
                leaf esi {
                  description 'Ethernet Segment Identifier(ESI).'
                              ;
                  type string {
                    length 0..20 ;
                  }
                }
                leaf sequence {
                  description 'The route sequence.'
                              ;
                  type uint32 ;
                }
                leaf local-as {
                  description 'the Autonomy system number of BGP in local equip'
                            + 'ment.'
                              ;
                  type ncd:asn-dot ;
                }
                leaf from-peer {
                  description 'Neighbor remote address that the route is receiv'
                            + 'ed from.'
                              ;
                  type string {
                    length 0..46 ;
                  }
                }
                leaf path-id {
                  description 'The path-id.'
                              ;
                  type uint32 ;
                }
                leaf best {
                  description 'Mark for the best.'
                              ;
                  type enumeration {
                    enum false {
                      value 1 ;
                      description 'Not chosen as best route.'
                                  ;
                    }
                    enum true {
                      value 2 ;
                      description 'Chosen as best route.'
                                  ;
                    }
                  }
                }
                leaf origin {
                  description 'Origin attribute.'
                              ;
                  type enumeration {
                    enum igp {
                      value 1 ;
                      description 'Networks are interior.'
                                  ;
                    }
                    enum egp {
                      value 2 ;
                      description 'Networks learned via EGP.'
                                  ;
                    }
                    enum incomplete {
                      value 3 ;
                      description Undetermined. ;
                    }
                  }
                }
                leaf as-path {
                  description 'As path attribute.'
                              ;
                  type ncd:string-with-blank {
                    length 0..256 ;
                  }
                }
                leaf nexthop {
                  description 'Nexthop attribute.'
                              ;
                  type string {
                    length 0..46 ;
                  }
                }
                leaf med {
                  description 'MED attribute.'
                              ;
                  type uint32 ;
                }
                leaf local-preference {
                  description 'Local preference attribute.'
                              ;
                  type uint32 ;
                }
                leaf atomic {
                  description 'The atomic-aggregate attribute.'
                              ;
                  type enumeration {
                    enum no-select {
                      value 1 ;
                    }
                    enum select {
                      value 2 ;
                    }
                  }
                }
                leaf aggregator {
                  description 'The aggregator attribute.'
                              ;
                  type ncd:string-with-blank {
                    length 0..28 ;
                  }
                }
                leaf community {
                  description 'The community attribute.'
                              ;
                  type ncd:string-with-blank {
                    length 0..256 ;
                  }
                }
                leaf originator-id {
                  description 'The originator-id attribute.'
                              ;
                  type string {
                    length 0..16 ;
                  }
                }
                leaf cluster-list {
                  description 'The cluster-list attribute.'
                              ;
                  type ncd:string-with-blank {
                    length 0..256 ;
                  }
                }
                leaf out-label1 {
                  description 'Out label1.'
                              ;
                  type uint32 ;
                }
                leaf out-label2 {
                  description 'Out label2.'
                              ;
                  type uint32 ;
                }
                leaf gw-ip {
                  description 'Gateway IP Address.'
                              ;
                  type string ;
                }
                leaf rt {
                  description 'Route Target (RT) attributes.'
                              ;
                  type ncd:string-with-blank {
                    length 0..256 ;
                  }
                }
                leaf routers-mac {
                  description "Router's MAC Extended Community."
                              ;
                  type ncd:mac-address ;
                }
                leaf unknown {
                  description 'Unknown attribute.'
                              ;
                  type ncd:string-with-blank {
                    length 0..256 ;
                  }
                }
                ncd:select name ;
                ncd:select 'name eti esi'
                           ;
                ncd:select 'name eti esi sequence'
                           ;
              }
              list RT-2 {
                description 'MAC/IP advertisement route.'
                            ;
                key 'name eti mac-addr ip-addr sequence'
                    ;
                leaf name {
                  description 'Name of instance.'
                              ;
                  type string {
                    length 1..32 ;
                  }
                }
                leaf eti {
                  description 'Ethernet Tag ID.'
                              ;
                  type uint32 ;
                }
                leaf mac-addr {
                  description 'MAC Address.'
                              ;
                  type ncd:mac-address ;
                }
                leaf ip-addr {
                  description 'IPv4 address,IPv6 address or null.'
                              ;
                  type string {
                    length 0..50 ;
                  }
                }
                leaf sequence {
                  description 'The route sequence.'
                              ;
                  type uint32 ;
                }
                leaf local-as {
                  description 'the Autonomy system number of BGP in local equip'
                            + 'ment.'
                              ;
                  type ncd:asn-dot ;
                }
                leaf from-peer {
                  description 'Neighbor remote address that the route is receiv'
                            + 'ed from.'
                              ;
                  type string {
                    length 0..46 ;
                  }
                }
                leaf path-id {
                  description 'The path-id.'
                              ;
                  type uint32 ;
                }
                leaf best {
                  description 'Mark for the best.'
                              ;
                  type enumeration {
                    enum false {
                      value 1 ;
                      description 'Not chosen as best route.'
                                  ;
                    }
                    enum true {
                      value 2 ;
                      description 'Chosen as best route.'
                                  ;
                    }
                  }
                }
                leaf origin {
                  description 'Origin attribute.'
                              ;
                  type enumeration {
                    enum igp {
                      value 1 ;
                      description 'Networks are interior.'
                                  ;
                    }
                    enum egp {
                      value 2 ;
                      description 'Networks learned via EGP.'
                                  ;
                    }
                    enum incomplete {
                      value 3 ;
                      description Undetermined. ;
                    }
                  }
                }
                leaf as-path {
                  description 'As path attribute.'
                              ;
                  type ncd:string-with-blank {
                    length 0..256 ;
                  }
                }
                leaf nexthop {
                  description 'Nexthop attribute.'
                              ;
                  type string {
                    length 0..46 ;
                  }
                }
                leaf med {
                  description 'MED attribute.'
                              ;
                  type uint32 ;
                }
                leaf local-preference {
                  description 'Local preference attribute.'
                              ;
                  type uint32 ;
                }
                leaf atomic {
                  description 'The atomic-aggregate attribute.'
                              ;
                  type enumeration {
                    enum no-select {
                      value 1 ;
                    }
                    enum select {
                      value 2 ;
                    }
                  }
                }
                leaf aggregator {
                  description 'The aggregator attribute.'
                              ;
                  type ncd:string-with-blank {
                    length 0..28 ;
                  }
                }
                leaf community {
                  description 'The community attribute.'
                              ;
                  type ncd:string-with-blank {
                    length 0..256 ;
                  }
                }
                leaf originator-id {
                  description 'The originator-id attribute.'
                              ;
                  type string {
                    length 0..16 ;
                  }
                }
                leaf cluster-list {
                  description 'The cluster-list attribute.'
                              ;
                  type ncd:string-with-blank {
                    length 0..256 ;
                  }
                }
                leaf out-label1 {
                  description 'Out label1.'
                              ;
                  type uint32 ;
                }
                leaf out-label2 {
                  description 'Out label2.'
                              ;
                  type uint32 ;
                }
                leaf gw-ip {
                  description 'Gateway IP Address.'
                              ;
                  type string ;
                }
                leaf rt {
                  description 'Route Target (RT) attributes.'
                              ;
                  type ncd:string-with-blank {
                    length 0..256 ;
                  }
                }
                leaf routers-mac {
                  description "Router's MAC Extended Community."
                              ;
                  type ncd:mac-address ;
                }
                leaf unknown {
                  description 'Unknown attribute.'
                              ;
                  type ncd:string-with-blank {
                    length 0..256 ;
                  }
                }
                ncd:select name ;
                ncd:select 'name eti mac-addr ip-addr'
                           ;
                ncd:select 'name eti mac-addr ip-addr sequence'
                           ;
              }
              list RT-3 {
                description 'Inclusive Multicast Route.'
                            ;
                key 'name eti origin-ip sequence'
                    ;
                leaf name {
                  description 'Name of instance.'
                              ;
                  type string {
                    length 1..32 ;
                  }
                }
                leaf eti {
                  description 'Ethernet Tag ID.'
                              ;
                  type uint32 ;
                }
                leaf origin-ip {
                  description "Originating Router's IP Address."
                              ;
                  type string {
                    length 0..50 ;
                  }
                }
                leaf sequence {
                  description 'The route sequence.'
                              ;
                  type uint32 ;
                }
                leaf local-as {
                  description 'the Autonomy system number of BGP in local equip'
                            + 'ment.'
                              ;
                  type ncd:asn-dot ;
                }
                leaf from-peer {
                  description 'Neighbor remote address that the route is receiv'
                            + 'ed from.'
                              ;
                  type string {
                    length 0..46 ;
                  }
                }
                leaf path-id {
                  description 'The path-id.'
                              ;
                  type uint32 ;
                }
                leaf best {
                  description 'Mark for the best.'
                              ;
                  type enumeration {
                    enum false {
                      value 1 ;
                      description 'Not chosen as best route.'
                                  ;
                    }
                    enum true {
                      value 2 ;
                      description 'Chosen as best route.'
                                  ;
                    }
                  }
                }
                leaf origin {
                  description 'Origin attribute.'
                              ;
                  type enumeration {
                    enum igp {
                      value 1 ;
                      description 'Networks are interior.'
                                  ;
                    }
                    enum egp {
                      value 2 ;
                      description 'Networks learned via EGP.'
                                  ;
                    }
                    enum incomplete {
                      value 3 ;
                      description Undetermined. ;
                    }
                  }
                }
                leaf as-path {
                  description 'As path attribute.'
                              ;
                  type ncd:string-with-blank {
                    length 0..256 ;
                  }
                }
                leaf nexthop {
                  description 'Nexthop attribute.'
                              ;
                  type string {
                    length 0..46 ;
                  }
                }
                leaf med {
                  description 'MED attribute.'
                              ;
                  type uint32 ;
                }
                leaf local-preference {
                  description 'Local preference attribute.'
                              ;
                  type uint32 ;
                }
                leaf atomic {
                  description 'The atomic-aggregate attribute.'
                              ;
                  type enumeration {
                    enum no-select {
                      value 1 ;
                    }
                    enum select {
                      value 2 ;
                    }
                  }
                }
                leaf aggregator {
                  description 'The aggregator attribute.'
                              ;
                  type ncd:string-with-blank {
                    length 0..28 ;
                  }
                }
                leaf community {
                  description 'The community attribute.'
                              ;
                  type ncd:string-with-blank {
                    length 0..256 ;
                  }
                }
                leaf originator-id {
                  description 'The originator-id attribute.'
                              ;
                  type string {
                    length 0..16 ;
                  }
                }
                leaf cluster-list {
                  description 'The cluster-list attribute.'
                              ;
                  type ncd:string-with-blank {
                    length 0..256 ;
                  }
                }
                leaf out-label1 {
                  description 'Out label1.'
                              ;
                  type uint32 ;
                }
                leaf out-label2 {
                  description 'Out label2.'
                              ;
                  type uint32 ;
                }
                leaf gw-ip {
                  description 'Gateway IP Address.'
                              ;
                  type string ;
                }
                leaf rt {
                  description 'Route Target (RT) attributes.'
                              ;
                  type ncd:string-with-blank {
                    length 0..256 ;
                  }
                }
                leaf routers-mac {
                  description "Router's MAC Extended Community."
                              ;
                  type ncd:mac-address ;
                }
                leaf unknown {
                  description 'Unknown attribute.'
                              ;
                  type ncd:string-with-blank {
                    length 0..256 ;
                  }
                }
                ncd:select name ;
                ncd:select 'name eti origin-ip'
                           ;
                ncd:select 'name eti origin-ip sequence'
                           ;
              }
            }
            container zenic-local-route {
              description 'EVPN route of zenic-local type.'
                          ;
              list RT-1 {
                description 'Ethernet Auto-Discovery (A-D) route.'
                            ;
                key 'name eti esi sequence'
                    ;
                leaf name {
                  description 'Name of instance.'
                              ;
                  type string {
                    length 1..32 ;
                  }
                }
                leaf eti {
                  description 'Ethernet Tag ID.'
                              ;
                  type uint32 ;
                }
                leaf esi {
                  description 'Ethernet Segment Identifier(ESI).'
                              ;
                  type string {
                    length 0..20 ;
                  }
                }
                leaf sequence {
                  description 'The route sequence.'
                              ;
                  type uint32 ;
                }
                leaf from-peer {
                  description 'Neighbor remote address that the route is receiv'
                            + 'ed from.'
                              ;
                  type string {
                    length 0..46 ;
                  }
                }
                leaf path-id {
                  description 'The path-id.'
                              ;
                  type uint32 ;
                }
                leaf best {
                  description 'Mark for the best.'
                              ;
                  type enumeration {
                    enum false {
                      value 1 ;
                      description 'Not chosen as best route.'
                                  ;
                    }
                    enum true {
                      value 2 ;
                      description 'Chosen as best route.'
                                  ;
                    }
                  }
                }
                leaf origin {
                  description 'Origin attribute.'
                              ;
                  type enumeration {
                    enum igp {
                      value 1 ;
                      description 'Networks are interior.'
                                  ;
                    }
                    enum egp {
                      value 2 ;
                      description 'Networks learned via EGP.'
                                  ;
                    }
                    enum incomplete {
                      value 3 ;
                      description Undetermined. ;
                    }
                  }
                }
                leaf as-path {
                  description 'As path attribute.'
                              ;
                  type ncd:string-with-blank {
                    length 0..256 ;
                  }
                }
                leaf nexthop {
                  description 'Nexthop attribute.'
                              ;
                  type string {
                    length 0..46 ;
                  }
                }
                leaf med {
                  description 'MED attribute.'
                              ;
                  type uint32 ;
                }
                leaf local-preference {
                  description 'Local preference attribute.'
                              ;
                  type uint32 ;
                }
                leaf atomic {
                  description 'The atomic-aggregate attribute.'
                              ;
                  type enumeration {
                    enum no-select {
                      value 1 ;
                    }
                    enum select {
                      value 2 ;
                    }
                  }
                }
                leaf aggregator {
                  description 'The aggregator attribute.'
                              ;
                  type ncd:string-with-blank {
                    length 0..28 ;
                  }
                }
                leaf community {
                  description 'The community attribute.'
                              ;
                  type ncd:string-with-blank {
                    length 0..256 ;
                  }
                }
                leaf originator-id {
                  description 'The originator-id attribute.'
                              ;
                  type string {
                    length 0..16 ;
                  }
                }
                leaf cluster-list {
                  description 'The cluster-list attribute.'
                              ;
                  type ncd:string-with-blank {
                    length 0..256 ;
                  }
                }
                leaf out-label1 {
                  description 'Out label1.'
                              ;
                  type uint32 ;
                }
                leaf out-label2 {
                  description 'Out label2.'
                              ;
                  type uint32 ;
                }
                leaf gw-ip {
                  description 'Gateway IP Address.'
                              ;
                  type string ;
                }
                leaf rt {
                  description 'Route Target (RT) attributes.'
                              ;
                  type ncd:string-with-blank {
                    length 0..256 ;
                  }
                }
                leaf routers-mac {
                  description "Router's MAC Extended Community."
                              ;
                  type ncd:mac-address ;
                }
                leaf unknown {
                  description 'Unknown attribute.'
                              ;
                  type ncd:string-with-blank {
                    length 0..256 ;
                  }
                }
                ncd:select name ;
                ncd:select 'name eti esi'
                           ;
                ncd:select 'name eti esi sequence'
                           ;
              }
              list RT-2 {
                description 'MAC/IP advertisement route.'
                            ;
                key 'name eti mac-addr ip-addr sequence'
                    ;
                leaf name {
                  description 'Name of instance.'
                              ;
                  type string {
                    length 1..32 ;
                  }
                }
                leaf eti {
                  description 'Ethernet Tag ID.'
                              ;
                  type uint32 ;
                }
                leaf mac-addr {
                  description 'MAC Address.'
                              ;
                  type ncd:mac-address ;
                }
                leaf ip-addr {
                  description 'IPv4 address,IPv6 address or null.'
                              ;
                  type string {
                    length 0..50 ;
                  }
                }
                leaf sequence {
                  description 'The route sequence.'
                              ;
                  type uint32 ;
                }
                leaf from-peer {
                  description 'Neighbor remote address that the route is receiv'
                            + 'ed from.'
                              ;
                  type string {
                    length 0..46 ;
                  }
                }
                leaf path-id {
                  description 'The path-id.'
                              ;
                  type uint32 ;
                }
                leaf best {
                  description 'Mark for the best.'
                              ;
                  type enumeration {
                    enum false {
                      value 1 ;
                      description 'Not chosen as best route.'
                                  ;
                    }
                    enum true {
                      value 2 ;
                      description 'Chosen as best route.'
                                  ;
                    }
                  }
                }
                leaf origin {
                  description 'Origin attribute.'
                              ;
                  type enumeration {
                    enum igp {
                      value 1 ;
                      description 'Networks are interior.'
                                  ;
                    }
                    enum egp {
                      value 2 ;
                      description 'Networks learned via EGP.'
                                  ;
                    }
                    enum incomplete {
                      value 3 ;
                      description Undetermined. ;
                    }
                  }
                }
                leaf as-path {
                  description 'As path attribute.'
                              ;
                  type ncd:string-with-blank {
                    length 0..256 ;
                  }
                }
                leaf nexthop {
                  description 'Nexthop attribute.'
                              ;
                  type string {
                    length 0..46 ;
                  }
                }
                leaf med {
                  description 'MED attribute.'
                              ;
                  type uint32 ;
                }
                leaf local-preference {
                  description 'Local preference attribute.'
                              ;
                  type uint32 ;
                }
                leaf atomic {
                  description 'The atomic-aggregate attribute.'
                              ;
                  type enumeration {
                    enum no-select {
                      value 1 ;
                    }
                    enum select {
                      value 2 ;
                    }
                  }
                }
                leaf aggregator {
                  description 'The aggregator attribute.'
                              ;
                  type ncd:string-with-blank {
                    length 0..28 ;
                  }
                }
                leaf community {
                  description 'The community attribute.'
                              ;
                  type ncd:string-with-blank {
                    length 0..256 ;
                  }
                }
                leaf originator-id {
                  description 'The originator-id attribute.'
                              ;
                  type string {
                    length 0..16 ;
                  }
                }
                leaf cluster-list {
                  description 'The cluster-list attribute.'
                              ;
                  type ncd:string-with-blank {
                    length 0..256 ;
                  }
                }
                leaf out-label1 {
                  description 'Out label1.'
                              ;
                  type uint32 ;
                }
                leaf out-label2 {
                  description 'Out label2.'
                              ;
                  type uint32 ;
                }
                leaf gw-ip {
                  description 'Gateway IP Address.'
                              ;
                  type string ;
                }
                leaf rt {
                  description 'Route Target (RT) attributes.'
                              ;
                  type ncd:string-with-blank {
                    length 0..256 ;
                  }
                }
                leaf routers-mac {
                  description "Router's MAC Extended Community."
                              ;
                  type ncd:mac-address ;
                }
                leaf unknown {
                  description 'Unknown attribute.'
                              ;
                  type ncd:string-with-blank {
                    length 0..256 ;
                  }
                }
                ncd:select name ;
                ncd:select 'name eti mac-addr ip-addr'
                           ;
                ncd:select 'name eti mac-addr ip-addr sequence'
                           ;
              }
              list RT-3 {
                description 'Inclusive Multicast Route.'
                            ;
                key 'name eti origin-ip sequence'
                    ;
                leaf name {
                  description 'Name of instance.'
                              ;
                  type string {
                    length 1..32 ;
                  }
                }
                leaf eti {
                  description 'Ethernet Tag ID.'
                              ;
                  type uint32 ;
                }
                leaf origin-ip {
                  description "Originating Router's IP Address."
                              ;
                  type string {
                    length 0..50 ;
                  }
                }
                leaf sequence {
                  description 'The route sequence.'
                              ;
                  type uint32 ;
                }
                leaf from-peer {
                  description 'Neighbor remote address that the route is receiv'
                            + 'ed from.'
                              ;
                  type string {
                    length 0..46 ;
                  }
                }
                leaf path-id {
                  description 'The path-id.'
                              ;
                  type uint32 ;
                }
                leaf best {
                  description 'Mark for the best.'
                              ;
                  type enumeration {
                    enum false {
                      value 1 ;
                      description 'Not chosen as best route.'
                                  ;
                    }
                    enum true {
                      value 2 ;
                      description 'Chosen as best route.'
                                  ;
                    }
                  }
                }
                leaf origin {
                  description 'Origin attribute.'
                              ;
                  type enumeration {
                    enum igp {
                      value 1 ;
                      description 'Networks are interior.'
                                  ;
                    }
                    enum egp {
                      value 2 ;
                      description 'Networks learned via EGP.'
                                  ;
                    }
                    enum incomplete {
                      value 3 ;
                      description Undetermined. ;
                    }
                  }
                }
                leaf as-path {
                  description 'As path attribute.'
                              ;
                  type ncd:string-with-blank {
                    length 0..256 ;
                  }
                }
                leaf nexthop {
                  description 'Nexthop attribute.'
                              ;
                  type string {
                    length 0..46 ;
                  }
                }
                leaf med {
                  description 'MED attribute.'
                              ;
                  type uint32 ;
                }
                leaf local-preference {
                  description 'Local preference attribute.'
                              ;
                  type uint32 ;
                }
                leaf atomic {
                  description 'The atomic-aggregate attribute.'
                              ;
                  type enumeration {
                    enum no-select {
                      value 1 ;
                    }
                    enum select {
                      value 2 ;
                    }
                  }
                }
                leaf aggregator {
                  description 'The aggregator attribute.'
                              ;
                  type ncd:string-with-blank {
                    length 0..28 ;
                  }
                }
                leaf community {
                  description 'The community attribute.'
                              ;
                  type ncd:string-with-blank {
                    length 0..256 ;
                  }
                }
                leaf originator-id {
                  description 'The originator-id attribute.'
                              ;
                  type string {
                    length 0..16 ;
                  }
                }
                leaf cluster-list {
                  description 'The cluster-list attribute.'
                              ;
                  type ncd:string-with-blank {
                    length 0..256 ;
                  }
                }
                leaf out-label1 {
                  description 'Out label1.'
                              ;
                  type uint32 ;
                }
                leaf out-label2 {
                  description 'Out label2.'
                              ;
                  type uint32 ;
                }
                leaf gw-ip {
                  description 'Gateway IP Address.'
                              ;
                  type string ;
                }
                leaf rt {
                  description 'Route Target (RT) attributes.'
                              ;
                  type ncd:string-with-blank {
                    length 0..256 ;
                  }
                }
                leaf routers-mac {
                  description "Router's MAC Extended Community."
                              ;
                  type ncd:mac-address ;
                }
                leaf unknown {
                  description 'Unknown attribute.'
                              ;
                  type ncd:string-with-blank {
                    length 0..256 ;
                  }
                }
                ncd:select name ;
                ncd:select 'name eti origin-ip'
                           ;
                ncd:select 'name eti origin-ip sequence'
                           ;
              }
            }
          }
          container evpn-ipv4-vrf {
            description 'Show EVPN route information of IPv4 VRF.'
                        ;
            container route {
              description 'EVPN route.'
                          ;
              list RT-1 {
                description 'Ethernet Auto-Discovery (A-D) route.'
                            ;
                key 'name eti esi sequence'
                    ;
                leaf name {
                  description 'Name of instance.'
                              ;
                  type string {
                    length 1..32 ;
                  }
                }
                leaf eti {
                  description 'Ethernet Tag ID.'
                              ;
                  type uint32 ;
                }
                leaf esi {
                  description 'Ethernet Segment Identifier(ESI).'
                              ;
                  type string {
                    length 0..20 ;
                  }
                }
                leaf sequence {
                  description 'The route sequence.'
                              ;
                  type uint32 ;
                }
                leaf local-as {
                  description 'the Autonomy system number of BGP in local equip'
                            + 'ment.'
                              ;
                  type ncd:asn-dot ;
                }
                leaf from-peer {
                  description 'Neighbor remote address that the route is receiv'
                            + 'ed from.'
                              ;
                  type string {
                    length 0..46 ;
                  }
                }
                leaf path-id {
                  description 'The path-id.'
                              ;
                  type uint32 ;
                }
                leaf best {
                  description 'Mark for the best.'
                              ;
                  type enumeration {
                    enum false {
                      value 1 ;
                      description 'Not chosen as best route.'
                                  ;
                    }
                    enum true {
                      value 2 ;
                      description 'Chosen as best route.'
                                  ;
                    }
                  }
                }
                leaf origin {
                  description 'Origin attribute.'
                              ;
                  type enumeration {
                    enum igp {
                      value 1 ;
                      description 'Networks are interior.'
                                  ;
                    }
                    enum egp {
                      value 2 ;
                      description 'Networks learned via EGP.'
                                  ;
                    }
                    enum incomplete {
                      value 3 ;
                      description Undetermined. ;
                    }
                  }
                }
                leaf as-path {
                  description 'As path attribute.'
                              ;
                  type ncd:string-with-blank {
                    length 0..256 ;
                  }
                }
                leaf nexthop {
                  description 'Nexthop attribute.'
                              ;
                  type string {
                    length 0..46 ;
                  }
                }
                leaf med {
                  description 'MED attribute.'
                              ;
                  type uint32 ;
                }
                leaf local-preference {
                  description 'Local preference attribute.'
                              ;
                  type uint32 ;
                }
                leaf atomic {
                  description 'The atomic-aggregate attribute.'
                              ;
                  type enumeration {
                    enum no-select {
                      value 1 ;
                    }
                    enum select {
                      value 2 ;
                    }
                  }
                }
                leaf aggregator {
                  description 'The aggregator attribute.'
                              ;
                  type ncd:string-with-blank {
                    length 0..28 ;
                  }
                }
                leaf community {
                  description 'The community attribute.'
                              ;
                  type ncd:string-with-blank {
                    length 0..256 ;
                  }
                }
                leaf originator-id {
                  description 'The originator-id attribute.'
                              ;
                  type string {
                    length 0..16 ;
                  }
                }
                leaf cluster-list {
                  description 'The cluster-list attribute.'
                              ;
                  type ncd:string-with-blank {
                    length 0..256 ;
                  }
                }
                leaf out-label1 {
                  description 'Out label1.'
                              ;
                  type uint32 ;
                }
                leaf out-label2 {
                  description 'Out label2.'
                              ;
                  type uint32 ;
                }
                leaf gw-ip {
                  description 'Gateway IP Address.'
                              ;
                  type string ;
                }
                leaf rt {
                  description 'Route Target (RT) attributes.'
                              ;
                  type ncd:string-with-blank {
                    length 0..256 ;
                  }
                }
                leaf routers-mac {
                  description "Router's MAC Extended Community."
                              ;
                  type ncd:mac-address ;
                }
                leaf unknown {
                  description 'Unknown attribute.'
                              ;
                  type ncd:string-with-blank {
                    length 0..256 ;
                  }
                }
                ncd:select name ;
                ncd:select 'name eti esi'
                           ;
                ncd:select 'name eti esi sequence'
                           ;
              }
              list ip-route {
                description 'IP-VRF route information.Include routes imported f'
                          + 'rom IP Prefix Route and MAC/IP advertisement route'
                          + '.'
                            ;
                key 'name ip-prefix sequence'
                    ;
                leaf name {
                  description 'Name of instance.'
                              ;
                  type string {
                    length 1..32 ;
                  }
                }
                leaf ip-prefix {
                  description 'IP Prefix and IP Prefix length.'
                              ;
                  type string {
                    length 0..50 ;
                  }
                }
                leaf sequence {
                  description 'The route sequence.'
                              ;
                  type uint32 ;
                }
                leaf local-as {
                  description 'the Autonomy system number of BGP in local equip'
                            + 'ment.'
                              ;
                  type ncd:asn-dot ;
                }
                leaf from-peer {
                  description 'Neighbor remote address that the route is receiv'
                            + 'ed from.'
                              ;
                  type string {
                    length 0..46 ;
                  }
                }
                leaf path-id {
                  description 'The path-id.'
                              ;
                  type uint32 ;
                }
                leaf best {
                  description 'Mark for the best.'
                              ;
                  type enumeration {
                    enum false {
                      value 1 ;
                      description 'Not chosen as best route.'
                                  ;
                    }
                    enum true {
                      value 2 ;
                      description 'Chosen as best route.'
                                  ;
                    }
                  }
                }
                leaf origin {
                  description 'Origin attribute.'
                              ;
                  type enumeration {
                    enum igp {
                      value 1 ;
                      description 'Networks are interior.'
                                  ;
                    }
                    enum egp {
                      value 2 ;
                      description 'Networks learned via EGP.'
                                  ;
                    }
                    enum incomplete {
                      value 3 ;
                      description Undetermined. ;
                    }
                  }
                }
                leaf as-path {
                  description 'As path attribute.'
                              ;
                  type ncd:string-with-blank {
                    length 0..256 ;
                  }
                }
                leaf nexthop {
                  description 'Nexthop attribute.'
                              ;
                  type string {
                    length 0..46 ;
                  }
                }
                leaf med {
                  description 'MED attribute.'
                              ;
                  type uint32 ;
                }
                leaf local-preference {
                  description 'Local preference attribute.'
                              ;
                  type uint32 ;
                }
                leaf atomic {
                  description 'The atomic-aggregate attribute.'
                              ;
                  type enumeration {
                    enum no-select {
                      value 1 ;
                    }
                    enum select {
                      value 2 ;
                    }
                  }
                }
                leaf aggregator {
                  description 'The aggregator attribute.'
                              ;
                  type ncd:string-with-blank {
                    length 0..28 ;
                  }
                }
                leaf community {
                  description 'The community attribute.'
                              ;
                  type ncd:string-with-blank {
                    length 0..256 ;
                  }
                }
                leaf originator-id {
                  description 'The originator-id attribute.'
                              ;
                  type string {
                    length 0..16 ;
                  }
                }
                leaf cluster-list {
                  description 'The cluster-list attribute.'
                              ;
                  type ncd:string-with-blank {
                    length 0..256 ;
                  }
                }
                leaf out-label1 {
                  description 'Out label1.'
                              ;
                  type uint32 ;
                }
                leaf out-label2 {
                  description 'Out label2.'
                              ;
                  type uint32 ;
                }
                leaf gw-ip {
                  description 'Gateway IP Address.'
                              ;
                  type string ;
                }
                leaf rt {
                  description 'Route Target (RT) attributes.'
                              ;
                  type ncd:string-with-blank {
                    length 0..256 ;
                  }
                }
                leaf routers-mac {
                  description "Router's MAC Extended Community."
                              ;
                  type ncd:mac-address ;
                }
                leaf unknown {
                  description 'Unknown attribute.'
                              ;
                  type ncd:string-with-blank {
                    length 0..256 ;
                  }
                }
                ncd:select name ;
                ncd:select 'name ip-prefix'
                           ;
                ncd:select 'name ip-prefix sequence'
                           ;
              }
            }
          }
          container evpn-ipv6-vrf {
            description 'Show EVPN route information of IPv6 VRF.'
                        ;
            container route {
              description 'EVPN route.'
                          ;
              list RT-1 {
                description 'Ethernet Auto-Discovery (A-D) route.'
                            ;
                key 'name eti esi sequence'
                    ;
                leaf name {
                  description 'Name of instance.'
                              ;
                  type string {
                    length 1..32 ;
                  }
                }
                leaf eti {
                  description 'Ethernet Tag ID.'
                              ;
                  type uint32 ;
                }
                leaf esi {
                  description 'Ethernet Segment Identifier(ESI).'
                              ;
                  type string {
                    length 0..20 ;
                  }
                }
                leaf sequence {
                  description 'The route sequence.'
                              ;
                  type uint32 ;
                }
                leaf local-as {
                  description 'the Autonomy system number of BGP in local equip'
                            + 'ment.'
                              ;
                  type ncd:asn-dot ;
                }
                leaf from-peer {
                  description 'Neighbor remote address that the route is receiv'
                            + 'ed from.'
                              ;
                  type string {
                    length 0..46 ;
                  }
                }
                leaf path-id {
                  description 'The path-id.'
                              ;
                  type uint32 ;
                }
                leaf best {
                  description 'Mark for the best.'
                              ;
                  type enumeration {
                    enum false {
                      value 1 ;
                      description 'Not chosen as best route.'
                                  ;
                    }
                    enum true {
                      value 2 ;
                      description 'Chosen as best route.'
                                  ;
                    }
                  }
                }
                leaf origin {
                  description 'Origin attribute.'
                              ;
                  type enumeration {
                    enum igp {
                      value 1 ;
                      description 'Networks are interior.'
                                  ;
                    }
                    enum egp {
                      value 2 ;
                      description 'Networks learned via EGP.'
                                  ;
                    }
                    enum incomplete {
                      value 3 ;
                      description Undetermined. ;
                    }
                  }
                }
                leaf as-path {
                  description 'As path attribute.'
                              ;
                  type ncd:string-with-blank {
                    length 0..256 ;
                  }
                }
                leaf nexthop {
                  description 'Nexthop attribute.'
                              ;
                  type string {
                    length 0..46 ;
                  }
                }
                leaf med {
                  description 'MED attribute.'
                              ;
                  type uint32 ;
                }
                leaf local-preference {
                  description 'Local preference attribute.'
                              ;
                  type uint32 ;
                }
                leaf atomic {
                  description 'The atomic-aggregate attribute.'
                              ;
                  type enumeration {
                    enum no-select {
                      value 1 ;
                    }
                    enum select {
                      value 2 ;
                    }
                  }
                }
                leaf aggregator {
                  description 'The aggregator attribute.'
                              ;
                  type ncd:string-with-blank {
                    length 0..28 ;
                  }
                }
                leaf community {
                  description 'The community attribute.'
                              ;
                  type ncd:string-with-blank {
                    length 0..256 ;
                  }
                }
                leaf originator-id {
                  description 'The originator-id attribute.'
                              ;
                  type string {
                    length 0..16 ;
                  }
                }
                leaf cluster-list {
                  description 'The cluster-list attribute.'
                              ;
                  type ncd:string-with-blank {
                    length 0..256 ;
                  }
                }
                leaf out-label1 {
                  description 'Out label1.'
                              ;
                  type uint32 ;
                }
                leaf out-label2 {
                  description 'Out label2.'
                              ;
                  type uint32 ;
                }
                leaf gw-ip {
                  description 'Gateway IP Address.'
                              ;
                  type string ;
                }
                leaf rt {
                  description 'Route Target (RT) attributes.'
                              ;
                  type ncd:string-with-blank {
                    length 0..256 ;
                  }
                }
                leaf routers-mac {
                  description "Router's MAC Extended Community."
                              ;
                  type ncd:mac-address ;
                }
                leaf unknown {
                  description 'Unknown attribute.'
                              ;
                  type ncd:string-with-blank {
                    length 0..256 ;
                  }
                }
                ncd:select name ;
                ncd:select 'name eti esi'
                           ;
                ncd:select 'name eti esi sequence'
                           ;
              }
              list ipv6-route {
                description 'IP-VRF route information.Include routes imported f'
                          + 'rom IP Prefix Route and MAC/IP advertisement route'
                          + '.'
                            ;
                key 'name ip-prefix sequence'
                    ;
                leaf name {
                  description 'Name of instance.'
                              ;
                  type string {
                    length 1..32 ;
                  }
                }
                leaf ip-prefix {
                  description 'IP Prefix and IP Prefix length.'
                              ;
                  type string {
                    length 0..50 ;
                  }
                }
                leaf sequence {
                  description 'The route sequence.'
                              ;
                  type uint32 ;
                }
                leaf local-as {
                  description 'the Autonomy system number of BGP in local equip'
                            + 'ment.'
                              ;
                  type ncd:asn-dot ;
                }
                leaf from-peer {
                  description 'Neighbor remote address that the route is receiv'
                            + 'ed from.'
                              ;
                  type string {
                    length 0..46 ;
                  }
                }
                leaf path-id {
                  description 'The path-id.'
                              ;
                  type uint32 ;
                }
                leaf best {
                  description 'Mark for the best.'
                              ;
                  type enumeration {
                    enum false {
                      value 1 ;
                      description 'Not chosen as best route.'
                                  ;
                    }
                    enum true {
                      value 2 ;
                      description 'Chosen as best route.'
                                  ;
                    }
                  }
                }
                leaf origin {
                  description 'Origin attribute.'
                              ;
                  type enumeration {
                    enum igp {
                      value 1 ;
                      description 'Networks are interior.'
                                  ;
                    }
                    enum egp {
                      value 2 ;
                      description 'Networks learned via EGP.'
                                  ;
                    }
                    enum incomplete {
                      value 3 ;
                      description Undetermined. ;
                    }
                  }
                }
                leaf as-path {
                  description 'As path attribute.'
                              ;
                  type ncd:string-with-blank {
                    length 0..256 ;
                  }
                }
                leaf nexthop {
                  description 'Nexthop attribute.'
                              ;
                  type string {
                    length 0..46 ;
                  }
                }
                leaf med {
                  description 'MED attribute.'
                              ;
                  type uint32 ;
                }
                leaf local-preference {
                  description 'Local preference attribute.'
                              ;
                  type uint32 ;
                }
                leaf atomic {
                  description 'The atomic-aggregate attribute.'
                              ;
                  type enumeration {
                    enum no-select {
                      value 1 ;
                    }
                    enum select {
                      value 2 ;
                    }
                  }
                }
                leaf aggregator {
                  description 'The aggregator attribute.'
                              ;
                  type ncd:string-with-blank {
                    length 0..28 ;
                  }
                }
                leaf community {
                  description 'The community attribute.'
                              ;
                  type ncd:string-with-blank {
                    length 0..256 ;
                  }
                }
                leaf originator-id {
                  description 'The originator-id attribute.'
                              ;
                  type string {
                    length 0..16 ;
                  }
                }
                leaf cluster-list {
                  description 'The cluster-list attribute.'
                              ;
                  type ncd:string-with-blank {
                    length 0..256 ;
                  }
                }
                leaf out-label1 {
                  description 'Out label1.'
                              ;
                  type uint32 ;
                }
                leaf out-label2 {
                  description 'Out label2.'
                              ;
                  type uint32 ;
                }
                leaf gw-ip {
                  description 'Gateway IP Address.'
                              ;
                  type string ;
                }
                leaf rt {
                  description 'Route Target (RT) attributes.'
                              ;
                  type ncd:string-with-blank {
                    length 0..256 ;
                  }
                }
                leaf routers-mac {
                  description "Router's MAC Extended Community."
                              ;
                  type ncd:mac-address ;
                }
                leaf unknown {
                  description 'Unknown attribute.'
                              ;
                  type ncd:string-with-blank {
                    length 0..256 ;
                  }
                }
                ncd:select name ;
                ncd:select 'name ip-prefix'
                           ;
                ncd:select 'name ip-prefix sequence'
                           ;
              }
            }
          }
          ncd:revise-date 2020-05-29 ;
        }
        ncd:revise-date 2018-01-10 ;
      }
      container all-in-routes {
        description 'Show route information from BGP neighbor.'
                    ;
        container ipv4-unicast {
          description 'Show IPv4 unicast route information.'
                      ;
          list route {
            description 'IPv4 unicast route.'
                        ;
            key 'local-as vrf from-peer prefix path-id'
                ;
            leaf local-as {
              description 'the Autonomy system number of BGP in local equipment.'
                          ;
              type ncd:asn-dot ;
            }
            leaf vrf {
              description 'VPN Routing/Forwarding instance name.'
                          ;
              type string {
                length 0..32 ;
              }
            }
            leaf from-peer {
              description 'Neighbor remote address that the route is received f'
                        + 'rom.'
                          ;
              type string {
                length 0..46 ;
              }
            }
            leaf prefix {
              description 'Network address and mask.'
                          ;
              type string {
                length 0..50 ;
              }
            }
            leaf path-id {
              description 'The path-id.'
                          ;
              type uint32 ;
            }
            leaf best {
              description 'Mark for the best.'
                          ;
              type enumeration {
                enum false {
                  value 1 ;
                  description 'Not chosen as best route.'
                              ;
                }
                enum true {
                  value 2 ;
                  description 'Chosen as best route.'
                              ;
                }
              }
            }
            leaf origin {
              description 'Origin attribute.'
                          ;
              type enumeration {
                enum igp {
                  value 1 ;
                  description 'Networks are interior.'
                              ;
                }
                enum egp {
                  value 2 ;
                  description 'Networks learned via EGP.'
                              ;
                }
                enum incomplete {
                  value 3 ;
                  description Undetermined. ;
                }
              }
            }
            leaf as-path {
              description 'As path attribute.'
                          ;
              type ncd:string-with-blank {
                length 0..256 ;
              }
            }
            leaf nexthop {
              description 'Nexthop attribute.'
                          ;
              type string {
                length 0..46 ;
              }
            }
            leaf med {
              description 'MED attribute.'
                          ;
              type uint32 ;
            }
            leaf local-preference {
              description 'Local preference attribute.'
                          ;
              type uint32 ;
            }
            leaf atomic {
              description 'The atomic-aggregate attribute.'
                          ;
              type enumeration {
                enum no-select {
                  value 1 ;
                }
                enum select {
                  value 2 ;
                }
              }
            }
            leaf aggregator {
              description 'The aggregator attribute.'
                          ;
              type ncd:string-with-blank {
                length 0..28 ;
              }
            }
            leaf community {
              description 'The community attribute.'
                          ;
              type ncd:string-with-blank {
                length 0..256 ;
              }
            }
            leaf originator-id {
              description 'The originator-id attribute.'
                          ;
              type string {
                length 0..16 ;
              }
            }
            leaf cluster-list {
              description 'The cluster-list attribute.'
                          ;
              type ncd:string-with-blank {
                length 0..256 ;
              }
            }
            leaf as4-path {
              description 'The as4-path attribute.'
                          ;
              type ncd:string-with-blank ;
            }
            leaf as4-aggregator {
              description 'The as4-aggregator attribute.'
                          ;
              type ncd:string-with-blank ;
            }
            leaf label-in {
              description 'Received label.'
                          ;
              type uint32 ;
            }
            leaf unknown {
              description 'Unknown attribute.'
                          ;
              type ncd:string-with-blank {
                length 0..256 ;
              }
            }
            ncd:select 'local-as vrf from-peer prefix path-id'
                       ;
            ncd:select 'local-as from-peer prefix path-id'
                       ;
          }
        }
        container vpnv4-unicast {
          description 'Show VPNv4 unicast route information.'
                      ;
          list route {
            description 'VPNv4 unicast route.'
                        ;
            key 'local-as from-peer rd prefix path-id'
                ;
            leaf local-as {
              description 'the Autonomy system number of BGP in local equipment.'
                          ;
              type ncd:asn-dot ;
            }
            leaf from-peer {
              description 'Neighbor remote address that the route is received f'
                        + 'rom.'
                          ;
              type string {
                length 0..46 ;
              }
            }
            leaf rd {
              description 'Specify route distinguisher.'
                          ;
              type string {
                length 0..22 ;
              }
            }
            leaf prefix {
              description 'Network address and mask.'
                          ;
              type string {
                length 0..50 ;
              }
            }
            leaf path-id {
              description 'The path-id.'
                          ;
              type uint32 ;
            }
            leaf best {
              description 'Mark for the best.'
                          ;
              type enumeration {
                enum false {
                  value 1 ;
                  description 'Not chosen as best route.'
                              ;
                }
                enum true {
                  value 2 ;
                  description 'Chosen as best route.'
                              ;
                }
              }
            }
            leaf origin {
              description 'Origin attribute.'
                          ;
              type enumeration {
                enum igp {
                  value 1 ;
                  description 'Networks are interior.'
                              ;
                }
                enum egp {
                  value 2 ;
                  description 'Networks learned via EGP.'
                              ;
                }
                enum incomplete {
                  value 3 ;
                  description Undetermined. ;
                }
              }
            }
            leaf as-path {
              description 'As path attribute.'
                          ;
              type ncd:string-with-blank {
                length 0..256 ;
              }
            }
            leaf nexthop {
              description 'Nexthop attribute.'
                          ;
              type string {
                length 0..46 ;
              }
            }
            leaf med {
              description 'MED attribute.'
                          ;
              type uint32 ;
            }
            leaf local-preference {
              description 'Local preference attribute.'
                          ;
              type uint32 ;
            }
            leaf atomic {
              description 'The atomic-aggregate attribute.'
                          ;
              type enumeration {
                enum no-select {
                  value 1 ;
                }
                enum select {
                  value 2 ;
                }
              }
            }
            leaf aggregator {
              description 'The aggregator attribute.'
                          ;
              type ncd:string-with-blank {
                length 0..28 ;
              }
            }
            leaf community {
              description 'The community attribute.'
                          ;
              type ncd:string-with-blank {
                length 0..256 ;
              }
            }
            leaf originator-id {
              description 'The originator-id attribute.'
                          ;
              type string {
                length 0..16 ;
              }
            }
            leaf cluster-list {
              description 'The cluster-list attribute.'
                          ;
              type ncd:string-with-blank {
                length 0..256 ;
              }
            }
            leaf as4-path {
              description 'The as4-path attribute.'
                          ;
              type ncd:string-with-blank ;
            }
            leaf as4-aggregator {
              description 'The as4-aggregator attribute.'
                          ;
              type ncd:string-with-blank ;
            }
            leaf ext-community {
              description 'The extended communtiy attribute.'
                          ;
              type ncd:string-with-blank ;
            }
            leaf label-in {
              description 'Received label.'
                          ;
              type uint32 ;
            }
            leaf unknown {
              description 'Unknown attribute.'
                          ;
              type ncd:string-with-blank {
                length 0..256 ;
              }
            }
            ncd:select 'local-as from-peer rd prefix path-id'
                       ;
          }
        }
        container ipv6-unicast {
          description 'Show IPv6 unicast route information.'
                      ;
          list route {
            description 'IPv6 unicast route.'
                        ;
            key 'local-as vrf from-peer prefix path-id'
                ;
            leaf local-as {
              description 'the Autonomy system number of BGP in local equipment.'
                          ;
              type ncd:asn-dot ;
            }
            leaf vrf {
              description 'VPN Routing/Forwarding instance name.'
                          ;
              type string {
                length 0..32 ;
              }
            }
            leaf from-peer {
              description 'Neighbor remote address that the route is received f'
                        + 'rom.'
                          ;
              type string {
                length 0..46 ;
              }
            }
            leaf prefix {
              description 'Network address and mask.'
                          ;
              type string {
                length 0..50 ;
              }
            }
            leaf path-id {
              description 'The path-id.'
                          ;
              type uint32 ;
            }
            leaf best {
              description 'Mark for the best.'
                          ;
              type enumeration {
                enum false {
                  value 1 ;
                  description 'Not chosen as best route.'
                              ;
                }
                enum true {
                  value 2 ;
                  description 'Chosen as best route.'
                              ;
                }
              }
            }
            leaf origin {
              description 'Origin attribute.'
                          ;
              type enumeration {
                enum igp {
                  value 1 ;
                  description 'Networks are interior.'
                              ;
                }
                enum egp {
                  value 2 ;
                  description 'Networks learned via EGP.'
                              ;
                }
                enum incomplete {
                  value 3 ;
                  description Undetermined. ;
                }
              }
            }
            leaf as-path {
              description 'As path attribute.'
                          ;
              type ncd:string-with-blank {
                length 0..256 ;
              }
            }
            leaf nexthop {
              description 'Nexthop attribute.'
                          ;
              type string {
                length 0..46 ;
              }
            }
            leaf med {
              description 'MED attribute.'
                          ;
              type uint32 ;
            }
            leaf local-preference {
              description 'Local preference attribute.'
                          ;
              type uint32 ;
            }
            leaf atomic {
              description 'The atomic-aggregate attribute.'
                          ;
              type enumeration {
                enum no-select {
                  value 1 ;
                }
                enum select {
                  value 2 ;
                }
              }
            }
            leaf aggregator {
              description 'The aggregator attribute.'
                          ;
              type ncd:string-with-blank {
                length 0..28 ;
              }
            }
            leaf community {
              description 'The community attribute.'
                          ;
              type ncd:string-with-blank {
                length 0..256 ;
              }
            }
            leaf originator-id {
              description 'The originator-id attribute.'
                          ;
              type string {
                length 0..16 ;
              }
            }
            leaf cluster-list {
              description 'The cluster-list attribute.'
                          ;
              type ncd:string-with-blank {
                length 0..256 ;
              }
            }
            leaf as4-path {
              description 'The as4-path attribute.'
                          ;
              type ncd:string-with-blank ;
            }
            leaf as4-aggregator {
              description 'The as4-aggregator attribute.'
                          ;
              type ncd:string-with-blank ;
            }
            leaf label-in {
              description 'Received label.'
                          ;
              type uint32 ;
            }
            leaf unknown {
              description 'Unknown attribute.'
                          ;
              type ncd:string-with-blank {
                length 0..256 ;
              }
            }
            ncd:select 'local-as vrf from-peer prefix path-id'
                       ;
            ncd:select 'local-as from-peer prefix path-id'
                       ;
          }
        }
        container vpnv6-unicast {
          description 'Show VPNv6 unicast route information.'
                      ;
          list route {
            description 'VPNv6 unicast route.'
                        ;
            key 'local-as from-peer rd prefix path-id'
                ;
            leaf local-as {
              description 'the Autonomy system number of BGP in local equipment.'
                          ;
              type ncd:asn-dot ;
            }
            leaf from-peer {
              description 'Neighbor remote address that the route is received f'
                        + 'rom.'
                          ;
              type string {
                length 0..46 ;
              }
            }
            leaf rd {
              description 'Specify route distinguisher.'
                          ;
              type string {
                length 0..22 ;
              }
            }
            leaf prefix {
              description 'Network address and mask.'
                          ;
              type string {
                length 0..50 ;
              }
            }
            leaf path-id {
              description 'The path-id.'
                          ;
              type uint32 ;
            }
            leaf best {
              description 'Mark for the best.'
                          ;
              type enumeration {
                enum false {
                  value 1 ;
                  description 'Not chosen as best route.'
                              ;
                }
                enum true {
                  value 2 ;
                  description 'Chosen as best route.'
                              ;
                }
              }
            }
            leaf origin {
              description 'Origin attribute.'
                          ;
              type enumeration {
                enum igp {
                  value 1 ;
                  description 'Networks are interior.'
                              ;
                }
                enum egp {
                  value 2 ;
                  description 'Networks learned via EGP.'
                              ;
                }
                enum incomplete {
                  value 3 ;
                  description Undetermined. ;
                }
              }
            }
            leaf as-path {
              description 'As path attribute.'
                          ;
              type ncd:string-with-blank {
                length 0..256 ;
              }
            }
            leaf nexthop {
              description 'Nexthop attribute.'
                          ;
              type string {
                length 0..46 ;
              }
            }
            leaf med {
              description 'MED attribute.'
                          ;
              type uint32 ;
            }
            leaf local-preference {
              description 'Local preference attribute.'
                          ;
              type uint32 ;
            }
            leaf atomic {
              description 'The atomic-aggregate attribute.'
                          ;
              type enumeration {
                enum no-select {
                  value 1 ;
                }
                enum select {
                  value 2 ;
                }
              }
            }
            leaf aggregator {
              description 'The aggregator attribute.'
                          ;
              type ncd:string-with-blank {
                length 0..28 ;
              }
            }
            leaf community {
              description 'The community attribute.'
                          ;
              type ncd:string-with-blank {
                length 0..256 ;
              }
            }
            leaf originator-id {
              description 'The originator-id attribute.'
                          ;
              type string {
                length 0..16 ;
              }
            }
            leaf cluster-list {
              description 'The cluster-list attribute.'
                          ;
              type ncd:string-with-blank {
                length 0..256 ;
              }
            }
            leaf as4-path {
              description 'The as4-path attribute.'
                          ;
              type ncd:string-with-blank ;
            }
            leaf as4-aggregator {
              description 'The as4-aggregator attribute.'
                          ;
              type ncd:string-with-blank ;
            }
            leaf ext-community {
              description 'The extended communtiy attribute.'
                          ;
              type ncd:string-with-blank ;
            }
            leaf label-in {
              description 'Received label.'
                          ;
              type uint32 ;
            }
            leaf unknown {
              description 'Unknown attribute.'
                          ;
              type ncd:string-with-blank {
                length 0..256 ;
              }
            }
            ncd:select 'local-as from-peer rd prefix path-id'
                       ;
          }
        }
        ncd:revise-date 2018-01-10 ;
      }
      container all-out-routes {
        description 'Show route information to BGP neighbor.'
                    ;
        container ipv4-unicast {
          description 'Show IPv4 unicast route information.'
                      ;
          list route {
            description 'IPv4 unicast route.'
                        ;
            key 'local-as vrf to-peer prefix path-id'
                ;
            leaf local-as {
              description 'the Autonomy system number of BGP in local equipment.'
                          ;
              type ncd:asn-dot ;
            }
            leaf vrf {
              description 'VPN Routing/Forwarding instance name.'
                          ;
              type string {
                length 0..32 ;
              }
            }
            leaf to-peer {
              description 'Neighbor remote address that the route is sent to.'
                          ;
              type string {
                length 0..46 ;
              }
            }
            leaf prefix {
              description 'Network address and mask.'
                          ;
              type string {
                length 0..50 ;
              }
            }
            leaf path-id {
              description 'The path-id.'
                          ;
              type uint32 ;
            }
            leaf origin {
              description 'Origin attribute.'
                          ;
              type enumeration {
                enum igp {
                  value 1 ;
                  description 'Networks are interior.'
                              ;
                }
                enum egp {
                  value 2 ;
                  description 'Networks learned via EGP.'
                              ;
                }
                enum incomplete {
                  value 3 ;
                  description Undetermined. ;
                }
              }
            }
            leaf as-path {
              description 'As path attribute.'
                          ;
              type ncd:string-with-blank {
                length 0..256 ;
              }
            }
            leaf nexthop {
              description 'Nexthop attribute.'
                          ;
              type string {
                length 0..46 ;
              }
            }
            leaf med {
              description 'MED attribute.'
                          ;
              type uint32 ;
            }
            leaf local-preference {
              description 'Local preference attribute.'
                          ;
              type uint32 ;
            }
            leaf atomic {
              description 'The atomic-aggregate attribute.'
                          ;
              type enumeration {
                enum no-select {
                  value 1 ;
                }
                enum select {
                  value 2 ;
                }
              }
            }
            leaf aggregator {
              description 'The aggregator attribute.'
                          ;
              type ncd:string-with-blank {
                length 0..28 ;
              }
            }
            leaf community {
              description 'The community attribute.'
                          ;
              type ncd:string-with-blank {
                length 0..256 ;
              }
            }
            leaf originator-id {
              description 'The originator-id attribute.'
                          ;
              type string {
                length 0..16 ;
              }
            }
            leaf cluster-list {
              description 'The cluster-list attribute.'
                          ;
              type ncd:string-with-blank {
                length 0..256 ;
              }
            }
            leaf as4-path {
              description 'The as4-path attribute.'
                          ;
              type ncd:string-with-blank ;
            }
            leaf as4-aggregator {
              description 'The as4-aggregator attribute.'
                          ;
              type ncd:string-with-blank ;
            }
            leaf label-out {
              description 'Sent label.'
                          ;
              type uint32 ;
            }
            leaf unknown {
              description 'Unknown attribute.'
                          ;
              type ncd:string-with-blank {
                length 0..256 ;
              }
            }
            ncd:select 'local-as vrf to-peer prefix path-id'
                       ;
            ncd:select 'local-as to-peer prefix path-id'
                       ;
          }
        }
        container vpnv4-unicast {
          description 'Show VPNv4 unicast route information.'
                      ;
          list route {
            description 'VPNv4 unicast route.'
                        ;
            key 'local-as to-peer rd prefix path-id'
                ;
            leaf local-as {
              description 'the Autonomy system number of BGP in local equipment.'
                          ;
              type ncd:asn-dot ;
            }
            leaf to-peer {
              description 'Neighbor remote address that the route is sent to.'
                          ;
              type string {
                length 0..46 ;
              }
            }
            leaf rd {
              description 'Specify route distinguisher.'
                          ;
              type string {
                length 0..22 ;
              }
            }
            leaf prefix {
              description 'Network address and mask.'
                          ;
              type string {
                length 0..50 ;
              }
            }
            leaf path-id {
              description 'The path-id.'
                          ;
              type uint32 ;
            }
            leaf origin {
              description 'Origin attribute.'
                          ;
              type enumeration {
                enum igp {
                  value 1 ;
                  description 'Networks are interior.'
                              ;
                }
                enum egp {
                  value 2 ;
                  description 'Networks learned via EGP.'
                              ;
                }
                enum incomplete {
                  value 3 ;
                  description Undetermined. ;
                }
              }
            }
            leaf as-path {
              description 'As path attribute.'
                          ;
              type ncd:string-with-blank {
                length 0..256 ;
              }
            }
            leaf nexthop {
              description 'Nexthop attribute.'
                          ;
              type string {
                length 0..46 ;
              }
            }
            leaf med {
              description 'MED attribute.'
                          ;
              type uint32 ;
            }
            leaf local-preference {
              description 'Local preference attribute.'
                          ;
              type uint32 ;
            }
            leaf atomic {
              description 'The atomic-aggregate attribute.'
                          ;
              type enumeration {
                enum no-select {
                  value 1 ;
                }
                enum select {
                  value 2 ;
                }
              }
            }
            leaf aggregator {
              description 'The aggregator attribute.'
                          ;
              type ncd:string-with-blank {
                length 0..28 ;
              }
            }
            leaf community {
              description 'The community attribute.'
                          ;
              type ncd:string-with-blank {
                length 0..256 ;
              }
            }
            leaf originator-id {
              description 'The originator-id attribute.'
                          ;
              type string {
                length 0..16 ;
              }
            }
            leaf cluster-list {
              description 'The cluster-list attribute.'
                          ;
              type ncd:string-with-blank {
                length 0..256 ;
              }
            }
            leaf as4-path {
              description 'The as4-path attribute.'
                          ;
              type ncd:string-with-blank ;
            }
            leaf as4-aggregator {
              description 'The as4-aggregator attribute.'
                          ;
              type ncd:string-with-blank ;
            }
            leaf ext-community {
              description 'The extended communtiy attribute.'
                          ;
              type ncd:string-with-blank ;
            }
            leaf label-out {
              description 'Sent label.'
                          ;
              type uint32 ;
            }
            leaf unknown {
              description 'Unknown attribute.'
                          ;
              type ncd:string-with-blank {
                length 0..256 ;
              }
            }
            ncd:select 'local-as to-peer rd prefix path-id'
                       ;
          }
        }
        container ipv6-unicast {
          description 'Show IPv6 unicast route information.'
                      ;
          list route {
            description 'IPv6 unicast route.'
                        ;
            key 'local-as vrf to-peer prefix path-id'
                ;
            leaf local-as {
              description 'the Autonomy system number of BGP in local equipment.'
                          ;
              type ncd:asn-dot ;
            }
            leaf vrf {
              description 'VPN Routing/Forwarding instance name.'
                          ;
              type string {
                length 0..32 ;
              }
            }
            leaf to-peer {
              description 'Neighbor remote address that the route is sent to.'
                          ;
              type string {
                length 0..46 ;
              }
            }
            leaf prefix {
              description 'Network address and mask.'
                          ;
              type string {
                length 0..50 ;
              }
            }
            leaf path-id {
              description 'The path-id.'
                          ;
              type uint32 ;
            }
            leaf origin {
              description 'Origin attribute.'
                          ;
              type enumeration {
                enum igp {
                  value 1 ;
                  description 'Networks are interior.'
                              ;
                }
                enum egp {
                  value 2 ;
                  description 'Networks learned via EGP.'
                              ;
                }
                enum incomplete {
                  value 3 ;
                  description Undetermined. ;
                }
              }
            }
            leaf as-path {
              description 'As path attribute.'
                          ;
              type ncd:string-with-blank {
                length 0..256 ;
              }
            }
            leaf nexthop {
              description 'Nexthop attribute.'
                          ;
              type string {
                length 0..46 ;
              }
            }
            leaf med {
              description 'MED attribute.'
                          ;
              type uint32 ;
            }
            leaf local-preference {
              description 'Local preference attribute.'
                          ;
              type uint32 ;
            }
            leaf atomic {
              description 'The atomic-aggregate attribute.'
                          ;
              type enumeration {
                enum no-select {
                  value 1 ;
                }
                enum select {
                  value 2 ;
                }
              }
            }
            leaf aggregator {
              description 'The aggregator attribute.'
                          ;
              type ncd:string-with-blank {
                length 0..28 ;
              }
            }
            leaf community {
              description 'The community attribute.'
                          ;
              type ncd:string-with-blank {
                length 0..256 ;
              }
            }
            leaf originator-id {
              description 'The originator-id attribute.'
                          ;
              type string {
                length 0..16 ;
              }
            }
            leaf cluster-list {
              description 'The cluster-list attribute.'
                          ;
              type ncd:string-with-blank {
                length 0..256 ;
              }
            }
            leaf as4-path {
              description 'The as4-path attribute.'
                          ;
              type ncd:string-with-blank ;
            }
            leaf as4-aggregator {
              description 'The as4-aggregator attribute.'
                          ;
              type ncd:string-with-blank ;
            }
            leaf label-out {
              description 'Sent label.'
                          ;
              type uint32 ;
            }
            leaf unknown {
              description 'Unknown attribute.'
                          ;
              type ncd:string-with-blank {
                length 0..256 ;
              }
            }
            ncd:select 'local-as vrf to-peer prefix path-id'
                       ;
            ncd:select 'local-as to-peer prefix path-id'
                       ;
          }
        }
        container vpnv6-unicast {
          description 'Show VPNv6 unicast route information.'
                      ;
          list route {
            description 'VPNv6 unicast route.'
                        ;
            key 'local-as to-peer rd prefix path-id'
                ;
            leaf local-as {
              description 'the Autonomy system number of BGP in local equipment.'
                          ;
              type ncd:asn-dot ;
            }
            leaf to-peer {
              description 'Neighbor remote address that the route is sent to.'
                          ;
              type string {
                length 0..46 ;
              }
            }
            leaf rd {
              description 'Specify route distinguisher.'
                          ;
              type string {
                length 0..22 ;
              }
            }
            leaf prefix {
              description 'Network address and mask.'
                          ;
              type string {
                length 0..50 ;
              }
            }
            leaf path-id {
              description 'The path-id.'
                          ;
              type uint32 ;
            }
            leaf origin {
              description 'Origin attribute.'
                          ;
              type enumeration {
                enum igp {
                  value 1 ;
                  description 'Networks are interior.'
                              ;
                }
                enum egp {
                  value 2 ;
                  description 'Networks learned via EGP.'
                              ;
                }
                enum incomplete {
                  value 3 ;
                  description Undetermined. ;
                }
              }
            }
            leaf as-path {
              description 'As path attribute.'
                          ;
              type ncd:string-with-blank {
                length 0..256 ;
              }
            }
            leaf nexthop {
              description 'Nexthop attribute.'
                          ;
              type string {
                length 0..46 ;
              }
            }
            leaf med {
              description 'MED attribute.'
                          ;
              type uint32 ;
            }
            leaf local-preference {
              description 'Local preference attribute.'
                          ;
              type uint32 ;
            }
            leaf atomic {
              description 'The atomic-aggregate attribute.'
                          ;
              type enumeration {
                enum no-select {
                  value 1 ;
                }
                enum select {
                  value 2 ;
                }
              }
            }
            leaf aggregator {
              description 'The aggregator attribute.'
                          ;
              type ncd:string-with-blank {
                length 0..28 ;
              }
            }
            leaf community {
              description 'The community attribute.'
                          ;
              type ncd:string-with-blank {
                length 0..256 ;
              }
            }
            leaf originator-id {
              description 'The originator-id attribute.'
                          ;
              type string {
                length 0..16 ;
              }
            }
            leaf cluster-list {
              description 'The cluster-list attribute.'
                          ;
              type ncd:string-with-blank {
                length 0..256 ;
              }
            }
            leaf as4-path {
              description 'The as4-path attribute.'
                          ;
              type ncd:string-with-blank ;
            }
            leaf as4-aggregator {
              description 'The as4-aggregator attribute.'
                          ;
              type ncd:string-with-blank ;
            }
            leaf ext-community {
              description 'The extended communtiy attribute.'
                          ;
              type ncd:string-with-blank ;
            }
            leaf label-out {
              description 'Sent label.'
                          ;
              type uint32 ;
            }
            leaf unknown {
              description 'Unknown attribute.'
                          ;
              type ncd:string-with-blank {
                length 0..256 ;
              }
            }
            ncd:select 'local-as to-peer rd prefix path-id'
                       ;
          }
        }
        ncd:revise-date 2018-01-10 ;
      }
    }
  }
}
