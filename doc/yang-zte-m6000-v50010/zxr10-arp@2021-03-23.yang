module zxr10-arp {
  namespace 'http://www.zte.com.cn/zxr10/netconf/schema/rosng/arp'
            ;
  prefix arp ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe ARP.'
              ;
  revision 2021-03-23 {
    description 'Modify feature of configuration/arp/interface-container/interfac'
              + 'e-list/detect-min-interval.'
                ;
  }
  revision 2021-01-28 {
    description 'Modify range of configuration/arp/interface-container/interfac'
              + 'e-list/temp-arp-timeout.'
                ;
  }
  revision 2020-08-10 {
    description 'Add detect-min-interval node of configuration/arp/interface-co'
              + 'ntainer/interface-list.'
                ;
  }
  revision 2020-08-06 {
    description 'Add host-route node of configuration/arp/interface-container/i'
              + 'nterface-list.'
                ;
  }
  revision 2020-07-22 {
    description 'Add destination-filtered node of configuration/arp/global-cont'
              + 'ainer/global.'
                ;
  }
  revision 2020-07-08 {
    description 'Add fast-reply node and fast-reply-mode node of configuration/'
              + 'arp/global-container/global.'
                ;
  }
  revision 2020-05-23 {
    description 'Add configuration/arp/vpls-evpns son nodes.'+"\n"
              + 'include:'+"\n"
              + '  arp description'
                ;
  }
  revision 2020-05-06 {
    description 'Add state/arp/l2-proxy-items/l2-proxy-item nodes and feature a'
              + 'bout getting l2-proxy-item .'
                ;
  }
  revision 2019-12-22 {
    description 'Add configuration/arp/vpls-evpns/probe-delay nodes.'
                ;
  }
  revision 2018-07-05 {
    description 'modify RARP feature'
                ;
  }
  revision 2018-04-27 {
    description 'modify arp broadcast and arp proxy-suppress feature'
                ;
  }
  revision 2018-02-07 {
    description 'Add configuration/arp/vpls-evpns son nodes.'+"\n"
              + 'Include:'+"\n"
              + '  arp broadcast'+"\n"
              + '  arp proxy-suppress'
                ;
  }
  revision 2017-12-25 {
    description 'Add arp-vpls-evpn feature.'+"\n"
              + 'Add configuration/arp/vpls-evpns node and its son nodes.'
                ;
  }
  revision 2017-12-12 {
    description "The arp-vxlan-evpn feature doesn't support all switch projects"
              + " and C600 project."
                ;
  }
  revision 2017-10-10 {
    description 'Add leaf node:/configuration/arp/interface-container/interface'
              + '-list/global-proxy.'
                ;
  }
  revision 2017-08-03 {
    description 'Add configuration/arp/vxlan-evpn-container/double-label node.'
                ;
  }
  revision 2017-07-05 {
    description 'Add arp-vxlan-evpn feature.'+"\n"
              + 'Add configuration/arp/vxlan-evpn-container node and its son no'
              + 'des.'
                ;
  }
  revision 2016-03-17 {
    description 'Add type case node under the clear-dynamic chioce node.'
                ;
  }
  revision 2016-01-25 {
    description '1.Modify the minimum value of configuration/arp/mac-protect-co'
              + 'ntainer/mac-protect-list/protect-num from 0 to 1.'
                ;
  }
  revision 2016-01-07 {
    description '1.Modify the type ipv4 of state/arp-item/detail/remote-ip to s'
              + 'tring.'
                ;
  }
  revision 2015-12-25 {
    description '1.Modify the type ipv4 of configuration/arp/vxlan-permanent-co'
              + 'ntainer/vxlan-permanent-list/remote-ip to choice.'+"\n"
              + '2.Modify the type ipv4 of state/arp/vxlan-arp-item/brief/remot'
              + 'e-ip to string.'
                ;
  }
  revision 2015-04-06 {
    description 'Delete the node of state/arp/ip-arp-inspection-configure.'
                ;
  }
  revision 2015-03-27 {
    description '1.Change the description of configuration/arp/interface-contai'
              + 'ner/interface-list/protect-num.'+"\n"
              + '2.Change the range and description of configuration/arp/mac-pr'
              + 'otect-container/mac-protect-list/protect-num.'+"\n"
              + '3.Change the range and description of configuration/arp/global'
              + '-container/global/global-protect-num.'+"\n"
              + '4.Change the range and description of configuration/arp/global'
              + '-container/global/mac-protect-num.'
                ;
  }
  revision 2015-03-13 {
    description '1.Delete the feature of freearp-periodic and cps-trust.'+"\n"
              + '2.Add the feature of interface-temp-arp-timeout to the node of'
              + ' configuration/arp/interface-container/interface-list/temp-arp'
              + '-timeout.'+"\n"
              + '3.Delete the units of configuration/arp/inspection-trust-conta'
              + 'iner/inspection-trust-list/inspection-trust.'
                ;
  }
  revision 2015-02-25 {
    description 'Modify the type unit8 of the leaf nodes of state/arp/ip-arp-in'
              + 'spection-configure to chars.'
                ;
  }
  revision 2015-02-13 {
    description '1.Add features of vxlan-arp,cps-trust,inspection-validate and '
              + 'inspection.'+"\n"
              + '2.Add configuration/arp/vxlan-permanent-container to the featu'
              + 're of vxlan-arp.'+"\n"
              + '3.Add configuration/arp/global-container/global/inspect-scr-ma'
              + 'c,inspect-des-mac and inspect-ip to the feature of inspection-'
              + 'validate.'+"\n"
              + '4.Add configuration/arp/inspection-container to the feature of'
              + ' inspection.'+"\n"
              + '5.Add state/arp/arp-statistics to the feature of clear-arp-sta'
              + 'tistics.'+"\n"
              + '6.Add state/arp/ip-arp-inspection-configure to the feature of '
              + 'inspection-validate.'+"\n"
              + '7.Add state/arp/ip-arp-inspection-interface to the feature of '
              + 'inspection-trust.'+"\n"
              + '8.Add state/arp/ip-arp-inspection-vlan to the feature of inspe'
              + 'ction-vlan.'+"\n"
              + '9.Add state/arp/vxlan-arp-item to the feature of vxlan-arp.'
                ;
  }
  revision 2015-01-15 {
    description 'Modify vxlan permanent arp item nodes.'+"\n"
              + 'Delete these nodes:'+"\n"
              + 'zxr10-arp/configuration/permanent-container/permanent-list/rem'
              + 'ote-ip.'+"\n"
              + 'zxr10-arp/configuration/permanent-container/permanent-list/vte'
              + 'p-intf-name.'+"\n"
              + 'zxr10-arp/configuration/permanent-container/permanent-list/vxl'
              + 'an-id.'+"\n"
              + 'Add these nodes:'+"\n"
              + 'zxr10-arp/vxlan-permanent-container and its children nodes.'
                ;
  }
  revision 2014-12-03 {
    description 'Resolve the problem of interface filtering.'+"\n"
              + '   Add default value of several nodes.'
                ;
  }
  revision 2014-08-11 {
    description 'Add vxlan arp item nodes and modify arp item detail nodes.'
                ;
  }
  revision 2014-05-20 {
    description 'Add 18 feature nodes.'+"\n"
              + 'Modify the protect-num node.'+"\n"
              + 'Add the inter-vlan-proxy node.'+"\n"
              + 'Remove permanent-flag node.'+"\n"
              + 'Modify the action-type of the no-to-static node.'+"\n"
              + 'Add performance parameters of the purge-delay and temp-arp-tim'
              + 'eout nodes.'
                ;
  }
  revision 2014-04-28 {
    description 'Delete nodes of parent-intf in permanent and static ARP config'
              + 'uration.'+"\n"
              + 'Modify the default value of del-flag and source-filtered nodes'
              + '.'+"\n"
              + 'The no-to-permanent-container node changes name to to-permanen'
              + 't-container.'+"\n"
              + 'Modify the configuration of static arp function.'+"\n"
              + 'Delete the nodes of mac inter-vlanid and exter-vlanid in the n'
              + 'o-static-list node.'+"\n"
              + 'Add inspection function.'
                ;
  }
  revision 2014-03-20 {
    description 'Initial version'
                ;
  }
  feature interface-network-learn {
    description 'Network ARP learning function.'
                ;
  }
  feature interface-temp-arp-timeout {
    description 'Temporary ARP aging time.'
                ;
  }
  feature inspection-vlan {
    description 'Set VLAN dynamic ARP inspection.'
                ;
  }
  feature inspection-trust {
    description 'Set dynamic ARP inspection trust.'
                ;
  }
  feature inspection-limit {
    description 'Set dynamic ARP inspection limit speed.'
                ;
  }
  feature to-permanent {
    description 'The dynamic ARP entry changes to the permanent type of the ent'
              + 'ry.'
                ;
  }
  feature detect {
    description 'Enable detect snooping function.'
                ;
  }
  feature keepalive-time {
    description 'The static routing the next-hop ARP keep alive interval.'
                ;
  }
  feature gratuitous-proxy-arp {
    description 'Set gratuitous proxy ARP.'
                ;
  }
  feature alarm-threshold {
    description Alarm-threshold. ;
  }
  feature clear-arp-statistics {
    description 'Clear the ARP packet statistics counting.'
                ;
  }
  feature conflict-notify {
    description 'Set ARP conflict notify.'
                ;
  }
  feature learn-limit {
    description 'Limit ARP learning function.'
                ;
  }
  feature limit-time {
    description 'ARP limit time.'
                ;
  }
  feature port-speed {
    description 'Packets number per second of the port.'
                ;
  }
  feature inter-vlan-proxy {
    description 'Set ARP proxy function between different VLANs in the same int'
              + 'erface.'
                ;
  }
  feature scan {
    description 'ARP scan under the interface.'
                ;
  }
  feature vxlan-arp {
    description 'ARP about VXLAN.'
                ;
  }
  feature inspection-validate {
    description 'Dynamic ARP inspection.'
                ;
  }
  feature inspection {
    description 'Dynamic ARP inspection about routers.'
                ;
  }
  feature arp-vxlan-evpn {
    description 'ARP configuration about VxLAN-EVPN.'
                ;
  }
  feature interface-global-proxy {
    description 'ARP global proxy function.'
                ;
  }
  feature arp-vpls-evpn {
    description 'ARP configurations about VPLS-EVPN.'
                ;
  }
  feature arp-vpls-evpn-l2-proxy {
    description 'ARP configurations about arp broadcast and arp proxy-suppress.'
                ;
  }
  feature rarp {
    description 'ARP configurations about RARP.'
                ;
  }
  feature get-l2-proxy-item {
    description 'A feature about getting l2-proxy-item'
                ;
  }
  feature arp-vpls-evpn-description {
    description 'Set the description of VPLS EVPN ARP.'
                ;
  }
  feature fast-reply {
    description 'A feature about arp fast-reply and arp fast-reply-mode.'
                ;
  }
  feature destination-filtered {
    description 'A feature about arp destination-filtered.'
                ;
  }
  feature host-route {
    description 'A feature about arp host-route.'
                ;
  }
  feature detect-min-interval {
    description 'A feature about arp detect-min-interval.'
                ;
  }
  container configuration {
    description 'ARP configuration commands.'
                ;
    container arp {
      description 'ARP configuration commands.'
                  ;
      container interface-container {
        description 'Commands under interface mode about ARP.'
                    ;
        list interface-list {
          description 'Commands under interface mode about ARP.'
                      ;
          key intf-name ;
          leaf intf-name {
            description 'Interface name.'
                        ;
            type ncd:ifname ;
          }
          leaf timeout {
            description 'Dynamic ARP entries of aging time.'
                        ;
            type uint32 {
              range 1..2147483 {
                description 'From 1 To 2147483.'
                            ;
              }
            }
            units seconds ;
            default 14400 ;
          }
          leaf purge-delay {
            description 'ARP purge delay.'
                        ;
            type uint32 {
              range 1..36000 {
                description 'From 1 to 36000.'
                            ;
              }
            }
            units seconds ;
            default 600 ;
          }
          leaf protect-num {
            description 'Protect limit number.Its value depends on the performa'
                      + 'nce parameters.'
                        ;
            type uint32 {
              range 0..262144 {
                description 'From 0 to 262144.'
                            ;
              }
            }
            default 0 ;
          }
          leaf limit-time {
            // if-feature limit-time ;
            description 'ARP limit time.'
                        ;
            type uint32 {
              range 0..1000 {
                description 'From 0 to 1000.'
                            ;
              }
            }
            units seconds ;
            default 10 ;
          }
          leaf port-speed {
            // if-feature port-speed ;
            description 'Packets number per second of the port.'
                        ;
            type uint32 {
              range 0..1000 {
                description 'From 0 to 1000.'
                            ;
              }
            }
            units number-per-second ;
            default 0 ;
          }
          leaf proxy {
            description 'ARP proxy.'
                        ;
            type enumeration {
              enum disable {
                value 0 ;
                description Disable. ;
              }
              enum enable {
                value 1 ;
                description Enable. ;
              }
            }
            default disable ;
          }
          leaf learn-disable {
            description 'Disable ARP learning function.'
                        ;
            type enumeration {
              enum disable {
                value 1 ;
                description Disable. ;
              }
              enum enable {
                value 2 ;
                description Enable. ;
              }
            }
            default disable ;
          }
          leaf source-filtered {
            description 'The interface source-filtered.'
                        ;
            type enumeration {
              enum enable {
                value 1 ;
                description Enable. ;
              }
              enum disable {
                value 2 ;
                description Disable. ;
              }
            }
            default enable ;
          }
          leaf local-proxy-arp {
            description 'ARP local proxy in the port.'
                        ;
            type enumeration {
              enum disable {
                value 0 ;
                description Disable. ;
              }
              enum enable {
                value 1 ;
                description Enable. ;
              }
            }
            default disable ;
          }
          leaf proxy-local {
            description 'Under the same VLAN ARP proxy function.'
                        ;
            type enumeration {
              enum disable {
                value 0 ;
                description Disable. ;
              }
              enum enable {
                value 1 ;
                description Enable. ;
              }
            }
            default disable ;
          }
          leaf learn-limit {
            // if-feature learn-limit ;
            description 'Limit ARP learning function.'
                        ;
            type enumeration {
              enum enable {
                value 1 ;
                description Enable. ;
              }
              enum disable {
                value 2 ;
                description Disable. ;
              }
            }
            default disable ;
          }
          leaf backupvrrp-learn-flag {
            description 'Backup VRRP ARP learning function.'
                        ;
            type enumeration {
              enum enable {
                value 1 ;
                description Enable. ;
              }
              enum disable {
                value 2 ;
                description Disable. ;
              }
            }
            default disable ;
          }
          leaf gratuitous-learn-flag {
            description 'Gratuitous ARP learning function.'
                        ;
            type enumeration {
              enum enable {
                value 1 ;
                description Enable. ;
              }
              enum disable {
                value 2 ;
                description Disable. ;
              }
            }
            default disable ;
          }
          leaf network-learn-flag {
            // if-feature interface-network-learn ;
            description 'Network ARP learning function.'
                        ;
            type enumeration {
              enum enable {
                value 1 ;
                description Enable. ;
              }
              enum disable {
                value 2 ;
                description Disable. ;
              }
            }
            default disable ;
          }
          leaf limit-alarm-threshold {
            // if-feature alarm-threshold ;
            description 'ARP learn-limit alarm-threshold.'
                        ;
            type uint32 {
              range 1..65535 {
                description 'From 1 to 65535.'
                            ;
              }
            }
            default 300 ;
          }
          leaf filter-alarm-thresshold {
            // if-feature alarm-threshold ;
            description 'ARP source-filter alarm-threshold.'
                        ;
            type uint32 {
              range 1..65535 {
                description 'From 1 to 65535.'
                            ;
              }
            }
            default 300 ;
          }
          leaf temp-arp-timeout {
            // if-feature interface-temp-arp-timeout ;
            description 'Temporary ARP aging time.Its maximum which is between '
                      + '10-100 and generally 10, depends on pruduct specificat'
                      + 'ion.'
                        ;
            type uint32 {
              range 1..100 {
                description 'From 1 to 100.'
                            ;
              }
            }
            units seconds ;
            default 3 ;
          }
          leaf inter-vlan-proxy {
            // if-feature inter-vlan-proxy ;
            description 'Set ARP proxy function between different VLANs in the '
                      + 'same interface.'
                        ;
            type enumeration {
              enum enable {
                value 1 ;
                description Enable. ;
              }
              enum disable {
                value 2 ;
                description Disable. ;
              }
            }
            default disable ;
          }
          leaf global-proxy {
            // if-feature interface-global-proxy ;
            description 'ARP global proxy.'
                        ;
            type enumeration {
              enum disable {
                value 0 ;
                description 'Disable global proxy function.'
                            ;
              }
              enum enable {
                value 1 ;
                description 'Enable global proxy function.'
                            ;
              }
            }
            default disable ;
            ncd:revise-date 2017-10-10 ;
          }
          container gratuitous-proxy {
            // if-feature gratuitous-proxy-arp ;
            description 'Gratuitous proxy ARP.'
                        ;
            leaf gratuitous-proxy-time {
              description 'Gratuitous proxy ARP regularly send interval.'
                          ;
              type uint32 {
                range 1..14400 {
                  description 'From 1 to 14400.'
                              ;
                }
              }
              units seconds ;
              default 30 ;
            }
          }
          container freearp {
            description 'Regularly send gratuitous ARP message sign of the port.'
                        ;
            leaf freearp-time {
              description 'The time interval of send gratuitous ARP message.'
                          ;
              type uint32 {
                range 10..14400 {
                  description 'From 10 to 14400.'
                              ;
                }
              }
              units seconds ;
              default 30 ;
            }
          }
          leaf rarp {
            // if-feature rarp ;
            description 'Set RARP function switch.'
                        ;
            type enumeration {
              enum disable {
                value 0 ;
                description 'Disable RARP function'
                            ;
              }
              enum enable {
                value 1 ;
                description 'Enable RARP function'
                            ;
              }
            }
            default disable ;
            ncd:revise-date 2018-07-05 ;
          }
          leaf host-route {
            // if-feature host-route ;
            description 'ARP host route function.'
                        ;
            type enumeration {
              enum enable {
                value 1 ;
                description 'Enable ARP host-route.'
                            ;
              }
              enum disable {
                value 0 ;
                description 'Disable ARP host-route.'
                            ;
              }
            }
            default disable ;
            ncd:revise-date 2020-08-06 ;
          }
          leaf detect-min-interval {
            // if-feature detect-min-interval ;
            description 'Set ARP detect minimum interval.'
                        ;
            type uint32 {
              range 1..3600 {
                description 'From 1 To 3600.'
                            ;
              }
            }
            units seconds ;
            default 3 ;
            ncd:revise-date 2020-08-10 ;
          }
        }
      }
      container permanent-container {
        description 'Set the permanent ARP.'
                    ;
        list permanent-list {
          description 'Set the permanent ARP.'
                      ;
          key 'ip intf-name'
              ;
          leaf ip {
            description 'IP address.'
                        ;
            type ncd:ipv4-address ;
          }
          leaf intf-name {
            description 'Interface name.'
                        ;
            type ncd:ifname ;
          }
          leaf mac {
            description 'MAC address.'
                        ;
            type ncd:mac-address ;
            mandatory true ;
          }
          leaf inter-vlanid {
            description 'Internal VLAN ID.'
                        ;
            type uint16 {
              range 1..4094 {
                description 'From 1 to 4094.'
                            ;
              }
            }
          }
          leaf exter-vlanid {
            description 'External VLAN ID.'
                        ;
            type uint16 {
              range 1..4094 {
                description 'From 1 to 4094.'
                            ;
              }
            }
          }
        }
      }
      container vxlan-permanent-container {
        // if-feature vxlan-arp ;
        description 'Set the vxlan permanent ARP.'
                    ;
        list vxlan-permanent-list {
          description 'Set the vxlan permanent ARP.'
                      ;
          key 'ip intf-name'
              ;
          leaf ip {
            description 'IP address.'
                        ;
            type ncd:ipv4-address ;
          }
          leaf intf-name {
            description 'Interface name.'
                        ;
            type ncd:ifname ;
          }
          leaf mac {
            description 'MAC address.'
                        ;
            type ncd:mac-address ;
            mandatory true ;
          }
          container vxlan-remote-ip {
            description 'The configuration of remote IP address.'
                        ;
            choice remote-ip-type {
              description 'The configuration of remote IP address.'
                          ;
              mandatory true ;
              case remote-ipv4 {
                description 'The configuration of remote IPv4 address.'
                            ;
                leaf ipv4 {
                  description 'Remote IPv4 address.'
                              ;
                  type ncd:ipv4-address ;
                  mandatory true ;
                }
              }
              case remote-ipv6 {
                description 'The configuration type of remote IPv6 address.'
                            ;
                leaf ipv6 {
                  description 'Remote IPv6 address.'
                              ;
                  type ncd:ipv6-address ;
                  mandatory true ;
                }
              }
            }
            ncd:revise-date 2015-12-25 ;
          }
          leaf vtep-intf-name {
            description 'Vtep interface name.'
                        ;
            type ncd:ifname ;
            mandatory true ;
          }
          leaf vxlan-id {
            description 'VXLAN ID.'
                        ;
            type uint32 ;
            mandatory true ;
          }
        }
      }
      container mac-protect-container {
        description 'The specified MAC ARP protection function.'
                    ;
        list mac-protect-list {
          description 'The specified MAC ARP protection function.'
                      ;
          key mac ;
          leaf mac {
            description 'MAC address.'
                        ;
            type ncd:mac-address ;
          }
          leaf protect-num {
            description 'Protect limit number.Its value depends on the performa'
                      + 'nce parameters.'
                        ;
            type uint32 {
              range 1..262144 {
                description 'From 1 to 262144.'
                            ;
              }
            }
            mandatory true ;
          }
        }
      }
      container global-container {
        description 'Commands under global mode about ARP.'
                    ;
        container global {
          description 'Commands under global mode about ARP.'
                      ;
          leaf global-protect-num {
            description 'Protect limit number.Its value depends on the performa'
                      + 'nce parameters.'
                        ;
            type uint32 {
              range 0..262144 {
                description 'From 0 to 262144.'
                            ;
              }
            }
            default 0 ;
          }
          leaf inspect-scr-mac {
            // if-feature inspection-validate ;
            description 'Source MAC dynamic ARP inspection.'
                        ;
            type enumeration {
              enum disable {
                value 0 ;
                description Disable. ;
              }
              enum enable {
                value 1 ;
                description Enable. ;
              }
            }
            default disable ;
          }
          leaf inspect-des-mac {
            // if-feature inspection-validate ;
            description 'Destination MAC dynamic ARP inspection.'
                        ;
            type enumeration {
              enum disable {
                value 0 ;
                description Disable. ;
              }
              enum enable {
                value 4 ;
                description Enable. ;
              }
            }
            default disable ;
          }
          leaf inspect-ip {
            // if-feature inspection-validate ;
            description 'IP address dynamic ARP inspection.'
                        ;
            type enumeration {
              enum disable {
                value 0 ;
                description Disable. ;
              }
              enum enable {
                value 2 ;
                description Enable. ;
              }
            }
            default disable ;
          }
          leaf mac-protect-num {
            description 'The number of ARP entries about common MAC protect fun'
                      + 'ction.Its value depends on the performance parameters.'
                        ;
            type uint32 {
              range 0..262144 {
                description 'From 0 to 262144.'
                            ;
              }
            }
            default 0 ;
          }
          leaf nexthop-keepalive-time {
            // if-feature keepalive-time ;
            description 'The static routing the next-hop ARP keep alive interva'
                      + 'l.'
                        ;
            type uint32 {
              range 10..14400 {
                description 'From 10 to 14400.'
                            ;
              }
            }
            units seconds ;
            default 30 ;
          }
          leaf global-timeout {
            description 'The ARP entry aging time.'
                        ;
            type uint32 {
              range 1..2147483 {
                description 'From 1 to 2147483.'
                            ;
              }
            }
            units seconds ;
            default 14400 ;
          }
          leaf log-flag {
            description 'ARP report log function.'
                        ;
            type enumeration {
              enum on {
                value 0 ;
                description On. ;
              }
              enum off {
                value 1 ;
                description Off. ;
              }
            }
            default off ;
          }
          leaf fast-reply {
            // if-feature fast-reply ;
            description 'ARP fast-reply switch, and the different projects can '
                      + 'have different default values.'
                        ;
            type enumeration {
              enum enable {
                value 1 ;
                description 'Enable fast-reply.'
                            ;
              }
              enum disable {
                value 0 ;
                description 'Disable fast-reply.'
                            ;
              }
            }
            ncd:revise-date 2020-07-08 ;
          }
          leaf fast-reply-mode {
            // if-feature fast-reply ;
            description 'The mode of ARP fast-reply, and the different projects'
                      + ' can have different default values.'
                        ;
            type enumeration {
              enum stateless {
                value 1 ;
                description 'Set stateless.'
                            ;
              }
              enum cache-only {
                value 0 ;
                description 'Set cache-only.'
                            ;
              }
            }
            ncd:revise-date 2020-07-08 ;
          }
          leaf destination-filtered {
            // if-feature destination-filtered ;
            description 'When the ARP proxy function is disabled, ARP packets a'
                      + 're filtered according to the destination IP address.'
                        ;
            type enumeration {
              enum enable {
                value 1 ;
                description Enable. ;
              }
              enum disable {
                value 0 ;
                description Disable. ;
              }
            }
            default disable ;
            ncd:revise-date 2020-07-22 ;
          }
        }
      }
      container gratuitous-proxy-container {
        // if-feature gratuitous-proxy-arp ;
        description 'Set gratuitous proxy ARP.'
                    ;
        list gratuitous-proxy-list {
          description 'Set gratuitous proxy ARP.'
                      ;
          key 'intf-name ip-begin ip-end'
              ;
          leaf intf-name {
            description 'Interface name.'
                        ;
            type ncd:ifname ;
          }
          leaf ip-begin {
            description 'Start IP address.'
                        ;
            type ncd:ipv4-address ;
          }
          leaf ip-end {
            description 'End IP address.'
                        ;
            type ncd:ipv4-address ;
          }
        }
      }
      container inspection-vlan-container {
        // if-feature inspection-vlan ;
        description 'Set VLAN dynamic ARP inspection.'
                    ;
        list inspection-vlan-list {
          description 'Set VLAN dynamic ARP inspection.'
                      ;
          key vlan-id ;
          leaf vlan-id {
            description 'VLAN id.'
                        ;
            type uint16 {
              range 1..4094 {
                description 'From 1 to 4094.'
                            ;
              }
            }
          }
        }
      }
      container acl-container {
        description 'Bind the ACL rule.'
                    ;
        list acl-list {
          description 'Bind the ACL rule.'
                      ;
          key intf-name ;
          leaf intf-name {
            description 'Interface name.'
                        ;
            type ncd:ifname ;
          }
          leaf acl-name {
            description 'ACL rule name.'
                        ;
            type ncd:string-all {
              length 1..31 {
                description 'From 1 to 31.'
                            ;
              }
            }
            mandatory true ;
          }
        }
      }
      container conflict-notify-container {
        // if-feature conflict-notify ;
        description 'Set ARP conflict notify.'
                    ;
        list conflict-notify-list {
          description 'Set ARP conflict notify.'
                      ;
          key intf-name ;
          leaf intf-name {
            description 'Interface name.'
                        ;
            type ncd:ifname ;
          }
          leaf conflict-notify-flag {
            description 'Conflict notify function flag.'
                        ;
            type enumeration {
              enum enable {
                value 1 ;
                description Enable. ;
              }
              enum disable {
                value 2 ;
                description Disable. ;
              }
            }
            mandatory true ;
          }
        }
      }
      container detect-container {
        // if-feature detect ;
        description 'Enable detect snooping function.'
                    ;
        list detect-list {
          description 'Enable detect snooping function.'
                      ;
          key intf-name ;
          leaf intf-name {
            description 'Interface name.'
                        ;
            type ncd:ifname ;
          }
          leaf detect-flag {
            description 'Detect flag.'
                        ;
            type enumeration {
              enum enable {
                value 1 ;
                description Enable. ;
              }
              enum disable {
                value 2 ;
                description Disable. ;
              }
            }
            default disable ;
          }
          leaf detect-mode {
            description 'Detect mode.'
                        ;
            type enumeration {
              enum packet {
                value 1 ;
                description 'Detect mode packet.'
                            ;
              }
              enum event {
                value 2 ;
                description 'Detect mode event.'
                            ;
              }
            }
            default packet ;
          }
          leaf loop-time {
            description 'Loop time.'
                        ;
            type int32 {
              range 2..14400 {
                description 'From 2 to 14400.'
                            ;
              }
            }
            units seconds ;
            default 60 ;
          }
          leaf retry-times {
            description 'Retry times.'
                        ;
            type uint32 {
              range 1..10 {
                description 'From 1 to 10.'
                            ;
              }
            }
            default 3 ;
          }
          leaf timeout {
            description Delay. ;
            type uint32 {
              range 1..60 {
                description 'From 1 to 60.'
                            ;
              }
            }
            units seconds ;
            default 3 ;
          }
        }
      }
      container inspection-trust-container {
        // if-feature inspection-trust ;
        description 'Set dynamic ARP inspection trust.'
                    ;
        list inspection-trust-list {
          description 'Set dynamic ARP inspection trust.'
                      ;
          key intf-name ;
          leaf intf-name {
            description 'Interface name.'
                        ;
            type ncd:ifname ;
          }
          leaf inspection-trust {
            description 'Dynamic ARP inspection trust.'
                        ;
            type enumeration {
              enum enable {
                value 1 ;
                description Enable. ;
              }
              enum disable {
                value 2 ;
                description Disable. ;
              }
            }
            mandatory true ;
          }
        }
      }
      container inspection-limit-container {
        // if-feature inspection-limit ;
        description 'Set dynamic ARP inspection limit speed.'
                    ;
        list inspection-limit-list {
          description 'Set dynamic ARP inspection limit speed.'
                      ;
          key intf-name ;
          leaf intf-name {
            description 'Interface name.'
                        ;
            type ncd:ifname ;
          }
          leaf inspection-limit {
            description 'Dynamic ARP inspection limit speed.'
                        ;
            type uint32 {
              range 1..100 {
                description 'From 1 to 100.'
                            ;
              }
            }
            units 'packets per second'
                  ;
            mandatory true ;
          }
        }
      }
      container clear-permanent {
        description 'Clear permanent ARP entries.'
                    ;
        choice permanent-choice {
          description 'Clear permanent ARP entries.'
                      ;
          case interface-case {
            description 'Interface name.'
                        ;
            leaf interface {
              description 'Interface name.'
                          ;
              type ncd:ifname ;
            }
          }
          case global-case {
            description 'Clear all permanent ARP entries.'
                        ;
            leaf global {
              description 'Clear all permanent ARP entries.'
                          ;
              type empty ;
            }
          }
        }
      }
      container inspection-container {
        // if-feature inspection ;
        description 'ARP DAI inspection.'
                    ;
        list inspection-list {
          description 'ARP DAI inspection.'
                      ;
          key intf-name ;
          leaf intf-name {
            description 'Interface name.'
                        ;
            type ncd:ifname ;
          }
          leaf inspection-flag {
            description 'Enable or disable ARP DAI inspection function.'
                        ;
            type enumeration {
              enum enable {
                value 1 ;
                description Enable. ;
              }
              enum disable {
                value 2 ;
                description Disable. ;
              }
            }
            default disable ;
          }
        }
      }
      container vxlan-evpn-container {
        // if-feature arp-vxlan-evpn ;
        description 'Set ARP VxLAN EVPN configurations.'
                    ;
        list vxlan-evpn-list {
          description 'Set ARP VxLAN EVPN configurations.'
                      ;
          key vxlan-id ;
          leaf vxlan-id {
            description 'VxLAN ID.'
                        ;
            type uint32 {
              range 1..16777215 ;
            }
          }
          leaf proxy {
            description 'Set ARP VxLAN EVPN proxy function.'
                        ;
            type enumeration {
              enum enable {
                value 1 ;
                description Enable. ;
              }
              enum disable {
                value 0 ;
                description Disable. ;
              }
            }
            default disable ;
          }
          leaf l3-proxy {
            description 'Set ARP VxLAN EVPN L3 proxy function.'
                        ;
            type enumeration {
              enum enable {
                value 1 ;
                description Enable. ;
              }
              enum disable {
                value 0 ;
                description Disable. ;
              }
            }
            default disable ;
          }
          leaf double-label {
            description 'Set whether create remote ARP entry on VxLAN-EVPN doub'
                      + 'le label.'
                        ;
            type enumeration {
              enum enable {
                value 1 ;
                description Enable. ;
              }
              enum disable {
                value 0 ;
                description Disable. ;
              }
            }
            default enable ;
            ncd:revise-date 2017-08-03 ;
          }
        }
        ncd:revise-date 2017-07-05 ;
      }
      container vpls-evpns {
        // if-feature arp-vpls-evpn ;
        description 'Set ARP VPLS EVPN configurations.'
                    ;
        list vpls-evpn {
          description 'Set ARP VPLS EVPN configurations.'
                      ;
          key instance-name ;
          leaf instance-name {
            description 'The name of VPLS instance.'
                        ;
            type string ;
          }
          leaf proxy {
            description 'Set ARP VPLS EVPN proxy function.The default value is '
                      + 'determined by the performance parameter.'
                        ;
            type enumeration {
              enum enable {
                value 1 ;
                description Enable. ;
              }
              enum disable {
                value 0 ;
                description Disable. ;
              }
            }
          }
          leaf l3-proxy {
            description 'Set ARP VPLS EVPN L3 proxy function.'
                        ;
            type enumeration {
              enum enable {
                value 1 ;
                description Enable. ;
              }
              enum disable {
                value 0 ;
                description Disable. ;
              }
            }
            default disable ;
          }
          leaf broadcast {
            // if-feature arp-vpls-evpn-l2-proxy ;
            description 'Set ARP VPLS EVPN L2 proxy broadcast function.'
                        ;
            type enumeration {
              enum enable {
                value 1 ;
                description Enable. ;
              }
              enum disable {
                value 0 ;
                description Disable. ;
              }
            }
            default enable ;
            ncd:revise-date 2018-02-07 ;
          }
          leaf proxy-suppress {
            // if-feature arp-vpls-evpn-l2-proxy ;
            description 'Set ARP VPLS EVPN L2 proxy proxy-suppress function.'
                        ;
            type enumeration {
              enum enable {
                value 1 ;
                description Enable. ;
              }
              enum disable {
                value 0 ;
                description Disable. ;
              }
            }
            default disable ;
            ncd:revise-date 2018-02-07 ;
          }
          leaf probe-delay {
            // if-feature arp-vpls-evpn-l2-proxy ;
            description 'Set ARP VPLS EVPN probe delay function.'
                        ;
            type uint32 {
              range 1..60 {
                description 1-60s ;
              }
            }
            ncd:revise-date 2019-12-22 ;
          }
          leaf description {
            // if-feature arp-vpls-evpn-description ;
            description 'The description of VPLS EVPN ARP.'
                        ;
            type ncd:string-with-blank {
              length 1..64 {
                description 'The description range of instance'
                            ;
              }
            }
            ncd:revise-date 2020-05-23 ;
          }
        }
        ncd:revise-date 2017-12-25 ;
      }
    }
  }
  container operation {
    config false ;
    description 'ARP operation commands.'
                ;
    container arp {
      description 'ARP operation commands.'
                  ;
      container to-static {
        description 'The dynamic ARP entry changes to the static type of the en'
                  + 'try.'
                    ;
        container to-static-container {
          description 'The static ARP entry changes to the dynamic type of the '
                    + 'entry.'
                      ;
          choice tostatic-choice {
            description 'The dynamic ARP entry changes to the static type of th'
                      + 'e entry.'
                        ;
            case interface-case {
              description 'Interface name.'
                          ;
              leaf intf-name {
                description 'Interface name.'
                            ;
                type ncd:ifname ;
              }
            }
            case global-case {
              description 'All dynamic ARP entries change to static ARP entries.'
                          ;
              leaf global {
                description 'All dynamic ARP entries change to static ARP entri'
                          + 'es.'
                            ;
                type empty ;
              }
            }
          }
        }
      }
      container scan {
        // if-feature scan ;
        description 'ARP scan under the interface.'
                    ;
        list scan {
          description 'ARP scan under the interface.'
                      ;
          key 'interface ip-begin ip-end'
              ;
          leaf interface {
            description 'Interface name.'
                        ;
            type ncd:ifname ;
          }
          leaf ip-begin {
            description 'Start IP address.'
                        ;
            type ncd:ipv4-address ;
          }
          leaf ip-end {
            description 'End IP address.'
                        ;
            type ncd:ipv4-address ;
          }
        }
      }
      container to-permanent {
        // if-feature to-permanent ;
        description 'The dynamic ARP entry changes to the permanent type of the'
                  + ' entry.'
                    ;
        container to-permanent-container {
          description 'The dynamic ARP entry changes to the permanent type of t'
                    + 'he entry.'
                      ;
          leaf interface {
            description 'interface name.'
                        ;
            type ncd:ifname ;
          }
        }
      }
      container clear {
        description 'Clear ARP entries.'
                    ;
        container tostatic {
          description 'Clear dynamic-to-static ARP entries.'
                      ;
          choice to-static-choice {
            description 'Clear dynamic-to-static ARP entries.'
                        ;
            case interface-case {
              description 'Interface name.'
                          ;
              leaf interface {
                description 'Interface name.'
                            ;
                type ncd:ifname ;
              }
            }
            case global-case {
              description 'Clear all dynamic-to-static ARP entries.'
                          ;
              leaf global {
                description 'Clear all dynamic-to-static ARP entries.'
                            ;
                type empty ;
              }
            }
          }
        }
        container statistics {
          // if-feature clear-arp-statistics ;
          description 'Clear the ARP packet statistics counting.'
                      ;
          leaf interface {
            description 'Interface name.'
                        ;
            type ncd:ifname ;
          }
        }
        container dynamic {
          description 'Clear dynamic ARP entries.'
                      ;
          choice clear-dynamic {
            description 'Clear dynamic ARP entries.'
                        ;
            case ip {
              description 'IP address.'
                          ;
              leaf ip {
                description 'IP address.'
                            ;
                type ncd:ipv4-address ;
              }
            }
            case ip-range {
              description 'IP address range.'
                          ;
              leaf start-ip {
                description 'Start IP address.'
                            ;
                type ncd:ipv4-address ;
                mandatory true ;
              }
              leaf end-ip {
                description 'End IP address.'
                            ;
                type ncd:ipv4-address ;
                mandatory true ;
              }
            }
            case mac {
              leaf mac {
                description 'MAC address.'
                            ;
                type ncd:mac-address ;
              }
            }
            case interface {
              description 'interface name.'
                          ;
              container interface-dynamic {
                description 'Clear dynamic ARP entries under the interface.'
                            ;
                choice clear-interface {
                  description 'Clear dynamic ARP entries under the interface.'
                              ;
                  case ip-case {
                    description 'IP address.'
                                ;
                    container ip {
                      description 'IP address.'
                                  ;
                      leaf interface-ip {
                        description 'IP address.'
                                    ;
                        type ncd:ipv4-address ;
                        mandatory true ;
                      }
                      leaf interface-name {
                        description 'Interface name.'
                                    ;
                        type ncd:ifname ;
                        mandatory true ;
                      }
                    }
                  }
                  case ip-range-case {
                    description 'IP address range.'
                                ;
                    container ip-range {
                      description 'IP address range.'
                                  ;
                      leaf start-ip {
                        description 'Start IP address.'
                                    ;
                        type ncd:ipv4-address ;
                        mandatory true ;
                      }
                      leaf end-ip {
                        description 'End IP address.'
                                    ;
                        type ncd:ipv4-address ;
                        mandatory true ;
                      }
                      leaf interface-name {
                        description 'Interface name.'
                                    ;
                        type ncd:ifname ;
                        mandatory true ;
                      }
                    }
                  }
                  case mac-case {
                    description 'MAC address.'
                                ;
                    container mac {
                      description 'MAC address.'
                                  ;
                      leaf interface-mac {
                        description 'MAC address.'
                                    ;
                        type ncd:mac-address ;
                        mandatory true ;
                      }
                      leaf interface-name {
                        description 'Interface name.'
                                    ;
                        type ncd:ifname ;
                        mandatory true ;
                      }
                    }
                  }
                  case interface-all-case {
                    description 'Delete all dynamic ARP entries under the inter'
                              + 'face.'
                                ;
                    container interface-all {
                      description 'Delete all dynamic ARP entries under the int'
                                + 'erface.'
                                  ;
                      leaf interface-name {
                        description 'Interface name.'
                                    ;
                        type ncd:ifname ;
                        mandatory true ;
                      }
                    }
                  }
                }
              }
            }
            case type {
              description 'Clear ARP entry by type.'
                          ;
              leaf type {
                description 'The type of ARP entry.'
                            ;
                type enumeration {
                  enum dynamic-learning {
                    value 1 ;
                    description 'Dynamic learning ARP.'
                                ;
                  }
                  enum DHCP {
                    value 2 ;
                    description 'DHCP ARP.'
                                ;
                  }
                  enum controller {
                    value 3 ;
                    description 'Controller ARP.'
                                ;
                  }
                }
                mandatory true ;
              }
              ncd:revise-date 2016-03-17 ;
            }
            case global {
              description 'Clear all dynamic ARP entries.'
                          ;
              leaf global-dynamic {
                description 'Clear all dynamic ARP entries.'
                            ;
                type empty ;
              }
            }
          }
        }
        container static {
          description 'Clear the static ARP entry.'
                      ;
          choice clear-static {
            description 'Clear the static ARP entry.'
                        ;
            case interface {
              description 'Clear static ARP entries under the interface.'
                          ;
              leaf interface {
                description 'Clear static ARP entries under the interface.'
                            ;
                type ncd:ifname ;
              }
            }
            case global {
              description 'Clear all static ARP entries.'
                          ;
              leaf global-static {
                description 'Clear all static ARP entries.'
                            ;
                type empty ;
              }
            }
          }
        }
      }
      container static {
        description 'Set the static ARP.'
                    ;
        list static-list {
          description 'Set the static ARP.'
                      ;
          key 'ip intf-name'
              ;
          leaf ip {
            description 'IP address.'
                        ;
            type ncd:ipv4-address ;
          }
          leaf intf-name {
            description 'Interface name.'
                        ;
            type ncd:ifname ;
          }
          leaf mac {
            description 'MAC address.'
                        ;
            type ncd:mac-address ;
            mandatory true ;
          }
          leaf inter-vlanid {
            description 'Internal VLAN ID.'
                        ;
            type uint16 {
              range 1..4094 {
                description 'From 1 to 4094.'
                            ;
              }
            }
          }
          leaf exter-vlanid {
            description 'External VLAN ID.'
                        ;
            type uint16 {
              range 1..4094 {
                description 'From 1 to 4094.'
                            ;
              }
            }
          }
        }
      }
      container no-static {
        description 'Delete a static ARP entry.'
                    ;
        list no-static-list {
          description 'Delete a static ARP entry.'
                      ;
          key 'ip intf-name'
              ;
          leaf ip {
            description 'IP address.'
                        ;
            type ncd:ipv4-address ;
          }
          leaf intf-name {
            description 'Interface name.'
                        ;
            type ncd:ifname ;
          }
        }
      }
      container no-to-static {
        description 'The static ARP entry changes to the dynamic type of the en'
                  + 'try.'
                    ;
        container no-to-static-container {
          description 'The static ARP entry changes to the dynamic type of the '
                    + 'entry.'
                      ;
          choice no-to-static-choice {
            description 'The dynamic ARP entry changes to the static type of th'
                      + 'e entry.'
                        ;
            case interface-case {
              description 'Interface name.'
                          ;
              leaf intf-name {
                description 'Interface name.'
                            ;
                type ncd:ifname ;
              }
            }
            case global-case {
              description 'All dynamic ARP entries change to static ARP entries.'
                          ;
              leaf global {
                description 'All dynamic ARP entries change to static ARP entri'
                          + 'es.'
                            ;
                type empty ;
              }
            }
          }
        }
      }
    }
  }
  container state {
    config false ;
    description 'Arp State Commod'
                ;
    container arp {
      description 'The show of ARP commod'
                  ;
      container arp-item {
        description 'Show Arp Item Node'
                    ;
        list brief {
          description 'Show Arp Item List'
                      ;
          key 'ip-address hardware-address interface-name exter-vlanid inter-vl'
            + 'anid item-type'
              ;
          leaf ip-address {
            description 'IP Address'
                        ;
            type ncd:ipv4-address ;
          }
          leaf hardware-address {
            description 'MAC Address'
                        ;
            type ncd:mac-address ;
          }
          leaf interface-name {
            description 'Interface Name'
                        ;
            type ncd:ifname ;
          }
          leaf exter-vlanid {
            description 'Exter Vlan ID'
                        ;
            type uint16 ;
          }
          leaf inter-vlanid {
            description 'Inter Vlan ID'
                        ;
            type uint16 ;
          }
          leaf item-type {
            description 'ARP Item Type'
                        ;
            type uint8 ;
          }
          leaf sub-interface-name {
            description 'Sub Interface Name'
                        ;
            type ncd:ifname ;
          }
          leaf age {
            description 'Show Dynamic Arp Time Or Show Arp Item Type'
                        ;
            type ncd:string-all ;
          }
          ncd:select ip-address ;
          ncd:select interface-name ;
          ncd:select exter-vlanid ;
          ncd:select inter-vlanid ;
          ncd:select item-type ;
          ncd:select 'ip-address interface-name'
                     ;
          ncd:select 'hardware-address interface-name'
                     ;
          ncd:select 'interface-name item-type'
                     ;
        }
        list detail {
          description 'Show Arp Item Detail Infomation'
                      ;
          key 'ip-address interface-name'
              ;
          leaf ip-address {
            description 'IP Address'
                        ;
            type ncd:ipv4-address ;
          }
          leaf interface-name {
            description 'Interface Name'
                        ;
            type ncd:ifname ;
          }
          leaf age {
            description 'Show Dynamic Arp Time Or Show Arp Item Type'
                        ;
            type ncd:string-all ;
          }
          leaf hardware-address {
            description 'MAC Address'
                        ;
            type ncd:mac-address ;
          }
          leaf physical-interface-name {
            description 'Physical Interface Name'
                        ;
            type ncd:ifname ;
          }
          leaf item-attribute {
            description 'Item Attribute'
                        ;
            type ncd:string-all ;
          }
          leaf item-class {
            description 'Item Class'
                        ;
            type ncd:string-all ;
          }
          leaf learn-time-stamp {
            description 'Learn Time Stamp'
                        ;
            type uint32 ;
          }
          leaf learn-ip-address {
            description 'Learn IP Address'
                        ;
            type ncd:ipv4-address ;
          }
          leaf item-vrf {
            description 'Item VRF'
                        ;
            type ncd:string-all ;
          }
          leaf data-source {
            description 'Data Source'
                        ;
            type ncd:string-all ;
          }
          leaf cps-trust {
            description 'CPS Trust'
                        ;
            type ncd:string-all ;
          }
          leaf vtep-interface-name {
            description 'Vtep Interface Name'
                        ;
            type ncd:ifname ;
          }
          leaf vxlan-id {
            description 'VXLAN ID'
                        ;
            type uint32 ;
          }
          leaf remote-ip {
            description 'Remote IP Address.'
                        ;
            type string ;
          }
          ncd:select 'ip-address interface-name'
                     ;
        }
      }
      container arp-statistics {
        // if-feature clear-arp-statistics ;
        description 'Show Arp Statistics'
                    ;
        list brief {
          description 'Show Arp Statistics Item List'
                      ;
          key interface-name ;
          leaf interface-name {
            description 'Interface Name'
                        ;
            type ncd:ifname ;
          }
          leaf rcv-packets {
            description 'Receive Packets Number'
                        ;
            type uint32 ;
            default 0 ;
          }
          leaf err-packets {
            description 'Error Packets Number'
                        ;
            type uint32 ;
            default 0 ;
          }
          ncd:select interface-name ;
        }
        list detail {
          description 'Show Arp Statistics Item Detail'
                      ;
          key interface-name ;
          leaf interface-name {
            description 'Interface Name'
                        ;
            type ncd:ifname ;
          }
          leaf rcv-packets {
            description 'Receive Packets Number'
                        ;
            type uint32 ;
            default 0 ;
          }
          leaf drop-limit-packets {
            description 'Drop Packets Number For Protect Limit'
                        ;
            type uint32 ;
            default 0 ;
          }
          leaf drop-source-filter-packets {
            description 'Drop Packets Number For Source Filter'
                        ;
            type uint32 ;
            default 0 ;
          }
          leaf drop-learn-limit-packets {
            description 'Drop Packets Number For Learn Limit'
                        ;
            type uint32 ;
            default 0 ;
          }
          leaf drop-speed-packets {
            description 'Drop Packets Number For Port Speed'
                        ;
            type uint32 ;
            default 0 ;
          }
          leaf drop-other-packets {
            description 'Drop Packets Number For Other'
                        ;
            type uint32 ;
            default 0 ;
          }
          ncd:select interface-name ;
        }
      }
      container ip-arp-inspection-interface {
        // if-feature inspection-trust ;
        description 'Show Ip Arp Inspection Interface'
                    ;
        list brief {
          description 'Show Ip Arp Inspection Interface Item'
                      ;
          key interface-name ;
          leaf interface-name {
            description 'Interface Name'
                        ;
            type ncd:ifname ;
          }
          leaf trust-state {
            description 'Trust State'
                        ;
            type ncd:string-all ;
          }
          leaf rate {
            description Rate ;
            type uint32 ;
            units pps ;
            default 0 ;
          }
          ncd:select interface-name ;
        }
      }
      container ip-arp-inspection-vlan {
        // if-feature inspection-vlan ;
        description 'Show Ip Arp Inspection Vlan'
                    ;
        list brief {
          description 'Show Ip Arp Inspection Vlan Item'
                      ;
          key 'vlan-id inspection vlan-name'
              ;
          leaf vlan-id {
            description 'VLAN ID'
                        ;
            type uint16 ;
          }
          leaf inspection {
            description 'Inspection State'
                        ;
            type ncd:string-all ;
          }
          leaf vlan-name {
            description 'VLAN Name'
                        ;
            type ncd:string-all ;
          }
          ncd:select vlan-id ;
          ncd:select inspection ;
          ncd:select vlan-name ;
        }
      }
      container vxlan-arp-item {
        // if-feature vxlan-arp ;
        description 'Show Vxlan Arp Item Node.'
                    ;
        list brief {
          description 'Show Vxlan Arp Item List'
                      ;
          key vnid ;
          leaf vnid {
            description 'VNI ID.'
                        ;
            type int32 ;
          }
          leaf ip-address {
            description 'IP address.'
                        ;
            type ncd:ipv4-address ;
            mandatory true ;
          }
          leaf mac {
            description 'MAC address.'
                        ;
            type ncd:mac-address ;
            mandatory true ;
          }
          leaf interface {
            description 'Interface name.'
                        ;
            type ncd:ifname ;
            mandatory true ;
          }
          leaf vtep-interface {
            description 'VTEP interface.'
                        ;
            type ncd:ifname ;
            mandatory true ;
          }
          leaf remote-ip {
            description 'Remote IP.'
                        ;
            type string ;
            mandatory true ;
          }
          ncd:select vnid ;
        }
      }
      container l2-proxy-items {
        // if-feature get-l2-proxy-item ;
        description 'Show ARP l2-proxy item'
                    ;
        list l2-proxy-item {
          description 'Show ARP l2-proxy item node.'
                      ;
          key 'ip-address vpls-name'
              ;
          leaf ip-address {
            description 'IP address'
                        ;
            type ncd:ipv4-address ;
          }
          leaf vpls-name {
            description 'VPLS EVPN instance name'
                        ;
            type ncd:string-all ;
          }
          leaf mac {
            description 'MAC address'
                        ;
            type ncd:mac-address ;
          }
          leaf item-type {
            description 'Item type'
                        ;
            type ncd:string-all ;
          }
          ncd:select vpls-name ;
        }
        ncd:revise-date 2020-05-06 ;
      }
    }
  }
}
