module zxr10-platform-oc {

  yang-version "1";

  // namespace
  namespace "http://www.zte.com.cn/zxr10/netconf/schema/rosng/zxr10-platform-oc";

  prefix "zte-platform";

  // import some basic types
  import openconfig-platform { prefix oc-platform; }
  import openconfig-types { prefix oc-types; }

  // meta
  organization "ZTE Corporation";

  contact "ZTE Corporation  \n"
        + "   Nanjing Institute of ZTE Corporation \n"
        + "   No.68 Zijinghua Rd. Yuhuatai District, Nanjing, China \n"
        + '   Tel: +86-25-52870000'
          ;

  description
    "The netconf module to describe the System Management";

  revision "2020-07-07" {
    description
      "add augment uptime leaf";
  }

  // grouping statements

  grouping platform-component-state {
    description
      "the operational state of system statistics.";

    leaf uptime {
        type uint32;
        description
          "Power on time of the board, Time interval from board power up to this point.";
    }
  }

  // augment statements
  augment "/oc-platform:components/oc-platform:component/oc-platform:state" {
    description
      "The board uptime.";

    uses platform-component-state;
  }

  // rpc statements

  // notification statements
}
