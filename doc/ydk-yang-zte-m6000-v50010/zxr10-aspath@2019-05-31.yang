module zxr10-aspath {
  namespace 'http://www.zte.com.cn/zxr10/netconf/schema/rosng/aspath'
            ;
  prefix aspath ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe aspath.'
              ;
  revision 2019-05-31 {
    description '1.Add the containers:/configuration/as-path/color-lists and /c'
              + 'onfiguration/as-path/aspath-list-standards.'
                ;
  }
  revision 2018-02-09 {
    description '1.Add the containers:/configuration/as-path/aspath-name-acls.'
                ;
  }
  revision 2013-11-26 {
    description 'Initial version'
                ;
  }
  container configuration {
    description 'Configuration model.'
                ;
    container as-path {
      description "ASPATH's list module."
                  ;
      container aspath-acls {
        description "Set ASPATH's list module."
                    ;
        list aspath-acl {
          description "Set ASPATH's list module."
                      ;
          key 'aspath-acl-number deny-permit regular-expression'
              ;
          leaf aspath-acl-number {
            description "Set ASPATH's access list number."
                        ;
            type uint16 {
              range 1..199 {
                description 'The ange of ASPATH access list name is from 1 to 1'
                          + '99.'
                            ;
              }
            }
          }
          leaf deny-permit {
            description 'Deny:Specify packets to reject;'+"\n"
                      + 'Permit:Specify packets to permit.'
                        ;
            type enumeration {
              enum deny {
                value 0 ;
                description 'Deny:Specify packets to reject.'
                            ;
              }
              enum permit {
                value 1 ;
                description 'Permit:Specify packets to permit.'
                            ;
              }
            }
          }
          leaf regular-expression {
            description 'A regular-expression to match the BGP AS paths.'
                        ;
            type ncd:string-with-blank {
              length 1..100 {
                description 'Regular-expression length is between 1 and 100(1~1'
                          + '00).'
                            ;
              }
            }
          }
        }
      }
      container aspath-name-acls {
        description "Set ASPATH's list module."
                    ;
        list aspath-name-acl {
          description "Set ASPATH's list module."
                      ;
          key 'aspath-acl-name deny-permit regular-expression'
              ;
          leaf aspath-acl-name {
            description "Set ASPATH's access list name."
                        ;
            type string {
              length 1..31 ;
            }
          }
          leaf deny-permit {
            description 'Deny:Specify packets to reject;'+"\n"
                      + 'Permit:Specify packets to permit.'
                        ;
            type enumeration {
              enum deny {
                value 0 ;
                description 'Deny:Specify packets to reject.'
                            ;
              }
              enum permit {
                value 1 ;
                description 'Permit:Specify packets to permit.'
                            ;
              }
            }
          }
          leaf regular-expression {
            description 'A regular-expression to match the BGP AS paths.'
                        ;
            type ncd:string-with-blank {
              length 1..100 {
                description 'Regular-expression length is between 1 and 100(1~1'
                          + '00).'
                            ;
              }
            }
          }
        }
        ncd:revise-date 2018-02-09 ;
      }
      container color-lists {
        description "Set color's list module."
                    ;
        list color-list {
          description "Set color's list module."
                      ;
          key 'color-name color-value'
              ;
          leaf color-name {
            description 'Set color list name.'
                        ;
            type string ;
          }
          leaf color-value {
            description 'Set color value.'
                        ;
            type uint32 {
              range 1..4294967295 {
                description 'The range of color value is from 1 to 4294967295.'
                            ;
              }
            }
          }
        }
        ncd:revise-date 2019-05-31 ;
      }
      container aspath-list-standards {
        description 'AS path access list(standard).'
                    ;
        list aspath-list-standard {
          description 'AS path access list(standard).'
                      ;
          key 'aspath-name aspath-seq'
              ;
          leaf aspath-name {
            description 'AS path access list name(standard).'
                        ;
            type string {
              length 1..31 ;
            }
          }
          leaf aspath-seq {
            description 'AS path access list sequence number(standard).'
                        ;
            type uint16 {
              range 0..65535 ;
            }
          }
          leaf aspath-value {
            description 'AS number.'
                        ;
            type union {
              type uint16 {
                range 1..65535 {
                  description 'The range of value is from 1 to 65535.'
                              ;
                }
              }
              type ncd:asn-dot ;
            }
            mandatory true ;
          }
          leaf aspath-count {
            description 'AS count.'
                        ;
            type uint8 {
              range 1..255 ;
            }
            mandatory true ;
          }
        }
        ncd:revise-date 2019-05-31 ;
      }
    }
  }
}
