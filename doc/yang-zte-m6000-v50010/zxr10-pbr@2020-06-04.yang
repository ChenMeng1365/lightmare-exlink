module zxr10-pbr {
  namespace 'http://www.zte.com.cn/zxr10/netconf/schema/rosng/pbr'
            ;
  prefix pbr ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf model to describe policy-based routing (PBR). PBR is'
            + ' a technique used to make routing decisions based on policies se'
            + 't by the network administrator.Through the application of PBR on'
            + ' a router, the router according to the route-map decided through'
            + ' the router packet handling.'
              ;
  revision 2020-06-04 {
    description 'Modify the range of routemap-name.'
                ;
  }
  revision 2017-07-25 {
    description 'Add V6000 project label.'
                ;
  }
  revision 2013-09-13 {
    description 'Initial version.'
                ;
  }
  container configuration {
    description 'Configuration model info.'
                ;
    container pbr {
      description 'PBR module'
                  ;
      container pbrs-v4 {
        description 'V4 PBR'
                    ;
        list pbr-v4 {
          description 'Configure of v4 PBR, support for Ethernet physical inter'
                    + 'face, POS interface and the SG interface.'
                      ;
          key interface-name ;
          leaf interface-name {
            description 'Interface name'
                        ;
            type ncd:ifname ;
          }
          leaf routemap-name {
            description 'Routemap name'
                        ;
            type string {
              length 1..200 {
                description 'The length of routemap name is from 1 to 200.'
                            ;
              }
            }
            mandatory true ;
          }
        }
      }
      container pbrs-v6 {
        description 'V6 PBR'
                    ;
        list pbr-v6 {
          description 'Configure of v6 PBR, support for Ethernet physical inter'
                    + 'face, POS interface and the SG interface.'
                      ;
          key interface-name ;
          leaf interface-name {
            description 'Interface name'
                        ;
            type ncd:ifname ;
          }
          leaf routemap-name {
            description 'Routemap name'
                        ;
            type string {
              length 1..200 {
                description 'The length of routemap name is from 1 to 200.'
                            ;
              }
            }
            mandatory true ;
          }
        }
      }
    }
  }
}
