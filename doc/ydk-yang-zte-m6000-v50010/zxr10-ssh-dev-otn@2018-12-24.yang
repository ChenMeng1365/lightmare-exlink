module zxr10-ssh-dev-otn {
  namespace 'http://www.zte.com.cn/zxr10/netconf/schema/rosng/zxr10-ssh-dev-otn'
            ;
  prefix ssh-dev-otn ;
  import zxr10-ssh {
    prefix ssh ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2018-12-24 {
    description '1.Add deviation /ssh:configuration/ssh:ssh/ssh:ssh-server/ssh:'
              + 'authentication/ssh:user/ssh:key-name.'+"\n"
              + '2.Add devation /ssh:state/ssh:ssh/ssh:public-key/ssh:key-name.'
              + ''+"\n"
              + '3.Add devation /ssh:operation/ssh:ssh/ssh:clear/ssh:public-key'
              + '/ssh:key-name.'
                ;
  }
  deviation '/ssh:configuration/ssh:ssh/ssh:ssh-server/ssh:authentication/ssh:u'
          + 'ser/ssh:key-name'
            {
    description 'Replace this node range,from 1-31 to 1-64.'
                ;
    deviate replace {
      type string {
        length 1..64 ;
      }
    }
  }
  deviation /ssh:state/ssh:ssh/ssh:public-key/ssh:key-name {
    description 'Replace this node range,from 1-31 to 1-64.'
                ;
    deviate replace {
      type string {
        length 1..64 ;
      }
    }
  }
  deviation /ssh:operation/ssh:ssh/ssh:clear/ssh:public-key/ssh:key-name {
    description 'Replace this node range,from 1-31 to 1-64.'
                ;
    deviate replace {
      type string {
        length 1..64 ;
      }
    }
  }
}
