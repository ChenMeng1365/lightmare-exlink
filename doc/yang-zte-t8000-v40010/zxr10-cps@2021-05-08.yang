module zxr10-cps {
  namespace 'http://www.zte.com.cn/zxr10/netconf/schema/rosng/cps'
            ;
  prefix cps ;
  yang-version 1 ;
  import zxr10-netconf-defs {
    prefix ncd ;
    revision-date 2014-06-24 ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe CPS(control plane security).'
              ;
  revision 2021-05-08 {
    description 'Add cps-cmd feature for 61v5_1.'
                ;
  }
  revision 2021-03-04 {
    description 'Modify if-feature of statistics-interval,from cps-router-cmd t'
              + 'o statistics-interval.'
                ;
  }
  revision 2020-12-07 {
    description 'Add an enumeration value pim-crp-known,gprc-known,gprc-default'
              + ',telemetry-udp for flowtype-name.'
                ;
  }
  revision 2020-09-25 {
    description 'Add feature of defend-policy-whitelist.'+"\n"
              + 'Add feature of defend-policy-blacklist.'
                ;
  }
  revision 2020-04-14 {
    description 'Add node:/configuration/cps/mngport-ip-packets-forward.'
                ;
  }
  revision 2020-04-02 {
    description 'Add feature for cps statistics.'
                ;
  }
  revision 2020-01-09 {
    description 'Add an enumeration value uni-nd-known for flowtype-name.'
                ;
  }
  revision 2019-11-06 {
    description 'Add an enumeration value openflow for flowtype-name.'+"\n"
              + 'Add an enumeration value lldp and openflow for mng protocol.'
                ;
  }
  revision 2019-07-26 {
    description 'Add an enumeration value pim-low for flowtype-name.'
                ;
  }
  revision 2019-06-26 {
    description 'Add nodes of /configuration/cps/defend-policy.'
                ;
  }
  revision 2019-04-09 {
    description 'Add max value (Perf-code)for'+"\n"
              + '/configuration/cps/flow/limits/limit/rate-imit'+"\n"
              + '/configuration/cps/flow/limits/limit/quota-limit'+"\n"
              + '/configuration/cps/flow/limit-profiles/limit-profile-item/rate'
              + '-limit'+"\n"
              + '/configuration/cps/flow/limit-profiles/limit-profile-item/quot'
              + 'a-limit'
                ;
  }
  revision 2018-11-29 {
    description 'Add the lable for 5960.'
                ;
  }
  revision 2015-07-27 {
    description "clear state node's configuration flag."
                ;
  }
  revision 2015-07-15 {
    description 'add flowtype enumurations.'
                ;
  }
  revision 2015-05-26 {
    description 'modify sequence between backpress-profiles node & apply-backpr'
              + 'ess-profiles node.'+"\n"
              + 'modify sequence between limit-profiles node & apply-limit-prof'
              + 'iles node.'
                ;
  }
  revision 2015-03-09 {
    description "modify ctm queue-depth & rate-limit destcpu leaf node's dataty"
              + "pe from string to enum."
                ;
  }
  revision 2015-01-11 {
    description "split state cps statistics flow-statistics list into three lis"
              + "ts:
\ncpu-statistics,interface-statistics,summary-statistics.
"
              + "\nadd interface-statistics leaf node:upsend-rate,which means u"
              + "psendpacket's rate
\ninpacket-rate,which means total inpacket'"
              + "s rate.
\nremove all cps nodes in state mode,except for statis"
              + "tics."
                ;
  }
  revision 2015-01-06 {
    description "modify operation cps clear flowtype statistics leaf's datatype"
              + " to empty
\nmodify operation cps clear flowtype from list to c"
              + "ontainer
\nmodify operation cps clear gtsm statistics leaf's d"
              + "atatype to empty
\nmodify operation cps clear gtsm from list t"
              + "o container
\nmodify state cps statistics flow-statistics summ"
              + "ary leaf's datatype to empty"
                ;
  }
  revision 2015-01-05 {
    description 'modify logical cpu regexpression,fix 613003103671 probolem.'
                ;
  }
  revision 2014-07-22 {
    description 'Modify ctm queue & rate configuration and state,change destcpu'
              + ' type form string to enum.'
                ;
  }
  revision 2014-07-14 {
    description 'Add flowtype name:openflow-controller,openflow-normal,cps-log'
                ;
  }
  revision 2014-05-15 {
    description "Modify mngport-filter leaf node \"any\"'s range from 0~1 to 1~"
              + "1."
                ;
  }
  revision 2014-04-25 {
    description 'Modify flowtype statistics summary range from 0-1 to 1-1.'
                ;
  }
  revision 2014-03-19 {
    description 'Split CTM queue list into 2 lists, make a distinction between '
              + 'up-priority and down-priority.'+"\n"
              + 'Split Mng-port mac ipv4/v6 into 2 lists, make a distinction be'
              + 'tween any item and specified item.'+"\n"
              + 'Split mng-protocol filter into 2 lists, make a distinction bet'
              + 'ween global item and item configured under interface.'
                ;
  }
  revision 2014-03-06 {
    description 'Modify flow backpress item module,add mimaction to avoid datab'
              + 'ase value problem.'+"\n"
              + 'Modify ctm rate module,split into up ctm-rate list and down ct'
              + 'm-rate list.'
                ;
  }
  revision 2014-01-26 {
    description 'Add new fLowtype enums and mng-protocol enums.'+"\n"
              + 'Modify mng port rate limit range from 0-10000 to 1-10000.'+"\n"
              + 'Modify flow limit interface filter number from 1712 to 504.'+"\n"
              + 'Add Quota limit range:0-85000.'+"\n"
              + 'Modify uint64 derived type.'
                ;
  }
  revision 2014-01-23 {
    description "Modify list:backpress-item  leaf:decline's range to 1-100."
                ;
  }
  revision 2013-10-11 {
    description 'Initial version.'
                ;
  }
  feature cps-router-cmd {
    description 'cps commands for router/ZSR/xGW.'
                ;
  }
  feature cps-cmd {
    description 'feature cps-router-cmd plus 61v5-1.'
                ;
  }
  feature defend-policy-feature {
    description 'Feature for defend policy.'
                ;
  }
  feature cpu-statis {
    description 'Feature for cpu statistics.'
                ;
  }
  feature defend-policy-whitelist {
    description 'Feature for defend-policy-whitelist.'
                ;
  }
  feature defend-policy-blacklist {
    description 'Feature for defend-policy-blacklist.'
                ;
  }
  feature statistics-interval {
    description 'Feature for statistics-interval.'
                ;
  }
  typedef flowtype-name {
    type enumeration {
      enum default {
        value 1 ;
      }
      enum bgp-default {
        value 2 ;
      }
      enum bgp-config {
        value 3 ;
      }
      enum bgp-known {
        value 4 ;
      }
      enum ospf-default {
        value 5 ;
      }
      enum ospf-config {
        value 6 ;
      }
      enum ospf-known {
        value 7 ;
      }
      enum isis-default {
        value 8 ;
      }
      enum isis-known {
        value 9 ;
      }
      enum rip {
        value 10 ;
      }
      enum pim-suppress {
        value 11 ;
      }
      enum pim {
        value 12 ;
      }
      enum igmp-suppress {
        value 13 ;
      }
      enum igmp-default {
        value 14 ;
      }
      enum msdp-default {
        value 15 ;
      }
      enum msdp-known {
        value 16 ;
      }
      enum mld {
        value 17 ;
      }
      enum mvpn {
        value 18 ;
      }
      enum msdp-config {
        value 19 ;
      }
      enum ospf-hello {
        value 20 ;
      }
      enum isis-hello {
        value 21 ;
      }
      enum pim-hello {
        value 22 ;
      }
      enum pim-known {
        value 23 ;
      }
      enum ldp-default {
        value 26 ;
      }
      enum ldp-config {
        value 27 ;
      }
      enum ldp-known {
        value 28 ;
      }
      enum ldp-udp {
        value 29 ;
      }
      enum rsvp {
        value 30 ;
      }
      enum ldp-known-hello {
        value 31 ;
      }
      enum pcep-default {
        value 32 ;
      }
      enum pcep-known {
        value 33 ;
      }
      enum telnet-default {
        value 36 ;
      }
      enum telnet-known {
        value 37 ;
      }
      enum snmp-default {
        value 38 ;
      }
      enum snmp-known {
        value 39 ;
      }
      enum ssh-default {
        value 40 ;
      }
      enum ssh-known {
        value 41 ;
      }
      enum rta-default {
        value 42 ;
      }
      enum rta-known {
        value 43 ;
      }
      enum syslog {
        value 44 ;
      }
      enum ftp-control-known {
        value 45 ;
      }
      enum http-default {
        value 52 ;
      }
      enum tacacs+ {
        value 53 ;
      }
      enum radius {
        value 55 ;
      }
      enum dhcp {
        value 56 ;
      }
      enum ntp {
        value 57 ;
      }
      enum ftp-default {
        value 58 ;
      }
      enum ftp-known {
        value 59 ;
      }
      enum tftp {
        value 60 ;
      }
      enum lsp-ping {
        value 61 ;
      }
      enum mac-ping {
        value 62 ;
      }
      enum bfd-default {
        value 63 ;
      }
      enum bfd-known {
        value 64 ;
      }
      enum vrrp {
        value 65 ;
      }
      enum ipsec {
        value 66 ;
      }
      enum l2tp {
        value 67 ;
      }
      enum icmp-app {
        value 68 ;
      }
      enum portal {
        value 69 ;
      }
      enum eap-authentication {
        value 70 ;
      }
      enum sib-af {
        value 71 ;
      }
      enum trace-udp {
        value 72 ;
      }
      enum dns {
        value 73 ;
      }
      enum netflow-protocol {
        value 74 ;
      }
      enum http-known {
        value 75 ;
      }
      enum twamp-tcp-default {
        value 76 ;
      }
      enum twamp-tcp-known {
        value 77 ;
      }
      enum twamp-udp-default {
        value 78 ;
      }
      enum twamp-udp-known {
        value 79 ;
      }
      enum sibmgr-default {
        value 80 ;
      }
      enum sibmgr-known {
        value 81 ;
      }
      enum single-port-loop {
        value 82 ;
      }
      enum radius-coa-dm {
        value 83 ;
      }
      enum dhcp-known {
        value 84 ;
      }
      enum sqa-general-flow {
        value 85 ;
      }
      enum sflow-protocol {
        value 86 ;
      }
      enum meap-authentication {
        value 87 ;
      }
      enum nhrp {
        value 88 ;
      }
      enum openflow-default {
        value 89 ;
      }
      enum openflow-known {
        value 90 ;
      }
      enum pcp {
        value 91 ;
      }
      enum icmp-default {
        value 92 ;
      }
      enum icmp-control {
        value 93 ;
      }
      enum tcp-default {
        value 94 ;
      }
      enum udp-default {
        value 95 ;
      }
      enum nd {
        value 96 ;
      }
      enum ah {
        value 97 ;
      }
      enum esp {
        value 98 ;
      }
      enum gre {
        value 99 ;
      }
      enum sctp-default {
        value 100 ;
      }
      enum arp-suppress {
        value 102 ;
      }
      enum arp-default {
        value 103 ;
      }
      enum ppp-connect {
        value 104 ;
      }
      enum arp-known {
        value 105 ;
      }
      enum hdlc-control {
        value 106 ;
      }
      enum fr-control {
        value 108 ;
      }
      enum lacp {
        value 110 ;
      }
      enum udld {
        value 111 ;
      }
      enum lldp {
        value 112 ;
      }
      enum stp {
        value 113 ;
      }
      enum pppoe-disc {
        value 114 ;
      }
      enum pppoe-session {
        value 115 ;
      }
      enum groupm {
        value 117 ;
      }
      enum efm {
        value 120 ;
      }
      enum slow-cfm {
        value 121 ;
      }
      enum mc-elam {
        value 122 ;
      }
      enum ssm {
        value 123 ;
      }
      enum evb {
        value 124 ;
      }
      enum nd-known {
        value 125 ;
      }
      enum mmd {
        value 126 ;
      }
      enum ether-loop-detect {
        value 127 ;
      }
      enum pppoe-keepalive {
        value 128 ;
      }
      enum pppoe-padi {
        value 129 ;
      }
      enum 802.1x {
        value 130 ;
      }
      enum hagp {
        value 131 ;
      }
      enum urpf {
        value 142 ;
      }
      enum noarp {
        value 143 ;
      }
      enum nosupervlan {
        value 144 ;
      }
      enum vplsmac {
        value 145 ;
      }
      enum bfd-special {
        value 146 ;
      }
      enum netflow-up {
        value 147 ;
      }
      enum nond {
        value 148 ;
      }
      enum pmtu {
        value 149 ;
      }
      enum special-multidata {
        value 152 ;
      }
      enum ttl1 {
        value 153 ;
      }
      enum llis14 {
        value 154 ;
      }
      enum ipfrag {
        value 155 ;
      }
      enum ipoption {
        value 156 ;
      }
      enum ipv6-special {
        value 157 ;
      }
      enum quick-cfm {
        value 159 ;
      }
      enum netflow-down {
        value 160 ;
      }
      enum nosa {
        value 161 ;
      }
      enum unihttp {
        value 162 ;
      }
      enum special-multidata6 {
        value 164 ;
      }
      enum ipoe-nosession {
        value 165 ;
      }
      enum tunnel-special {
        value 166 ;
      }
      enum nat-alg {
        value 168 ;
      }
      enum nat-nonat {
        value 169 ;
      }
      enum nat-pcp {
        value 170 ;
      }
      enum nat-p2mp-local {
        value 171 ;
      }
      enum nat-li {
        value 172 ;
      }
      enum sflow-up {
        value 173 ;
      }
      enum sflow-down {
        value 174 ;
      }
      enum ptp-normal {
        value 175 ;
      }
      enum ptp-special {
        value 176 ;
      }
      enum mpls-oam-cv {
        value 177 ;
      }
      enum ip-unreachable {
        value 178 ;
      }
      enum atm-oam {
        value 179 ;
      }
      enum slow-mpls-tp-oam {
        value 181 ;
      }
      enum quick-mpls-tp-oam {
        value 182 ;
      }
      enum mpls-tp-aps {
        value 183 ;
      }
      enum multi-hop-access {
        value 184 ;
      }
      enum up-slow-cfm {
        value 185 ;
      }
      enum sdc-access {
        value 186 ;
      }
      enum unihttp_syn {
        value 187 ;
      }
      enum down-fast-cfm {
        value 188 ;
      }
      enum up-fast-cfm {
        value 189 ;
      }
      enum rtelnet-serial-flow {
        value 191 ;
      }
      enum radius-proxy-traffic {
        value 192 ;
      }
      enum firewall-normal {
        value 194 ;
      }
      enum firewall-alg {
        value 195 ;
      }
      enum ipv6-ah-or-esp {
        value 196 ;
      }
      enum openflow-controller {
        value 197 ;
      }
      enum openflow-normal {
        value 198 ;
      }
      enum otn-aps {
        value 199 ;
      }
      enum cps-log {
        value 200 ;
      }
      enum no-nhrp {
        value 201 ;
      }
      enum fast-unihttp {
        value 203 ;
      }
      enum erps {
        value 204 ;
      }
      enum uni-arp-default {
        value 205 ;
      }
      enum uni-arp-known {
        value 206 ;
      }
      enum uni-nd {
        value 207 ;
      }
      enum uni-l2tp {
        value 208 ;
      }
      enum uni-dhcp {
        value 209 ;
      }
      enum openflow-tblmissing {
        value 210 ;
      }
      enum arp-nni {
        value 211 ;
      }
      enum openflow-lldp {
        value 212 ;
      }
      enum openflow-arp {
        value 213 ;
      }
      enum openflow-dhcp {
        value 214 ;
      }
      enum openflow-bgp {
        value 215 ;
      }
      enum openflow-ospf {
        value 216 ;
      }
      enum openflow-icmp {
        value 217 ;
      }
      enum static-arp-trust {
        value 218 ;
      }
      enum vrrp-known {
        value 219 ;
      }
      enum netconf-tls-default {
        value 220 ;
      }
      enum netconf-tls-known {
        value 221 ;
      }
      enum ict-x1 {
        value 222 ;
      }
      enum ict-x2 {
        value 223 ;
      }
      enum arp-protect {
        value 224 ;
      }
      enum nd-protect {
        value 225 ;
      }
      enum dns-snooping {
        value 227 ;
      }
      enum rsvp-known {
        value 228 ;
      }
      enum tpa-default {
        value 229 ;
      }
      enum pim-low {
        value 231 ;
      }
      enum ntp-known {
        value 232 ;
      }
      enum uni-nd-known {
        value 233 ;
      }
      enum tpa-open {
        value 230 ;
      }
      enum pim-crp-known {
        value 234 ;
      }
      enum gprc-known {
        value 235 ;
      }
      enum gprc-default {
        value 236 ;
      }
      enum telemetry-udp {
        value 237 ;
      }
    }
    description 'Flowtype name enumeration.'
                ;
  }
  container configuration {
    description 'Configuration model info.'
                ;
    container cps {
      description 'Control plane security configuration'
                  ;
      container flow {
        if-feature cps-cmd ;
        description 'Flowtype operation'
                    ;
        container limits {
          description 'Flowtype limit configurations'
                      ;
          list limit {
            description 'Flowtype limit configuration'
                        ;
            key 'ifname flowtype'
                ;
            leaf ifname {
              description 'Interface name'
                          ;
              type ncd:ifname ;
            }
            leaf flowtype {
              description 'Flowtype name'
                          ;
              type flowtype-name ;
            }
            leaf rate-limit {
              description 'Rate limit value(pps:packet per second)'
                          ;
              type uint32 {
                range 0..85000 {
                  description "It's toplimit depends on ability of the device."
                              ;
                }
              }
              units pps ;
              mandatory true ;
            }
            leaf quota-limit {
              description 'Quota limit value(pps:packet per second)'
                          ;
              type uint32 {
                range 0..85000 {
                  description "It's toplimit depends on ability of the device."
                              ;
                }
              }
              units pps ;
              mandatory true ;
            }
          }
        }
        container limit-profiles {
          if-feature cps-router-cmd ;
          description 'Flowtype limit profile configurations'
                      ;
          list limit-profile {
            description 'Flowtype limit profile configuration'
                        ;
            max-elements 16 ;
            key profile-num ;
            leaf profile-num {
              description 'Profile number'
                          ;
              type uint8 {
                range 1..16 ;
              }
            }
          }
          list limit-profile-item {
            description 'Flow limit profile item configuration'
                        ;
            key 'profile-num flowtype'
                ;
            leaf profile-num {
              description 'Profile number'
                          ;
              type uint8 {
                range 1..16 ;
              }
            }
            leaf flowtype {
              description 'Flowtype name'
                          ;
              type flowtype-name ;
            }
            leaf rate-limit {
              description 'Rate limit value(pps:packet per second)'
                          ;
              type uint32 {
                range 0..85000 {
                  description "It's toplimit depends on ability of the device."
                              ;
                }
              }
              units pps ;
              mandatory true ;
            }
            leaf quota-limit {
              description 'Quota limit value(pps:packet per second)'
                          ;
              type uint32 {
                range 0..85000 {
                  description "It's toplimit depends on ability of the device."
                              ;
                }
              }
              units pps ;
              mandatory true ;
            }
          }
        }
        container apply-limit-profiles {
          if-feature cps-router-cmd ;
          description 'Apply flowtype limit profile configurations'
                      ;
          list apply-limit-profile {
            description 'Apply flowtype limit profile configuration'
                        ;
            key ifname ;
            leaf ifname {
              description 'Interface name'
                          ;
              type ncd:ifname {
                length 0..32 ;
              }
            }
            leaf profile-num {
              description 'Profile number'
                          ;
              type uint8 {
                range 1..16 ;
              }
              mandatory true ;
            }
          }
        }
        container backpress-profiles {
          if-feature cps-router-cmd ;
          description 'Flowtype backpress profile configurations'
                      ;
          list backpress-profile {
            description 'Flowtype backpress profile configuration'
                        ;
            max-elements 16 ;
            key profile-num ;
            leaf profile-num {
              description 'Profile number'
                          ;
              type uint8 {
                range 1..16 ;
              }
            }
          }
          list backpress-item {
            description 'Flowtype backpress profile item configuration'
                        ;
            max-elements 5 ;
            key 'profile-num overshoot-percent'
                ;
            leaf profile-num {
              description 'Profile number'
                          ;
              type uint8 {
                range 1..16 ;
              }
            }
            leaf overshoot-percent {
              description 'Overshoot percent'
                          ;
              type uint8 {
                range 1..100 ;
              }
            }
            choice supress-type {
              description 'Suppress type'
                          ;
              mandatory true ;
              case restore {
                description Restore ;
                leaf restore {
                  description 'Restore default rate limit operation'
                              ;
                  type empty ;
                  mandatory true ;
                }
              }
              case decline {
                description Decline ;
                leaf decline {
                  description 'Backpress decline percent'
                              ;
                  type uint8 {
                    range 1..100 ;
                  }
                  mandatory true ;
                }
              }
              case suspend {
                description Suspend ;
                leaf suspend {
                  description 'Suspend operation'
                              ;
                  type empty ;
                  mandatory true ;
                }
              }
            }
          }
        }
        container apply-backpress-profiles {
          if-feature cps-router-cmd ;
          description 'Apply backpress profile configurations'
                      ;
          list apply-backpress-profile {
            description 'Apply backpress profile configuration'
                        ;
            key 'ifname flowtype'
                ;
            leaf ifname {
              description 'Interface name'
                          ;
              type ncd:ifname ;
            }
            leaf flowtype {
              description 'Flowtype name'
                          ;
              type flowtype-name ;
            }
            leaf profile-num {
              description 'Profile number'
                          ;
              type uint8 {
                range 1..16 ;
              }
              mandatory true ;
            }
          }
        }
      }
      container ctm {
        if-feature cps-router-cmd ;
        description 'Ctm configuration'
                    ;
        container queue-depths {
          description 'Queue depth configurations'
                      ;
          container up-queue-depths {
            description 'Up queue depth configurations'
                        ;
            list up-queue-depth {
              description 'Up queue depth configuration'
                          ;
              key 'destcpu ifname up-priority'
                  ;
              leaf destcpu {
                description 'Destination CPU name'
                            ;
                type enumeration {
                  enum r-cpu {
                    value 1 ;
                    description r-cpu ;
                  }
                  enum l-cpu {
                    value 2 ;
                    description l-cpu ;
                  }
                }
              }
              leaf ifname {
                description 'Interface name'
                            ;
                type ncd:ifname ;
              }
              leaf up-priority {
                description 'Up priority'
                            ;
                type uint8 {
                  range 0..7 ;
                }
              }
              leaf queue-depth {
                description 'Queue depth value'
                            ;
                type enumeration {
                  enum high {
                    value 1 ;
                  }
                  enum middle {
                    value 2 ;
                  }
                  enum normal {
                    value 3 ;
                  }
                  enum low {
                    value 4 ;
                  }
                }
                mandatory true ;
              }
            }
          }
          container down-queue-depths {
            description 'Down queue depth configurations'
                        ;
            list down-queue-depth {
              description 'Down queue depth configuration'
                          ;
              key 'destcpu ifname down-priority'
                  ;
              leaf destcpu {
                description 'Destination CPU name'
                            ;
                type enumeration {
                  enum r-cpu {
                    value 1 ;
                    description r-cpu ;
                  }
                  enum l-cpu {
                    value 2 ;
                    description l-cpu ;
                  }
                }
              }
              leaf ifname {
                description 'Interface name'
                            ;
                type ncd:ifname ;
              }
              leaf down-priority {
                description 'Down priority'
                            ;
                type uint8 {
                  range 16..19 ;
                }
              }
              leaf queue-depth {
                description 'Queue depth value'
                            ;
                type enumeration {
                  enum high {
                    value 1 ;
                  }
                  enum middle {
                    value 2 ;
                  }
                  enum normal {
                    value 3 ;
                  }
                  enum low {
                    value 4 ;
                  }
                }
                mandatory true ;
              }
            }
          }
        }
        container rate-limits {
          description 'Ctm rate limit configurations'
                      ;
          container up-rate-limits {
            description 'Ctm up-rate limit configurations'
                        ;
            list up-rate-limit {
              description 'Ctm up-rate limit configuration'
                          ;
              key 'destcpu board'
                  ;
              leaf destcpu {
                description 'Destination CPU name'
                            ;
                type enumeration {
                  enum r-cpu {
                    value 1 ;
                    description r-cpu ;
                  }
                  enum l-cpu {
                    value 2 ;
                    description l-cpu ;
                  }
                }
              }
              leaf board {
                description 'Source board name'
                            ;
                type ncd:board ;
              }
              leaf up-cir {
                description 'Up cir value'
                            ;
                type uint32 {
                  range 0..600000 ;
                }
                units kbps ;
                mandatory true ;
              }
              leaf up-cbs {
                description 'Up cbs value'
                            ;
                type uint32 {
                  range 0..256 ;
                }
                units KByte ;
                mandatory true ;
              }
              leaf up-eir {
                description 'Up eir value'
                            ;
                type uint32 {
                  range 0..200000 ;
                }
                units kbps ;
                mandatory true ;
              }
            }
          }
          container down-rate-limits {
            description 'Ctm up-rate limit configurations'
                        ;
            list down-rate-limit {
              description 'Ctm up-rate limit configuration'
                          ;
              key 'destcpu board'
                  ;
              leaf destcpu {
                description 'Destination CPU name'
                            ;
                type enumeration {
                  enum r-cpu {
                    value 1 ;
                    description r-cpu ;
                  }
                  enum l-cpu {
                    value 2 ;
                    description l-cpu ;
                  }
                }
              }
              leaf board {
                description 'Source board name'
                            ;
                type ncd:board ;
              }
              leaf down-cir {
                description 'Down cir value'
                            ;
                type uint32 {
                  range 0..2000000 ;
                }
                units kbps ;
                mandatory true ;
              }
              leaf down-cbs {
                description 'Down cbs value'
                            ;
                type uint32 {
                  range 0..256 ;
                }
                units KByte ;
                mandatory true ;
              }
              leaf down-eir {
                description 'Down eir value'
                            ;
                type uint32 {
                  range 0..2000000 ;
                }
                units kbps ;
                mandatory true ;
              }
            }
          }
        }
      }
      container mng-protocol-filters {
        if-feature cps-cmd ;
        description 'Management protocol filter configurations'
                    ;
        container mng-protocol-global-filter {
          description 'Management protocol filter configurations'
                      ;
          list mng-protocol-filter {
            description 'Management protocol filter configuration'
                        ;
            key mng-protocol ;
            leaf mng-protocol {
              description 'Management protocol type'
                          ;
              type enumeration {
                enum telnet {
                  value 1 ;
                }
                enum ssh {
                  value 2 ;
                }
                enum ftp {
                  value 3 ;
                }
                enum snmp {
                  value 4 ;
                }
                enum http {
                  value 5 ;
                }
                enum ping {
                  value 6 ;
                }
                enum tftp {
                  value 7 ;
                }
              }
            }
            leaf permit-flag {
              description 'Permit or deny flag'
                          ;
              type enumeration {
                enum permit {
                  value 1 ;
                }
                enum deny {
                  value 2 ;
                }
              }
              mandatory true ;
            }
          }
        }
        container mng-protocol-if-filters {
          description 'Management protocol interface filter configurations'
                      ;
          list mng-protocol-if-filter {
            description 'Management protocol interface filter configuration'
                        ;
            key 'ifname mng-protocol'
                ;
            leaf ifname {
              description 'Interface name'
                          ;
              type ncd:ifname ;
            }
            leaf mng-protocol {
              description 'Management protocol type'
                          ;
              type enumeration {
                enum telnet {
                  value 1 ;
                }
                enum ssh {
                  value 2 ;
                }
                enum ftp {
                  value 3 ;
                }
                enum snmp {
                  value 4 ;
                }
                enum http {
                  value 5 ;
                }
                enum ping {
                  value 6 ;
                }
                enum tftp {
                  value 7 ;
                }
              }
            }
            leaf permit-flag {
              description 'Permit or deny flag'
                          ;
              type enumeration {
                enum permit {
                  value 1 ;
                }
                enum deny {
                  value 2 ;
                }
              }
              mandatory true ;
            }
          }
        }
      }
      container mngport-filter {
        description 'Mng port filter'
                    ;
        container mng-mac-filters {
          description 'Mng-port mac filter configurations'+"\n"
                    + 'mng-mac-item-filters & mng-mac-any-filter total max conf'
                    + 'iguration items number is 20'
                      ;
          container mng-mac-any-fliter {
            description 'Mng-port mac any filter configuration'
                        ;
            presence mng-mac-any-filter ;
            leaf permit-flag {
              description 'Permit flag'
                          ;
              type enumeration {
                enum deny {
                  value 1 ;
                }
                enum permit {
                  value 2 ;
                }
              }
              mandatory true ;
            }
          }
          container mng-mac-item-filters {
            description 'Mng-port mac filter configurations'
                        ;
            list mng-mac-filter {
              description 'Mng-port mac filter configuration'
                          ;
              max-elements 20 ;
              key mac-addr ;
              leaf mac-addr {
                description 'Mac address'
                            ;
                type ncd:mac-address {
                  length 0..32 ;
                }
              }
              leaf permit-flag {
                description 'Permit flag'
                            ;
                type enumeration {
                  enum deny {
                    value 1 ;
                  }
                  enum permit {
                    value 2 ;
                  }
                }
                mandatory true ;
              }
            }
          }
        }
        container mng-ip-filters {
          description 'Mng-port IP filter configurations'+"\n"
                    + 'mng-ip-item-filters & mng-ip-any-filter total max config'
                    + 'uration items number is 20'
                      ;
          container mng-ip-any-filter {
            description 'Mng-port any IP filter configuration'
                        ;
            presence mng-ip-any-filter ;
            leaf permit-flag {
              description 'Permit flag'
                          ;
              type enumeration {
                enum deny {
                  value 1 ;
                }
                enum permit {
                  value 2 ;
                }
              }
              mandatory true ;
            }
          }
          container mng-ip-item-filters {
            description 'Mng-port IP filter configurations'
                        ;
            list mng-ip-filter {
              description 'Mng-port IP filter configuration'
                          ;
              max-elements 20 ;
              key 'ip-addr ip-mask'
                  ;
              leaf ip-addr {
                description 'Ip address'
                            ;
                type ncd:ipv4-address ;
              }
              leaf ip-mask {
                description 'Ip mask'
                            ;
                type ncd:ipv4-mask ;
              }
              leaf permit-flag {
                description 'Permit flag'
                            ;
                type enumeration {
                  enum deny {
                    value 1 ;
                  }
                  enum permit {
                    value 2 ;
                  }
                }
                mandatory true ;
              }
            }
          }
        }
        container mng-ipv6-filters {
          description 'Mng-port IPv6 filter configurations'+"\n"
                    + 'mng-ipv6-item-filters & mng-ipv6-any-filter total max co'
                    + 'nfiguration items number is 20'
                      ;
          container mng-ipv6-any-filter {
            description 'Mng-port any IPv6 filter configuration'
                        ;
            presence mng-ipv6-any-filter ;
            leaf permit-flag {
              description 'Permit flag'
                          ;
              type enumeration {
                enum deny {
                  value 1 ;
                }
                enum permit {
                  value 2 ;
                }
              }
              mandatory true ;
            }
          }
          container mng-ipv6-item-filters {
            description 'Mng-port IPv6 filter configurations'
                        ;
            list mng-ipv6-filter {
              description 'Mng-port IPv6 filter configuration'
                          ;
              max-elements 20 ;
              key 'ipv6-addr prefix-len'
                  ;
              leaf ipv6-addr {
                description 'Ipv6 address'
                            ;
                type ncd:ipv6-address ;
              }
              leaf prefix-len {
                description 'Ipv6 prefix length'
                            ;
                type uint8 {
                  range 1..128 ;
                }
              }
              leaf permit-flag {
                description 'Permit flag'
                            ;
                type enumeration {
                  enum deny {
                    value 1 ;
                  }
                  enum permit {
                    value 2 ;
                  }
                }
                mandatory true ;
              }
            }
          }
        }
        container mng-port-filters {
          description 'Mng-port port filter configurations'
                      ;
          list mng-port-filter {
            description 'Mng-port port filter configuration'
                        ;
            max-elements 5 ;
            key 'protocol-type local-remote port-number'
                ;
            leaf protocol-type {
              description 'Protocol type'
                          ;
              type enumeration {
                enum tcp {
                  value 6 ;
                }
                enum udp {
                  value 17 ;
                }
              }
            }
            leaf local-remote {
              description 'Local or remote port flag'
                          ;
              type enumeration {
                enum remote {
                  value 1 ;
                }
                enum local {
                  value 2 ;
                }
              }
            }
            leaf port-number {
              description 'Port number'
                          ;
              type uint16 {
                range 1..65535 ;
              }
            }
            leaf permit-flag {
              description 'Permit flag'
                          ;
              type enumeration {
                enum deny {
                  value 1 ;
                }
                enum permit {
                  value 2 ;
                }
              }
              mandatory true ;
            }
          }
        }
        container mng-protocol-filters {
          description 'Mng-port protocol filter configurations'
                      ;
          list mng-protocol-filter {
            description 'Mng-port protocol filter configuration'
                        ;
            key protocol-type ;
            leaf protocol-type {
              description 'Protocol type'
                          ;
              type enumeration {
                enum any {
                  value 1 ;
                }
                enum arp {
                  value 2 ;
                }
                enum ftp {
                  value 3 ;
                }
                enum icmp {
                  value 4 ;
                }
                enum radius {
                  value 5 ;
                }
                enum snmp {
                  value 6 ;
                }
                enum ssh {
                  value 7 ;
                }
                enum tacacs-plus {
                  value 8 ;
                }
                enum telnet {
                  value 9 ;
                }
                enum tftp {
                  value 10 ;
                }
                enum nd {
                  value 11 ;
                }
                enum ntp {
                  value 12 ;
                }
                enum ipfrag {
                  value 13 ;
                }
                enum http {
                  value 14 ;
                }
                enum dhcp {
                  value 15 ;
                }
                enum netconf-over-tls {
                  value 16 ;
                }
                enum lldp {
                  value 17 ;
                }
                enum openflow {
                  value 18 ;
                }
              }
            }
            choice permit-or-deny {
              case permit {
                leaf permit {
                  description 'Permit flag'
                              ;
                  type enumeration {
                    enum permit {
                      value 2 ;
                    }
                  }
                  mandatory true ;
                }
                leaf rate-limit {
                  description 'Rate limit value'
                              ;
                  type uint32 {
                    range 1..10000 ;
                  }
                }
              }
              case deny {
                leaf deny {
                  description 'Deny flag'
                              ;
                  type enumeration {
                    enum deny {
                      value 1 ;
                    }
                  }
                  mandatory true ;
                }
              }
            }
          }
        }
      }
      container statistics-interval {
        if-feature statistics-interval ;
        description 'Statistics interval value configuration'
                    ;
        leaf interval {
          description 'Statistics interval value(s:second)'
                      ;
          type uint32 {
            range '0 | 5..120'
                  ;
          }
          units s ;
          default 10 ;
        }
      }
      container defend-policy {
        if-feature defend-policy-feature ;
        description 'Policy configurations.'
                    ;
        container ipv4-white-list {
          if-feature defend-policy-whitelist ;
          description 'Configure IPv4 whitelist.'
                      ;
          list ipv4-access-list {
            description 'Configure ipv4-access-list.'
                        ;
            key acl-name ;
            leaf acl-name {
              description 'Name of ACL.'
                          ;
              type string {
                length 1..31 ;
              }
            }
          }
        }
        container ipv4-black-list {
          if-feature defend-policy-blacklist ;
          description 'Configure IPv4 blacklist.'
                      ;
          list ipv4-access-list {
            description 'Configure ipv4-access-list.'
                        ;
            key acl-name ;
            leaf acl-name {
              description 'Name of ACL.'
                          ;
              type string {
                length 1..31 ;
              }
            }
          }
        }
        container ipv6-white-list {
          if-feature defend-policy-whitelist ;
          description 'Configure IPv6 whitelist.'
                      ;
          list ipv6-access-list {
            description 'Configure ipv6-access-list.'
                        ;
            key acl-name ;
            leaf acl-name {
              description 'Name of ACL.'
                          ;
              type string {
                length 1..31 ;
              }
            }
          }
        }
        container ipv6-black-list {
          if-feature defend-policy-blacklist ;
          description 'Configure IPv6 blacklist.'
                      ;
          list ipv6-access-list {
            description 'Configure ipv6-access-list.'
                        ;
            key acl-name ;
            leaf acl-name {
              description 'Name of ACL.'
                          ;
              type string {
                length 1..31 ;
              }
            }
          }
        }
        ncd:revise-date 2019-06-26 ;
      }
      container mngport-ip-packets-forward {
        description 'IP-forwarding of management ethernet interface.'
                    ;
        presence 'ip-forwarding of management interface'
                 ;
        leaf forwarding-switch {
          description 'forwarding switch.'
                      ;
          type enumeration {
            enum enable {
              value 1 ;
              description open. ;
            }
            enum disable {
              value 0 ;
              description close. ;
            }
          }
          mandatory true ;
        }
        ncd:revise-date 2020-04-14 ;
      }
    }
  }
  container state {
    config false ;
    description 'State model info.'
                ;
    container cps {
      description 'Control plane security state'
                  ;
      container ctm {
        if-feature cps-router-cmd ;
        description 'Show CTM configurations'
                    ;
        list rate-limit {
          description 'Show CTM rate limit configuration'
                      ;
          key 'destcpu board up-down-ctm'
              ;
          leaf destcpu {
            description 'Destination CPU name'
                        ;
            type enumeration {
              enum r-cpu {
                value 1 ;
                description r-cpu ;
              }
              enum l-cpu {
                value 2 ;
                description l-cpu ;
              }
            }
          }
          leaf board {
            description 'Source board name'
                        ;
            type ncd:board ;
          }
          leaf up-down-ctm {
            description 'Up or down CTM flag'
                        ;
            type enumeration {
              enum up {
                value 1 ;
              }
              enum down {
                value 2 ;
              }
            }
          }
          leaf cir {
            description 'Cir value'
                        ;
            type uint32 {
              range 0..4294967295 ;
            }
            units kbps ;
          }
          leaf cbs {
            description 'Cbs value'
                        ;
            type uint32 {
              range 0..4294967295 ;
            }
            units KByte ;
          }
          leaf eir {
            description 'Eir value'
                        ;
            type uint32 {
              range 0..4294967295 ;
            }
            units kbps ;
          }
          ncd:select 'destcpu board up-down-ctm'
                     ;
        }
        list queue-depth {
          description 'Show CTM queue depth configuration'
                      ;
          key 'destcpu priority-queue ifname'
              ;
          leaf destcpu {
            description 'Destination CPU name'
                        ;
            type enumeration {
              enum r-cpu {
                value 1 ;
                description r-cpu ;
              }
              enum l-cpu {
                value 2 ;
                description l-cpu ;
              }
            }
          }
          leaf priority-queue {
            description 'Priority queue value'
                        ;
            type uint8 {
              range '0..7 | 16..19'
                    ;
            }
          }
          leaf ifname {
            description 'Interface name'
                        ;
            type ncd:ifname ;
          }
          leaf queue-depth {
            description 'Ctm queue depth value'
                        ;
            type enumeration {
              enum high {
                value 1 ;
              }
              enum middle {
                value 2 ;
              }
              enum normal {
                value 3 ;
              }
              enum low {
                value 4 ;
              }
            }
          }
          ncd:select 'destcpu priority-queue ifname'
                     ;
        }
      }
      container flow {
        if-feature cps-cmd ;
        description 'Show flowtype configuration'
                    ;
        list limit {
          description 'Show interface all flowtype limit value'
                      ;
          key 'ifname flowtype'
              ;
          leaf ifname {
            description 'Interface name'
                        ;
            type ncd:ifname ;
          }
          leaf flowtype {
            description 'Flowtype name'
                        ;
            type flowtype-name ;
          }
          leaf rate-limit {
            description 'Flowtype rate limit value(pps:packet per second)'
                        ;
            type uint32 {
              range 0..4294967295 ;
            }
            units pps ;
          }
          leaf quota-limit {
            description 'Flowtype quota limit value(pps:packet per second)'
                        ;
            type uint32 {
              range 0..4294967295 ;
            }
            units pps ;
          }
          ncd:select 'ifname flowtype'
                     ;
        }
      }
      container mng-protocol-filter {
        if-feature cps-cmd ;
        description 'Show mng protocol filter configuration'
                    ;
        list mng-proto-filter {
          description 'Show management protocol configuration'
                      ;
          key 'ifname mng-protocol'
              ;
          leaf ifname {
            description 'Interface name'
                        ;
            type ncd:ifname ;
          }
          leaf mng-protocol {
            description 'Management protocol type'
                        ;
            type enumeration {
              enum telnet {
                value 1 ;
              }
              enum ssh {
                value 2 ;
              }
              enum ftp {
                value 3 ;
              }
              enum snmp {
                value 4 ;
              }
              enum http {
                value 5 ;
              }
              enum ping {
                value 6 ;
              }
              enum tftp {
                value 7 ;
              }
            }
          }
          leaf permit-or-deny {
            description 'Permit or deny flag'
                        ;
            type enumeration {
              enum permit {
                value 1 ;
              }
              enum deny {
                value 2 ;
              }
            }
          }
          ncd:select 'ifname mng-protocol'
                     ;
        }
      }
      container mngport-filter {
        description 'Show management port filter configuration'
                    ;
        list mng-mac-filter {
          description 'Show mng-port MAC address filter configuration'
                      ;
          key mac-addr ;
          leaf mac-addr {
            description 'Mac address'
                        ;
            type ncd:mac-address ;
          }
          leaf permit-flag {
            description 'Permit flag'
                        ;
            type enumeration {
              enum deny {
                value 1 ;
              }
              enum permit {
                value 2 ;
              }
            }
          }
        }
        list mng-ip-filter {
          description 'Show mng-port ip address filter configuration'
                      ;
          key 'ip-addr ip-addr-mask'
              ;
          leaf ip-addr {
            description 'Ip address'
                        ;
            type ncd:ipv4-address ;
          }
          leaf ip-addr-mask {
            description 'Ip address mask'
                        ;
            type ncd:ipv4-mask ;
          }
          leaf permit-flag {
            description 'Permit flag'
                        ;
            type enumeration {
              enum deny {
                value 1 ;
              }
              enum permit {
                value 2 ;
              }
            }
          }
          ncd:select 'ip-addr ip-addr-mask'
                     ;
        }
        list mng-ipv6-filter {
          description 'Show mng-port ipv6 address filter configuration'
                      ;
          key 'ipv6-addr prefix-len'
              ;
          leaf ipv6-addr {
            description 'Ipv6 address'
                        ;
            type ncd:ipv6-address ;
          }
          leaf prefix-len {
            description 'Ipv6 address prefix length'
                        ;
            type uint8 {
              range 1..128 ;
            }
          }
          leaf permit-flag {
            description 'Permit flag'
                        ;
            type enumeration {
              enum deny {
                value 1 ;
              }
              enum permit {
                value 2 ;
              }
            }
          }
          ncd:select 'ipv6-addr prefix-len'
                     ;
        }
        list mng-port-filter {
          description 'Show mng-port port filter configuration'
                      ;
          key 'protocol-type local-remote port-number'
              ;
          leaf protocol-type {
            description 'Protocol type'
                        ;
            type enumeration {
              enum tcp {
                value 6 ;
              }
              enum udp {
                value 17 ;
              }
            }
          }
          leaf local-remote {
            description 'Local or remote port'
                        ;
            type enumeration {
              enum remote {
                value 1 ;
              }
              enum local {
                value 2 ;
              }
            }
          }
          leaf port-number {
            description 'Port number'
                        ;
            type uint16 {
              range 1..65535 ;
            }
          }
          leaf permit-flag {
            description 'Permit flag'
                        ;
            type enumeration {
              enum deny {
                value 1 ;
              }
              enum permit {
                value 2 ;
              }
            }
          }
          ncd:select 'protocol-type local-remote port-number'
                     ;
        }
        list mng-protocol-filter {
          description 'Show mng-port protocol filter configuration'
                      ;
          key protocol-type ;
          leaf protocol-type {
            description 'Protocol type'
                        ;
            type enumeration {
              enum any {
                value 1 ;
              }
              enum arp {
                value 2 ;
              }
              enum ftp {
                value 3 ;
              }
              enum icmp {
                value 4 ;
              }
              enum radius {
                value 5 ;
              }
              enum snmp {
                value 6 ;
              }
              enum ssh {
                value 7 ;
              }
              enum tacacs-plus {
                value 8 ;
              }
              enum telnet {
                value 9 ;
              }
              enum tftp {
                value 10 ;
              }
              enum nd {
                value 11 ;
              }
              enum ntp {
                value 12 ;
              }
              enum ipfrag {
                value 13 ;
              }
              enum http {
                value 14 ;
              }
              enum dhcp {
                value 15 ;
              }
              enum netconf-over-tls {
                value 16 ;
              }
              enum lldp {
                value 17 ;
              }
              enum openflow {
                value 18 ;
              }
            }
          }
          leaf permit-flag {
            description 'Permit flag'
                        ;
            type enumeration {
              enum deny {
                value 1 ;
              }
              enum permit {
                value 2 ;
              }
            }
          }
          leaf rate-limit {
            description 'Rate limit value'
                        ;
            type uint32 {
              range 0..10000 ;
            }
          }
        }
      }
      container statistics {
        description 'Show statistics infomation'
                    ;
        list gtsm-statistics {
          if-feature cps-cmd ;
          description 'Show gtsm statistics infomation'
                      ;
          key flowtype ;
          leaf flowtype {
            description 'Flowtype name'
                        ;
            type flowtype-name ;
          }
          leaf upsend-pkts {
            description 'Upsend packets number'
                        ;
            type uint32 {
              range 0..4294967295 ;
            }
            units packets ;
            default 0 ;
          }
          leaf drop-pkts {
            description 'Drop packets number'
                        ;
            type uint32 {
              range 0..4294967295 ;
            }
            units packets ;
            default 0 ;
          }
        }
        list cpu-statistics {
          if-feature cpu-statis ;
          description 'Statistics based on CPU'
                      ;
          key 'flowtype cpuinfo'
              ;
          leaf flowtype {
            description 'Flowtype name'
                        ;
            type flowtype-name ;
          }
          leaf cpuinfo {
            description 'Cpu name'
                        ;
            type string {
              length 0..32 ;
            }
          }
          leaf in-packets {
            description 'In packets based on CPU'
                        ;
            type ncd:uint64-8bytes ;
            units packets ;
            default 0 ;
          }
          leaf upsend-packets {
            description 'Sendout packets based on CPU'
                        ;
            type ncd:uint64-8bytes ;
            units packets ;
            default 0 ;
          }
          ncd:select 'flowtype cpuinfo'
                     ;
          ncd:select cpuinfo ;
        }
        list interface-statistics {
          if-feature cps-cmd ;
          description 'Statistics based on interface'
                      ;
          key 'flowtype ifname'
              ;
          leaf flowtype {
            description 'Flowtype name'
                        ;
            type flowtype-name ;
          }
          leaf ifname {
            description 'Interface name'
                        ;
            type ncd:ifname ;
          }
          leaf in-packets {
            description 'In packets'
                        ;
            type ncd:uint64-8bytes ;
            units packets ;
            default 0 ;
          }
          leaf upsend-packets {
            description 'Upsend packets'
                        ;
            type ncd:uint64-8bytes ;
            units packets ;
            default 0 ;
          }
          leaf drop-packets {
            description 'Drop packets'
                        ;
            type ncd:uint64-8bytes ;
            units packets ;
            default 0 ;
          }
          leaf upsend-rate {
            description "Upsend packet's rate"
                        ;
            type uint32 ;
            default 0 ;
          }
          leaf inpackets-rate {
            description "In-packet's rate"
                        ;
            type uint32 ;
            default 0 ;
          }
          ncd:select 'flowtype ifname'
                     ;
          ncd:select ifname ;
        }
        list summary-statistics {
          if-feature cps-cmd ;
          description 'Statistics based on all interfaces'
                      ;
          key flowtype ;
          leaf flowtype {
            description 'Flowtype name'
                        ;
            type flowtype-name ;
          }
          leaf in-packets {
            description 'Summary in-packets on all interfaces'
                        ;
            type ncd:uint64-8bytes ;
            units packets ;
            default 0 ;
          }
          leaf upsend-packets {
            description 'Summary upsend packets on all interfaces'
                        ;
            type ncd:uint64-8bytes ;
            units packets ;
            default 0 ;
          }
          leaf drop-packets {
            description 'Summary drop packets on all interfaces'
                        ;
            type ncd:uint64-8bytes ;
            default 0 ;
          }
        }
      }
    }
  }
  container operation {
    if-feature cps-cmd ;
    config false ;
    description 'Operation model info.'
                ;
    container cps {
      description 'Control plane security operation'
                  ;
      container clear {
        description 'Clear operation'
                    ;
        container flowtype {
          description 'Clear flowtype statistics infomation'
                      ;
          leaf statistics {
            description 'Clear flowtype statistics'
                        ;
            type empty ;
          }
        }
        container gtsm {
          description 'Clear gtsm statistics infomation'
                      ;
          leaf statistics {
            description 'Clear gtsm statistics'
                        ;
            type empty ;
          }
        }
      }
    }
  }
}
