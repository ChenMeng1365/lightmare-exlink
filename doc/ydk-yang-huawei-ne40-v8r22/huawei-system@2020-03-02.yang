/*
Copyright (C) 2020 Huawei Technologies Co., Ltd. All rights reserved.
*/
module huawei-system {
  namespace "urn:huawei:yang:huawei-system";
  prefix system;
  import huawei-pub-type {
    prefix pub-type;
  }
  import huawei-extension {
    prefix ext;
  }
  
  organization
    "Huawei Technologies Co., Ltd.";
  contact
    "Huawei Industrial Base
     Bantian, Longgang
     Shenzhen 518129
     People's Republic of China
     Website: http://www.huawei.com
     Email: support@huawei.com";
  description
    "System.";
  revision 2020-03-02 {
    description
      "Initial revision.";
    reference
      "Huawei private.";
  }
  ext:task-name "system";
  
  typedef risk-level-type {
    type enumeration {
      enum "high" {
        value 0;
        description
          "High level.";
      }
      enum "medium" {
        value 1;
        description
          "Medium level.";
      }
      enum "low" {
        value 2;
        description
          "Low level.";
      }
    }
    description
      "Security risk level.";
    }
   
   typedef security-risk-type {
    type enumeration {
      enum "insecure-algorithm" {
        value 0;
        description
          "Insecure algorithm type.";
      }
      enum "insecure-protocol" {
        value 1;
        description
          "Insecure protocol type.";
      }
      enum "insecure-configuration" {
        value 2;
        description
          "Insecure configuration type.";
      }
    }
    description
      "Security risk type.";
  }

  container system {
    description
      "System.";
    container system-info {
      description
        "Configure system information.";
      leaf sys-name {
        type string {
          length "1..246";
        }
        default "HUAWEI";
        description
          "System name.";
      }
      leaf sys-contact {
        type string {
          length "1..255";
        }
        default "R&D Beijing, Huawei Technologies co.,Ltd.";
        description
          "System contact information.";
      }
      leaf sys-location {
        type string {
          length "1..255";
        }
        default "Beijing China";
        description
          "System location information.";
      }
      leaf sys-desc {
        type string {
          length "0..255";
        }
        config false;
        description
          "Textual description of an entity.";
      }
      leaf sys-object-id {
        type string {
          length "0..255";
        }
        config false;
        description
          "Entity OID.";
      }
      leaf system-gmt-time {
        type uint32;
        config false;
        description
          "Current system time in UTC seconds.";
      }
      leaf sys-uptime {
        type pub-type:time-tick;
        config false;
        description
          "Time elapses since the system is running.";
      }
      leaf sys-service {
        type bits {
          bit physical-layer {
            position 0;
            description
              "Physical layer.";
          }
          bit data-link-layer {
            position 1;
            description
              "Data Link layer.";
          }
          bit network-layer {
            position 2;
            description
              "Network layer.";
          }
          bit transport-layer {
            position 3;
            description
              "Transport layer.";
          }
          bit session-layer {
            position 4;
            description
              "Session layer.";
          }
          bit presentation-layer {
            position 5;
            description
              "Presentation layer.";
          }
          bit application-layer {
            position 6;
            description
              "Application layer.";
          }
        }
        config false;
        description
          "Integer value which indicates the set of services that this entity offers.";
      }
      leaf platform-name {
        type string {
          length "0..255";
        }
        config false;
        description
          "Name of a platform. For example, Huawei Versatile Routing Platform.";
      }
      leaf platform-version {
        type string {
          length "1..255";
        }
        config false;
        description
          "Version of a platform. For example, VRP (R) Software, Version 8.10.";
      }
      leaf product-name {
        type string {
          length "0..255";
        }
        config false;
        description
          "Name of a product.";
      }
      leaf product-version {
        type string {
          length "1..255";
        }
        config false;
        description
          "Product version. The version format is VxxRxxCxxSPxxx, for example, V800R002C01SPC001.";
      }
	  leaf uname {
		type string {
		  length "1..52";
		}
		config false;
		description 
		  "The array device shall contain a name that identifies the hardware that the system is running on.";
	  }	  
      leaf patch-version {
        type string {
          length "1..255";
        }
        config false;
        description
          "Latest patch version. The version format is CPxxx/HPxxx, for example, CP001.";
      }
      leaf esn {
        type string {
          length "0..511";
        }
        config false;
        description
          "Product ESN number.";
      }
      leaf mac {
        type pub-type:mac-address;
        config false;
        description
          "System MAC address.";
      }
      leaf software-name {
        type string {
          length "4..255";
        }
        config false;
        description
          "System software name. For example, VRPV800R019C10B210D1111_nos.cc.";
      }
    }

    container security-risks {
      config false;
      description
        "List of security risk information.";
      list security-risk {
        key "level feature-name type content";
        description
          "Statistics of security risk.";
        leaf level {
          type risk-level-type;
          description
            "Security risk Level.";
        }
        leaf feature-name {
          type string {
            length "1..31";
          }
          description
            "Feature name.";
        }
        leaf type {
          type security-risk-type;
          description
            "Security risk type.";
        }
        leaf content {
          type string {
            length "1..511";
          }
          description
            "Risk information.";
        }
        leaf repair-action {
          type string {
            length "1..511";
          }
          description
            "Repair action.";
        }
      }
    }
    container security-configurations {
      config false;
      description
        "List of security configuration.";
      list security-configuration {
        key "feature-name security-item";
        description
          "Statistics of security configuration.";
        leaf feature-name {
          type string {
            length "1..31";
          }
          description
            "Feature name.";
        }
        leaf security-item {
          type string {
            length "1..127";
          }
          description
            "Security item.";
        }
        leaf item-content {
          type string {
            length "1..1023";
          }
          description
            "Security item content.";
        }
      }
    }

    container weak-passwords {
      config false;
      description
        "List of weak password.";
      list weak-password {
        key "password";
        description
          "Statistics of weak password.";
        leaf password {
          type string {
            length "1..128";
          }
          description
            "Weak password.";
        }
      }
    }
  }

  rpc load-weak-password-dictionary {
    description
      "Load weak password dictionary.";
    input {
      leaf filename {
        type string {
          length "5..255";
          pattern '.+\.txt';
        }
        description
          "Name of a password dictionary file, the extension should be txt.";
      }
    }
  }

  rpc unload-weak-password-dictionary {
    description
      "Unload weak password dictionary.";
  }
}
