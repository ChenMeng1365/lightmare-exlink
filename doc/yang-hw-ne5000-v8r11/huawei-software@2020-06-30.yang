/*
Copyright (C) 2019-2020 Huawei Technologies Co., Ltd. All rights reserved.
*/
module huawei-software {
  namespace "urn:huawei:yang:huawei-software";
  prefix software;

  import huawei-extension {
    prefix ext;
  } 
  import ietf-yang-types {
    prefix yang;
  } 

  organization
    "Huawei Technologies Co., Ltd.";
  contact
    "Huawei Industrial Base
     Bantian, Longgang
     Shenzhen 518129
     People's Republic of China
     Website: http://www.huawei.com
     Email: support@huawei.com";
  description
    "Specify software package upgrade management.";
  revision 2020-06-30 {
    description
      "Revert modification of software node's config attribute.";
    reference
      "Huawei private.";
  }
  revision 2020-06-29 {
    description
      "Modify node description.";
    reference
      "Huawei private.";
  }
  revision 2020-05-27 {
    description
      "Add rpc refresh-startup-secure-version-configuration.";
    reference
      "Huawei private.";
  }
  revision 2020-03-02 {
    description
      "Add install-feature-software, uninstall-feature-software, upgrade-feature-software.";
    reference
      "Huawei private.";
  }
  revision 2019-12-02 {
    description
      "Initial revision.";
    reference
      "Huawei private.";
  }
  ext:task-name "upgrade";
  typedef startup-mode {
    type enumeration {
      enum "primary" {
        value 1;
        description
          "Upgrade the software package on the master MPU.";
      }
      enum "slave" {
        value 2;
        description
          "Upgrade the software package on the slave MPU.";
      }
      enum "all" {
        value 3;
        description
          "Upgrade the software package on all MPUs.";
      }
    }
    description
      "Startup mode.";
  }
  typedef package-type {
    type enumeration {
      enum "system" {
        value 1;
        description
          "The type of a software package on the device is a system software package.";
      }
      enum "feature" {
        value 2;
        description
          "The type of a software package on the device is a feature software package.";
      }
    }
    description
      "Specify the type of a software package on the device.";
  }
  typedef checkpoint-create-type {
    type enumeration {
      enum "manual" {
        value 1;
        description
          "The type of a checkpoint created mode.";
      }
      enum "auto" {
        value 2;
        description
          "The type of a checkpoint created mode.";
      }
    }
    description
      "Specify the type of a software package on the device.";
  }
  container software {
    description
      "Specify software package upgrade management.";
    container global {
      description 
        "Configure of auto save checkpoint switch.";
      container auto-save {
        description 
          "Configure of enable auto save checkpoint.";
        leaf enable {
          type boolean;
          default "true";
          description 
            "Enable/disable auto save checkpoint when upgrade software package.";    
        }
      }
    }
    container versions {
      config false;
      status deprecated;
      description
        "List of operational state of software package versions. The node versions is deprecated. You are advised to use the node /system/system-info.";
      list version {
        key "base";
        status deprecated;
        description
          "Operational state of a software package version. The node version is deprecated. You are advised to use the node /system/system-info.";
        leaf base {
          type string {
            length "1..63";
          }
          status deprecated;
          description
            "Current software package version. The node base is deprecated. You are advised to use the node /system/system-info/product-version.";
        }
        leaf patch {
          type string {
            length "1..63";
          }
          status deprecated;
          description
            "Current patch package version. The node patch is deprecated. You are advised to use the node /system/system-info/patch-version.";
        }
      }
    }
    container startup-packages {
      config false;
      description
        "List of operational state of startup software packages.";
      list startup-package {
        key "slot-id";
        description
          "Operational state of startup software package.";
        leaf slot-id {
          type string {
            length "1..31";
          }
          description
            "Slot ID.";
        }
        leaf current-package {
          type string {
            length "4..255";
          }
          description
            "The name of a software package used at the current startup.";
        }
        leaf next-package {
          type string {
            length "4..255";
          }
          description
            "The name of a software package used at the next startup.";
        }
      }
    }
    container packages {
      config false;
      description
        "List of operational state of software packages on the device.";
      list package {
        key "name";
        description
          "Operational state of a software package on the device.";
        leaf name {
          type string {
            length "4..255";
          }
          description
            "The name of a software package on the device. There may exist user-created software packages with names longer than 127 on the device, however, such packages cannot be used for the next startup.";
        }
        leaf package-type {
          type package-type;
          description
            "The type of a software package on the device.";
        }
      }
    }
    container upgrade-rollback-timer {
      config false;
      description
        "Operational data of upgrade rollback timer.";
      leaf timer-enable {
        type boolean;
        description
          "When the rollback timer is closed, the time leaf will not be shown.";
      }
      leaf time {
        when "../timer-enable = 'true'";
        type uint32 {
          range "10..360";
        }
        units min;
        description
          "Rollback time.";
      }
    }
    container checkpoint-infos {
      config false;
      description 
        "List of checkpoint base information.";
      list checkpoint-info {
        key "name";
        description 
          "Statistics of a checkpoint info.";
        leaf name {
          type string {
            length "5..32";
        }
          description 
            "Checkpoint name.";    
        }
        leaf create-time {
          type yang:date-and-time;
          description 
            "Checkpoint create time.";
        }
        leaf create-mode {
          type checkpoint-create-type;
          description 
            "Checkpoint create mode.";
        }
        leaf base-package {
          type string {
            length "0..255";
          }
          description 
            "Checkpoint software package.";
        }
        leaf feature-package {
          type string {
            length "0..2047";
          }
                description 
            "Checkpoint feature packages.";
        }
        leaf patch-package {
          type string {
            length "0..2047";
          }
          description 
            "Checkpoint patch packages.";
        }
        leaf module-package {
          type string {
            length "0..2047";
          }
          description "Checkpoint mod patchs.";
        }
      }
    }
  }
  rpc startup-by-mode {
    description
      "Specify the mode-based upgrade for software packages.";
    ext:node-ref "/software/packages/package"; 
    input {
      leaf name {
        type string {
          length "4..127";
        }
        mandatory true;
        description
          "Specify the name of a software package that needs to be upgraded.";
      }
      leaf mode {
        type startup-mode;
        description
          "Specify a software package upgrade mode.";
      }
    }
  }
  rpc startup-by-slot-id {
    description
      "Specify the slot ID-based upgrade for software packages.";
    ext:node-ref "/software/packages/package";
    input {
      leaf name {
        type string {
          length "4..127";
        }
        mandatory true;
        description
          "Specify the name of a software package that needs to be upgraded.";
      }
      leaf slot-id {
        type string {
          length "1..31";
        }
        description
          "Specify the slot ID of a board on which a software package needs to be upgraded.";
      }
    }
  }
  rpc enable-upgrade-rollback {
    description
      "Specify the rollback time when upgrade software package.";
    input {
      leaf rollback-time {
        type uint32 {
          range "10..360";
        }
        units min;
        mandatory true;
        description
          "Specify the rollback time.";
      }
    }
  }
  rpc undo-upgrade-rollback {
    ext:node-ref "/software/upgrade-rollback-timer";
    description
      "Delete the rollback time when upgrade software package.";
  }
  rpc install-feature-software {
    description
      "Install feature software.";
    input  {
      leaf name {
        type string {
          length "4..127";
        }
        mandatory true;
        description
          "Specify the name of a feature software package.";
      }
    }
  }
  rpc uninstall-feature-software {
    description
      "Uninstall feature software.";
    input  {
      leaf name {
        type string {
          length "4..127";
        }
        mandatory true;
        description
          "Specify the name of a feature software package.";
      }
    }
  }
  rpc upgrade-feature-software {
    description
      "Upgrade feature software on line.";
    input  {
      leaf name {
        type string {
          length "4..127";
        }
        mandatory true;
        description
          "Specify the name of a feature software package.";
      }
    }
  }
  rpc startup-feature-software {
    description
      "Startup feature software.";
    input  {
      leaf feature-package-name {
        type string {
          length "4..127";
        }
        mandatory true;
        description
          "Specify the name of a feature software package.";
      }
    }  
}
  rpc create-startup-checkpoint {
    ext:node-ref "/software/checkpoint-infos/checkpoint-info";
    description
      "Create a specified startup checkpoint.";
    input  {
      leaf name {
        type leafref {
          path "/software/checkpoint-infos/checkpoint-info/name";
        }
        mandatory true;
        description
          "Specify the name of a checkpoint.";
      }
    }
  }
  rpc delete-startup-checkpoint {
    ext:node-ref "/software/checkpoint-infos/checkpoint-info";
    description
      "Delete a specified startup checkpoint.";
    input  {
      leaf name {
        type leafref {
          path "/software/checkpoint-infos/checkpoint-info/name";
        }
        mandatory true;
        description
          "Specify the name of a checkpoint.";
      }
    }
  }
  rpc check-startup-checkpoint {
    ext:node-ref "/software/checkpoint-infos/checkpoint-info";
    description
      "Check a specified startup checkpoint.";
    input  {
      leaf name {
        type leafref {
          path "/software/checkpoint-infos/checkpoint-info/name";
        }
        mandatory true;
        description
          "Specify the name of a checkpoint.";
      }
    }
  }
  rpc restore-startup-checkpoint {
    ext:node-ref "/software/checkpoint-infos/checkpoint-info";
    description
      "Restore a specified checkpoint.";
    input  {
      leaf name {
        type leafref {
          path "/software/checkpoint-infos/checkpoint-info/name";
        }
        mandatory true;
        description
          "Specify the name of a checkpoint.";
      }
    }
  }
  rpc refresh-startup-secure-version-configuration {
    description
      "Update the eFUSE and version revocation list. If the slot parameter is not specified, information on all boards is updated.";
    input {
      leaf slot {
        type string {
          length "1..49";
        }
        description
          "Specify the slot name.";
      }
    }
  }
}
