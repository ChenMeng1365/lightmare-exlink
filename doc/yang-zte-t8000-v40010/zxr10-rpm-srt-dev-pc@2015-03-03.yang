module zxr10-rpm-srt-dev-pc {
  namespace 'http://www.zte.com.cn/zxr10/netconf/schema/rosng/rpm-srt-dev-pc' ;
  prefix zxr10-rpm-srt-dev-pc ;
  import zxr10-rpm-srt {
    prefix rpm-srt ;
    revision-date 2014-08-07 ;
  }
  organization 'ZTE Corporation' ;
  contact "ZTE Corporation  
\n"
        + "   Nanjing Institute of ZTE Corporation 
\n"
        + "   No.68 Zijinghua Rd. Yuhuatai District, Nanjing, China 
\n"
        + '   Tel: +86-25-52870000'
          ;
  description "Some projects which don't support \"permanent\" will use this de"
            + "viation file, include ASR, ZSRV2, T8000, 15K, MSE, xGW, SWITCH, "
            + "PC and so on."
              ;
  revision 2015-03-03 {
    description 'The initial revision.' ;
  }
  deviation "/rpm-srt:configuration/rpm-srt:rpm-srt/rpm-srt:rpm-srtv4/rpm-srt:r"
          + "oute-config/rpm-srt:public-net/rpm-srt:only-ifs/rpm-srt:only-if/rp"
          + "m-srt:permanent"
            {
    description 'The permanent node will not be supported.' ;
    deviate not-supported ;
  }
  deviation "/rpm-srt:configuration/rpm-srt:rpm-srt/rpm-srt:rpm-srtv4/rpm-srt:r"
          + "oute-config/rpm-srt:public-net/rpm-srt:only-nhs/rpm-srt:only-nh/rp"
          + "m-srt:permanent"
            {
    description 'The permanent node will not be supported.' ;
    deviate not-supported ;
  }
  deviation "/rpm-srt:configuration/rpm-srt:rpm-srt/rpm-srt:rpm-srtv4/rpm-srt:r"
          + "oute-config/rpm-srt:public-net/rpm-srt:both-if-nhs/rpm-srt:both-if"
          + "-nh/rpm-srt:permanent"
            {
    description 'The permanent node will not be supported.' ;
    deviate not-supported ;
  }
  deviation "/rpm-srt:configuration/rpm-srt:rpm-srt/rpm-srt:rpm-srtv4/rpm-srt:r"
          + "oute-config/rpm-srt:private-net/rpm-srt:only-ifs/rpm-srt:only-if/r"
          + "pm-srt:permanent"
            {
    description 'The permanent node will not be supported.' ;
    deviate not-supported ;
  }
  deviation "/rpm-srt:configuration/rpm-srt:rpm-srt/rpm-srt:rpm-srtv4/rpm-srt:r"
          + "oute-config/rpm-srt:private-net/rpm-srt:only-nhs/rpm-srt:only-nh/r"
          + "pm-srt:permanent"
            {
    description 'The permanent node will not be supported.' ;
    deviate not-supported ;
  }
  deviation "/rpm-srt:configuration/rpm-srt:rpm-srt/rpm-srt:rpm-srtv4/rpm-srt:r"
          + "oute-config/rpm-srt:private-net/rpm-srt:both-if-nhs/rpm-srt:both-i"
          + "f-nh/rpm-srt:permanent"
            {
    description 'The permanent node will not be supported.' ;
    deviate not-supported ;
  }
  deviation "/rpm-srt:configuration/rpm-srt:rpm-srt/rpm-srt:rpm-srtv4/rpm-srt:r"
          + "oute-config/rpm-srt:mng-net/rpm-srt:only-nhs/rpm-srt:only-nh/rpm-s"
          + "rt:permanent"
            {
    description 'The permanent node will not be supported.' ;
    deviate not-supported ;
  }
}
