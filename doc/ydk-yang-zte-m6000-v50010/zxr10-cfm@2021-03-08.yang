module zxr10-cfm {
  namespace 'http://www.zte.com.cn/zxr10/netconf/schema/rosng/cfm'
            ;
  prefix cfm ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe the CFM.'
              ;
  revision 2021-03-08 {
    description "1 The feature 'pwmip' is available for the device of PTN.61V5_"
              + "1."
                ;
  }
  revision 2021-03-02 {
    description "1 The module zxr10-cfm is available for the device of OTN.8700"
              + ",9700 and 7000.
\n2 The feature 'csf' and 'interworkmode' is a"
              + "vailable for the device of OTN.M721,8700,9700 and 7000."
                ;
  }
  revision 2020-07-06 {
    description "1 Modify the value range of 'configuration/cfm/lmeps/lmep/stat"
              + "istics-interval'."
                ;
  }
  revision 2020-06-24 {
    description "1 Modify the leaf 'state/cfm/rmep-on-demand-lms/rmep-on-demand"
              + "-lm/frame-loss-average-far' status to obsolete.
\n2 Modify the"
              + " leaf 'state/cfm/rmep-on-demand-lms/rmep-on-demand-lm/frame-lo"
              + "ss-average-near'status to obsolete.
\n3 Modify the leaf 'state"
              + "/cfm/rmep-on-demand-lms/rmep-on-demand-lm/frame-loss-highest-f"
              + "ar' status to obsolete.
\n4 Modify the leaf 'state/cfm/rmep-on"
              + "-demand-lms/rmep-on-demand-lm/frame-loss-highest-near' status "
              + "to obsolete.
\n5 Modify the leaf 'state/cfm/rmep-on-demand-lms"
              + "/rmep-on-demand-lm/frame-loss-total-far' status to obsolete.
\n"
              + "6 Modify the leaf'state/cfm/rmep-on-demand-lms/rmep-on-demand-"
              + "lm/frame-loss-total-near' status to obsolete."
                ;
  }
  revision 2020-05-20 {
    description 'Add the node operation/cfm/on-demand-lmms/on-demand-lmm/state/'
              + 'enable/priority/all.'
                ;
  }
  revision 2020-03-18 {
    description 'Md string name length expand from 8 to 43'+"\n"
              + 'Ma name-ietf-rfc2579-string name length expand from 13 to 45'
                ;
  }
  revision 2020-01-19 {
    description 'The module zxr10-cfm is available for the device of MW.NR8000 '
              + 'and MSR.ZSRV2.'
                ;
  }
  revision 2019-12-18 {
    description '1.Add the container state/cfm/rmeps/lm/proactive-single-ended/'
              + 'current.'+"\n"
              + '2.Add the container state/cfm/rmeps/lm/proactive-dual-ended/cu'
              + 'rrent.'+"\n"
              + '3.Add the container state/cfm/rmeps/dm/proactive-single-ended/'
              + 'current.'+"\n"
              + '4.Add the container state/cfm/rmeps/dm/proactive-dual-ended/cu'
              + 'rrent.'
                ;
  }
  revision 2019-10-09 {
    description '1.Add the container configuration/cfm/lmeps/lmep/ais.'+"\n"
              + '2.Add the leaf operation/cfm/tests/test/state/enable/drop-elig'
              + 'ibility.'+"\n"
              + '3.Add feature node ais-fun.'
                ;
  }
  revision 2019-07-10 {
    description '1.Add the leaf configuration/cfm/lmeps/lmep/statistics-interva'
              + 'l.'+"\n"
              + '2.Add the container state/cfm/rmeps.'
                ;
  }
  revision 2019-01-22 {
    description '1.Add the leaf /on-demand-dm/dm-results/dm-result/max-delay.'+"\n"
              + '2.Add the leaf /on-demand-dm/dm-results/dm-result/max-delay-va'
              + 'riation.'+"\n"
              + '3.Add the leaf /on-demand-dm/dm-results/dm-result/min-delay.'+"\n"
              + '4.Add the leaf /on-demand-dm/dm-results/dm-result/min-delay-va'
              + 'riation.'
                ;
  }
  revision 2018-05-18 {
    description '1. Add feature nodes dot1q,qinq,interworkmode,test,csf,mtu,pwm'
              + 'ip,bnm-service-policy.'+"\n"
              + '2. Add dynamic customization for the max value of MD/MA index,'
              + ' and the scope of all the related nodes can be customized, suc'
              + 'h as:'+"\n"
              + '    2.1)/configuration/cfm/lmeps/lmep/md-index'+"\n"
              + '    2.2)/operation/cfm/loopbacks/loopback/ma-index'+"\n"
              + '3.Obsolete the leaf /configuration/cfm/mas/ma/pvid.'+"\n"
              + '4.Add the choice /configuration/cfm/mas/ma/primary-vid.'+"\n"
              + '5.Obsolete the leaf /configuration/cfm/lmeps/lmep/priority.'+"\n"
              + '6.Add the container /configuration/cfm/lmeps/lmep/ccm-ltm-prio'
              + 'rity.'+"\n"
              + '7.Obsolete the case /configuration/cfm/lmeps/lmep/state-proact'
              + 'ive-1dm/enable-proactive-1dm/priority-1dm/priority/single-prio'
              + 'rity.'+"\n"
              + '8.Add the case /configuration/cfm/lmeps/lmep/state-proactive-1'
              + 'dm/enable-proactive-1dm/priority-1dm/priority/dot1q.'+"\n"
              + '9.Add the case /configuration/cfm/lmeps/lmep/state-proactive-1'
              + 'dm/enable-proactive-1dm/priority-1dm/priority/qinq.'+"\n"
              + '10.Obsolete the case /configuration/cfm/lmeps/lmep/state-proac'
              + 'tive-dmm/enable-proactive-dmm/priority-dmm/priority/single-pri'
              + 'ority.'+"\n"
              + '11.Add the case /configuration/cfm/lmeps/lmep/state-proactive-'
              + 'dmm/enable-proactive-dmm/priority-dmm/priority/dot1q.'+"\n"
              + '12.Add the case /configuration/cfm/lmeps/lmep/state-proactive-'
              + 'dmm/enable-proactive-dmm/priority-dmm/priority/qinq.'+"\n"
              + '13.Obsolete the leaf /configuration/cfm/lmeps/lmep/state-proac'
              + 'tive-lmm/enable-proactive-lmm/priority-lmm.'+"\n"
              + '14.Add the container /configuration/cfm/lmeps/lmep/state-proac'
              + 'tive-lmm/enable-proactive-lmm/lmm-priority.'+"\n"
              + '15.Add the leaf /configuration/cfm/lmeps/lmep/interwork-mode.'+"\n"
              + '16.Add the container /configuration/cfm/lmeps/lmep/csf.'+"\n"
              + '17.Add the container /configuration/cfm/lmeps/lmep/mtu.'+"\n"
              + '18.Obsolete the case /operation/cfm/on-demand-lmms/on-demand-l'
              + 'mm/state/enable/priority/priority/single-priority.'+"\n"
              + '19.Add the case /operation/cfm/on-demand-lmms/on-demand-lmm/st'
              + 'ate/enable/priority/priority/dot1q.'+"\n"
              + '20.Add the case /operation/cfm/on-demand-lmms/on-demand-lmm/st'
              + 'ate/enable/priority/priority/qinq.'+"\n"
              + '21.Obsolete the case /operation/cfm/on-demand-dms/on-demand-dm'
              + '/state/enable/priority/priority/single-priority.'+"\n"
              + '22.Add the case /operation/cfm/on-demand-dms/on-demand-dm/stat'
              + 'e/enable/priority/priority/dot1q.'+"\n"
              + '23.Add the case /operation/cfm/on-demand-dms/on-demand-dm/stat'
              + 'e/enable/priority/priority/qinq.'+"\n"
              + '24.Add the container /operation/cfm/mtu-detects.'+"\n"
              + '25.Add the container /operation/cfm/tests.'+"\n"
              + '26.Add the leaf /on-demand-dm/dm-results/dm-result/average-del'
              + 'ay.'+"\n"
              + '27.Add the leaf /on-demand-dm/dm-results/dm-result/average-del'
              + 'ay-variation.'+"\n"
              + '28.Add the leaf /on-demand-dm/dm-results/dm-result/delay.'+"\n"
              + '29.Add the leaf /on-demand-dm/dm-results/dm-result/delay-varia'
              + 'tion.'+"\n"
              + '30.Add the container /mtu-detect.'+"\n"
              + '31.Add the container /test.'
                ;
  }
  revision 2018-03-20 {
    description "1 Add the leaf '/on-demand-lm/lm-results/lm-result/frame-loss-"
              + "ratio-near-total'.
\n2 Add the leaf '/on-demand-lm/lm-results/"
              + "lm-result/frame-loss-ratio-far-total'."
                ;
  }
  revision 2017-12-05 {
    description "1 Modify the leaf 'configuration/cfm/lmeps/lmep/primary-vlan' "
              + "status to obsolete.
\n2 Modify the leaf 'configuration/cfm/mas"
              + "/ma/addition-detect-vlans'status to obsolete."
                ;
  }
  revision 2017-06-14 {
    description "1 Modify the Length range of 'configuration/cfm/mds/md/name-fo"
              + "rmat/name-domain-name-string/name-domain-name-string'.
\n2 Mod"
              + "ifythe Length range of 'configuration/cfm/mas/ma/name-format/n"
              + "ame-ietf-rfc2579-string/name-ietf-rfc2579-string'.
\n3 Modify "
              + "the Length range of 'configuration/cfm/mas/ma/name-format/name"
              + "-icc-string/name-icc-string'."
                ;
  }
  revision 2017-05-11 {
    description "1 Add the leaf 'configuration/cfm/lmeps/lmep/bnm-service-polic"
              + "y-adjust."
                ;
  }
  revision 2017-04-10 {
    description "1 Add the container 'configuration/cfm/lmeps/lmep/state-proact"
              + "ive-lmm'."
                ;
  }
  revision 2016-11-21 {
    description "1 Add the leaf 'loopback/lb-results/lb-result/rmep-id'."
                ;
  }
  revision 2016-07-20 {
    description "1 Add the container 'configuration/cfm/pw-mips'.
\n2 Add the l"
              + "able of M6000-S."
                ;
  }
  revision 2016-06-01 {
    description "1 Modify the description of 'operation/cfm/on-demand-dms/on-de"
              + "mand-dm/direction'."
                ;
  }
  revision 2016-05-05 {
    description "1 Modify the \"Mandatory\" attribute of 'configuration/cfm/lme"
              + "ps/lmep/state-proactive-1dm/enable-proactive-1dm/enable-proact"
              + "ive-1dm'.
\n2 Modify the \"Mandatory\" attribute of 'configura"
              + "tion/cfm/lmeps/lmep/state-proactive-dmm/enable-proactive-dmm/e"
              + "nable-proactive-dmm'."
                ;
  }
  revision 2016-04-06 {
    description "1 Add the container 'configuration/cfm/lmeps/lmep/state-proact"
              + "ive-1dm/enable-proactive-1dm/priority-1dm'.
\n2 Add the contai"
              + "ner'configuration/cfm/lmeps/lmep/state-proactive-dmm/enable-pr"
              + "oactive-dmm/priority-dmm'.
\n3 Add the container 'operation/cf"
              + "m/on-demand-lmms/on-demand-lmm/state/enable/priority'.
\n4 Add"
              + " the container 'operation/cfm/on-demand-dms/on-demand-dm/state"
              + "/enable/priority'."
                ;
  }
  revision 2015-08-03 {
    description '1 Modify the "config" attribute of the operation node and its '
              + 'leaf nodes.'
                ;
  }
  revision 2015-06-26 {
    description "1 Modify the description of 'configuration/cfm/mas/ma/addition"
              + "-detect-vlans'."
                ;
  }
  revision 2015-05-06 {
    description "1 Add the leaf 'configuration/cfm/mas/ma/addition-detect-vlans"
              + "'.
\n2 Add the leaf 'configuration/cfm/lmeps/lmep/primary-vlan"
              + "'."
                ;
  }
  revision 2015-02-12 {
    description "1 Modify the description of 'state/cfm/lb-packet-reads/lb-pack"
              + "et-read'.
\n2 Modify the description of 'state/cfm/ltr-reads/l"
              + "tr-read'."
                ;
  }
  revision 2014-12-12 {
    description "1 Add the notification node 'zxr10-cfm/loopback'.
\n2 Add the "
              + "notification node 'zxr10-cfm/linktrace'.
\n3 Add the notificat"
              + "ionnode 'zxr10-cfm/on-demand-lm'.
\n4 Add the notification nod"
              + "e 'zxr10-cfm/on-demand-dm'.
\n5 Add the leaf 'operation/cfm/lo"
              + "opbacks/loopback/serial-no'.
\n6 Add the leaf 'operation/cfm/o"
              + "n-demand-lmms/on-demand-lmm/state/enable/serial-no'.
\n7 Add t"
              + "he leaf 'operation/cfm/on-demand-dms/on-demand-dm/state/enable"
              + "/serial-no'."
                ;
  }
  revision 2014-09-03 {
    description "1 Modify the description of 'configuration/cfm/lmeps/lmep/inte"
              + "rval-ais'.
\n2 Add the leaf 'operation/cfm/linktraces/linktrac"
              + "e/serial-no'.
\n3 Add the leaf 'state/cfm/ltr-reads/ltr-read/s"
              + "erial-no'."
                ;
  }
  revision 2014-07-28 {
    description "1 Add the description of 'configuration/cfm/lmeps/lmep/state-d"
              + "lm/enable-dlm/oam-count'.
\n2 Add the description of 'configur"
              + "ation/cfm/lmeps/lmep/state-proactive-1dm/enable-proactive-1dm/"
              + "frame-size-1dm'.
\n3 Add the description of 'configuration/cfm"
              + "/lmeps/lmep/state-proactive-dmm/enable-proactive-dmm/frame-siz"
              + "e-dmm'.
\n4 Add the description of 'operation/cfm/on-demand-lm"
              + "ms/on-demand-lmm/state/enable/oam-count'.
\n5 Add the descript"
              + "ion of 'operation/cfm/on-demand-dms/on-demand-dm/state/enable/"
              + "frame-size'.
\n6 Add the description of 'operation/cfm/on-dema"
              + "nd-dms/on-demand-dm/direction'."
                ;
  }
  revision 2014-07-21 {
    description "1 Delete the default of 'configuration/cfm/mas/ma/pvid'.
\n2 M"
              + "odify the range of 'configuration/cfm/mas/ma/pvid'.
\n3 Modify"
              + " the range of 'configuration/cfm/mas/ma/name-format/name-prima"
              + "ry-vid/name-primary-vid'.
\n4 Modify the description of 'confi"
              + "guration/cfm/mas/ma/name-format/name-integer-4-octets/name-int"
              + "eger-4-octets'."
                ;
  }
  revision 2014-06-16 {
    description '1 Modify the description of the remote-if-status.'+"\n"
              + '2 Modify the description of the client-level.'+"\n"
              + '3 Add the value of reset option for the client-level.'+"\n"
              + '4 Add regular string for the mac-address.'+"\n"
              + '5 Modify the value of MimAction option for the rmep-id-1dm.'+"\n"
              + '6 Modify the value of MimAction option for the rmep-id-dmm.'
                ;
  }
  revision 2013-12-18 {
    description 'Initial version.'
                ;
  }
  feature dot1q {
    description 'Dot1q function.'
                ;
  }
  feature qinq {
    description 'QinQ function.'
                ;
  }
  feature interworkmode {
    description 'Interwork mode.'
                ;
  }
  feature test {
    description 'ETH-Test function.'
                ;
  }
  feature csf {
    description 'CSF function.'
                ;
  }
  feature mtu {
    description 'MTU function.'
                ;
  }
  feature pwmip {
    description 'Pseudo Wire MIP.'
                ;
  }
  feature bnm-service-policy {
    description 'BNM service policy.'
                ;
  }
  feature ais-fun {
    description 'AIS function.'
                ;
  }
  feature lmm-all-pri {
    description 'LMM all priority function.'
                ;
  }
  container configuration {
    description 'CFM configuration information.'
                ;
    container cfm {
      description 'CFM configuration information.'
                  ;
      container global {
        description 'CFM global information.'
                    ;
        leaf admin-state {
          description 'CFM global state.'
                      ;
          type enumeration {
            enum enable {
              value 1 ;
              description 'Enable CFM global status'
                          ;
            }
            enum disable {
              value 2 ;
              description 'Disable CFM global status'
                          ;
            }
          }
          default disable ;
        }
      }
      container mds {
        description 'CFM MD information.'
                    ;
        list md {
          description 'MD list.'
                      ;
          key index ;
          leaf index {
            description 'MD index. Its maximum value depends on the performance'
                      + ' parameters.'
                        ;
            type uint16 {
              range 1..65535 ;
            }
          }
          leaf level {
            description 'MD level.'
                        ;
            type uint8 {
              range 0..7 ;
            }
            mandatory true ;
          }
          choice name-format {
            description 'Name format.'
                        ;
            mandatory true ;
            case name-no-present {
              description 'No name present.'
                          ;
              leaf name-no-present {
                description 'No name present.'
                            ;
                type empty ;
              }
            }
            case name-domain-name-string {
              description 'Domain Name based string.'
                          ;
              leaf name-domain-name-string {
                description 'Domain Name based string.'
                            ;
                type string {
                  length 1..43 ;
                }
              }
            }
            case name-2-octets-integer {
              description '2-octet integer.'
                          ;
              leaf name-2-octets-integer {
                description '2-octet integer.'
                            ;
                type uint16 {
                  range 0..65535 ;
                }
              }
            }
            case name-ietf-rfc2579-string {
              description 'Based IETF RFC2579 string.'
                          ;
              leaf name-ietf-rfc2579-string {
                description 'Based IETF RFC2579 string.'
                            ;
                type string {
                  length 1..43 ;
                }
              }
            }
          }
        }
      }
      container mas {
        description 'CFM MA information.'
                    ;
        list ma {
          description 'MA list.'
                      ;
          key 'md-index ma-index'
              ;
          leaf md-index {
            description 'MD index. Its maximum value depends on the performance'
                      + ' parameters.'
                        ;
            type uint16 {
              range 1..65535 ;
            }
          }
          leaf ma-index {
            description 'MA index. Its maximum value depends on the performance'
                      + ' parameters.'
                        ;
            type uint16 {
              range 1..65535 ;
            }
          }
          leaf pvid {
            status obsolete {
              ncd:revise-date 2018-05-18 ;
            }
            description 'MA Primary VID.'
                        ;
            type uint16 {
              range 1..4094 ;
            }
          }
          leaf ccm-interval {
            description 'CCM transmission period indication. 1-7 respectively, '
                      + 'corresponding to the period of 3.3ms, 10ms, 100ms, 1s,'
                      + ' 10s, 60s and 600s.'
                        ;
            type uint16 {
              range 1..7 ;
            }
            default 4 ;
          }
          choice name-format {
            description 'Name format.'
                        ;
            mandatory true ;
            case name-primary-vid {
              description 'Primary VID.'
                          ;
              leaf name-primary-vid {
                description 'Primary VID.'
                            ;
                type uint32 {
                  range 0..4094 ;
                }
              }
            }
            case name-ietf-rfc2579-string {
              description 'Based IETF RFC2579 string.'
                          ;
              leaf name-ietf-rfc2579-string {
                description 'Based IETF RFC2579 string.'
                            ;
                type string {
                  length 1..45 ;
                }
              }
            }
            case name-2-octets-integer {
              description '2-octet integer.'
                          ;
              leaf name-2-octets-integer {
                description '2-octet integer.'
                            ;
                type uint32 {
                  range 0..65535 ;
                }
              }
            }
            case name-integer-4-octets {
              description '4-octet integer.'
                          ;
              leaf name-integer-4-octets {
                description '4-octet integer.'
                            ;
                type uint32 {
                  range 1..4294967295 ;
                }
              }
            }
            case name-icc-string {
              description 'ICC-based Format.'
                          ;
              leaf name-icc-string {
                description 'MA name. It consists of two subfields: the ITU car'
                          + 'rier code (ICC) followed by a unique MAID code (UM'
                          + 'C). The ITU Carrier Code consists of 1-6 left-just'
                          + 'ified characters, alphabetic, or leading alphabeti'
                          + 'c with trailing numeric. The UMC code immediately '
                          + 'follows the ICC and shall consist of 7-12 characte'
                          + 'rs, with trailing NULLs, completing the 13-charact'
                          + 'er MAID Value.'
                            ;
                type string {
                  length 1..13 ;
                }
              }
            }
          }
          leaf addition-detect-vlans {
            status obsolete {
              ncd:revise-date 2017-12-05 ;
            }
            description 'Additional detect VLAN list, VLAN range from [1..4094].'
                        ;
            type ncd:bitmap {
              length 0..13312 {
                description 'VLAN list string length, VLAN range from [1..4094].'
                            ;
              }
            }
            ncd:revise-date 2015-05-06 ;
          }
          choice primary-vid {
            description 'MA Primary VID.'
                        ;
            case dot1q {
              // if-feature dot1q ;
              description 'Dot1q VLAN.'
                          ;
              leaf vid {
                description 'MA Primary VID.'
                            ;
                type uint16 {
                  range 1..4094 ;
                }
              }
            }
            case qinq {
              // if-feature qinq ;
              description 'QinQ VLAN.'
                          ;
              leaf internal-vid {
                description 'MA internal Primary VID.'
                            ;
                type uint16 {
                  range 1..4094 ;
                }
                mandatory true ;
              }
              leaf external-vid {
                description 'MA external Primary VID.'
                            ;
                type uint16 {
                  range 1..4094 ;
                }
                mandatory true ;
              }
            }
            ncd:revise-date 2018-05-18 ;
          }
        }
      }
      container lmeps {
        description 'CFM local MEP information.'
                    ;
        list lmep {
          description 'Local MEP list.'
                      ;
          key 'md-index ma-index mp-id'
              ;
          leaf md-index {
            description 'MD index. Its maximum value depends on the performance'
                      + ' parameters.'
                        ;
            type uint16 {
              range 1..65535 ;
            }
          }
          leaf ma-index {
            description 'MA index. Its maximum value depends on the performance'
                      + ' parameters.'
                        ;
            type uint16 {
              range 1..65535 ;
            }
          }
          leaf mp-id {
            description 'Local MEPID.'
                        ;
            type uint16 {
              range 1..8191 ;
            }
          }
          leaf direction {
            description 'MEP type. Down MEP: A MEP residing in a Bridge that re'
                      + 'ceives CFM PDUs from, and transmits them towards, the '
                      + 'direction of the LAN. Up MEP: A MEP residing in a Brid'
                      + 'ge that transmits CFM PDUs towards, and receives them '
                      + 'from, the direction of the Bridge Relay Entity.'
                        ;
            type enumeration {
              enum down {
                value 1 ;
                description 'Down MEP'
                            ;
              }
              enum up {
                value 2 ;
                description 'Up MEP'
                            ;
              }
            }
            mandatory true ;
          }
          leaf if-name {
            description 'Interface name.'
                        ;
            type ncd:ifname ;
            mandatory true ;
          }
          leaf admin-state {
            description 'The state of entity function.'
                        ;
            type enumeration {
              enum enable {
                value 1 ;
                description 'Enable entity function'
                            ;
              }
              enum disable {
                value 2 ;
                description 'Disable entity function'
                            ;
              }
            }
            default disable ;
          }
          leaf ccm-send {
            description 'Controls the transmission of CCMs. When set to enable,'
                      + ' CCMs are transmitted. When set to disable, CCM transm'
                      + 'ission ceases.'
                        ;
            type enumeration {
              enum enable {
                value 1 ;
                description 'Enable local MEP CCM sending state'
                            ;
              }
              enum disable {
                value 2 ;
                description 'Disable local MEP CCM sending state'
                            ;
              }
            }
            default disable ;
          }
          leaf alarm-lowest-pri {
            description 'MEP lowest alarm priority.'
                        ;
            type uint8 {
              range 1..9 ;
            }
            default 1 ;
          }
          leaf priority {
            status obsolete {
              ncd:revise-date 2018-05-18 ;
            }
            description 'The priority parameter for CCMs and LTMs transmitted b'
                      + 'y the MEP.'
                        ;
            type uint8 {
              range 0..7 ;
            }
            default 7 ;
          }
          container ccm-ltm-priority {
            description 'The priority parameter of CCMs and LTMs.'
                        ;
            choice priority {
              description 'The priority parameter of message.'
                          ;
              case dot1q {
                // if-feature dot1q ;
                description 'Dot1q VLAN priority.'
                            ;
                leaf pri {
                  description 'The priority parameter.'
                              ;
                  type uint8 {
                    range 0..7 ;
                  }
                }
              }
              case qinq {
                // if-feature qinq ;
                description 'QinQ VLAN priority.'
                            ;
                leaf internal-pri {
                  description 'The internal priority parameter.'
                              ;
                  type uint8 {
                    range 0..7 ;
                  }
                }
                leaf external-pri {
                  description 'The external priority parameter.'
                              ;
                  type uint8 {
                    range 0..7 ;
                  }
                }
              }
            }
            ncd:revise-date 2018-05-18 ;
          }
          leaf client-level {
            description 'Client level.'
                        ;
            type uint8 {
              range 1..7 ;
            }
          }
          leaf state-ais {
            description 'The state of AIS function.'
                        ;
            type enumeration {
              enum enable {
                value 1 ;
                description 'Enable AIS function'
                            ;
              }
              enum disable {
                value 2 ;
                description 'Disable AIS function'
                            ;
              }
            }
            default disable ;
          }
          leaf state-lck {
            description 'The state of LCK function.'
                        ;
            type enumeration {
              enum enable {
                value 1 ;
                description 'Enable LCK function'
                            ;
              }
              enum disable {
                value 2 ;
                description 'Disable LCK function'
                            ;
              }
            }
            default disable ;
          }
          leaf interval-ais {
            description 'The AIS transmission interval.'
                        ;
            type enumeration {
              enum one-second {
                value 1 ;
                description 'Configure AIS interval 1 second(default)'
                            ;
              }
              enum one-minute {
                value 3 ;
                description 'Configure AIS interval 1 minute'
                            ;
              }
            }
            default one-second ;
          }
          leaf interval-lck {
            description 'The LCK transmission interval.'
                        ;
            type enumeration {
              enum one-second {
                value 1 ;
                description 'Configure LCK interval 1 second'
                            ;
              }
              enum one-minute {
                value 3 ;
                description 'Configure LCK interval 1 minute'
                            ;
              }
            }
            default one-second ;
          }
          choice state-dlm {
            description 'The state of proactive dual-ended loss measurement.'
                        ;
            case disable-dlm {
              description 'Disable DLM function.'
                          ;
              leaf disable-dlm {
                description 'Disable DLM function.'
                            ;
                type empty ;
              }
            }
            case enable-dlm {
              description 'Enable DLM function.'
                          ;
              leaf enable-dlm {
                description 'Enable DLM function.'
                            ;
                type empty ;
                mandatory true ;
              }
              leaf oam-count {
                description 'Indicating whether OAM packets are counted. Set tr'
                          + 'ue if OAM packets need to be counted, else false.'
                            ;
                type enumeration {
                  enum false {
                    value 0 ;
                    description "OAM packets don't need to be counted."
                                ;
                  }
                  enum true {
                    value 1 ;
                    description 'OAM packets need to be counted.'
                                ;
                  }
                }
                default false ;
              }
            }
          }
          choice state-proactive-1dm {
            description 'The state of proactive one-way delay measurements.'
                        ;
            case disable-proactive-1dm {
              description 'Disable proactive one-way delay measurements.'
                          ;
              leaf disable-proactive-1dm {
                description 'Disable proactive one-way delay measurements.'
                            ;
                type empty ;
              }
            }
            case enable-proactive-1dm {
              description 'Enable proactive one-way delay measurements.'
                          ;
              leaf enable-proactive-1dm {
                description 'Enable proactive one-way delay measurements.'
                            ;
                type empty ;
                mandatory true ;
              }
              leaf rmep-id-1dm {
                description 'Remote MEPID.'
                            ;
                type uint16 {
                  range 1..8191 ;
                }
              }
              leaf interval-1dm {
                description 'Packet transmission interval.'
                            ;
                type uint8 {
                  range 1..60 ;
                }
                units second ;
                default 1 ;
              }
              leaf frame-size-1dm {
                description 'Frame size.'
                            ;
                type enumeration {
                  enum 64 {
                    value 64 ;
                    description 'Configure frame size 64 bytes.'
                                ;
                  }
                  enum 128 {
                    value 128 ;
                    description 'Configure frame size 128 bytes.'
                                ;
                  }
                  enum 256 {
                    value 256 ;
                    description 'Configure frame size 256 bytes.'
                                ;
                  }
                  enum 512 {
                    value 512 ;
                    description 'Configure frame size 512 bytes.'
                                ;
                  }
                  enum 1024 {
                    value 1024 ;
                    description 'Configure frame size 1024 bytes.'
                                ;
                  }
                  enum 1280 {
                    value 1280 ;
                    description 'Configure frame size 1280 bytes.'
                                ;
                  }
                  enum 1518 {
                    value 1518 ;
                    description 'Configure frame size 1518 bytes.'
                                ;
                  }
                }
                default 64 ;
              }
              container priority-1dm {
                description 'Proactive 1DM priority.'
                            ;
                choice priority {
                  description 'The priority parameter of message.'
                              ;
                  case single-priority {
                    status obsolete {
                      ncd:revise-date 2018-05-18 ;
                    }
                    description 'Specify single priority.'
                                ;
                    leaf single-priority {
                      description Priority. ;
                      type uint8 {
                        range 0..7 ;
                      }
                    }
                  }
                  case dot1q {
                    // if-feature dot1q ;
                    description 'Dot1q VLAN priority.'
                                ;
                    leaf pri {
                      description 'The priority parameter.'
                                  ;
                      type uint8 {
                        range 0..7 ;
                      }
                    }
                    ncd:revise-date 2018-05-18 ;
                  }
                  case qinq {
                    // if-feature qinq ;
                    description 'QinQ VLAN priority.'
                                ;
                    leaf internal-pri {
                      description 'The internal priority parameter.'
                                  ;
                      type uint8 {
                        range 0..7 ;
                      }
                    }
                    leaf external-pri {
                      description 'The external priority parameter.'
                                  ;
                      type uint8 {
                        range 0..7 ;
                      }
                    }
                    ncd:revise-date 2018-05-18 ;
                  }
                }
                ncd:revise-date 2016-04-06 ;
              }
            }
          }
          choice state-proactive-dmm {
            description 'The state of proactive two-way delay measurements.'
                        ;
            case disable-proactive-dmm {
              description 'Disable proactive two-way delay measurements.'
                          ;
              leaf disable-proactive-dmm {
                description 'Disable proactive two-way delay measurements.'
                            ;
                type empty ;
              }
            }
            case enable-proactive-dmm {
              description 'Enable proactive two-way delay measurements.'
                          ;
              leaf enable-proactive-dmm {
                description 'Enable proactive two-way delay measurements.'
                            ;
                type empty ;
                mandatory true ;
              }
              leaf rmep-id-dmm {
                description 'Remote MEPID.'
                            ;
                type uint16 {
                  range 1..8191 ;
                }
              }
              leaf interval-dmm {
                description 'Packet transmission interval.'
                            ;
                type uint8 {
                  range 1..60 ;
                }
                units second ;
                default 1 ;
              }
              leaf frame-size-dmm {
                description 'Frame size.'
                            ;
                type enumeration {
                  enum 64 {
                    value 64 ;
                    description 'Configure frame size 64 bytes.'
                                ;
                  }
                  enum 128 {
                    value 128 ;
                    description 'Configure frame size 128 bytes.'
                                ;
                  }
                  enum 256 {
                    value 256 ;
                    description 'Configure frame size 256 bytes.'
                                ;
                  }
                  enum 512 {
                    value 512 ;
                    description 'Configure frame size 512 bytes.'
                                ;
                  }
                  enum 1024 {
                    value 1024 ;
                    description 'Configure frame size 1024 bytes.'
                                ;
                  }
                  enum 1280 {
                    value 1280 ;
                    description 'Configure frame size 1280 bytes.'
                                ;
                  }
                  enum 1518 {
                    value 1518 ;
                    description 'Configure frame size 1518 bytes.'
                                ;
                  }
                }
                default 64 ;
              }
              container priority-dmm {
                description 'Proactive DMM priority.'
                            ;
                choice priority {
                  description 'The priority parameter of message.'
                              ;
                  case single-priority {
                    status obsolete {
                      ncd:revise-date 2018-05-18 ;
                    }
                    description 'Specify single priority.'
                                ;
                    leaf single-priority {
                      description Priority. ;
                      type uint8 {
                        range 0..7 ;
                      }
                    }
                  }
                  case dot1q {
                    // if-feature dot1q ;
                    description 'Dot1q VLAN priority.'
                                ;
                    leaf pri {
                      description 'The priority parameter.'
                                  ;
                      type uint8 {
                        range 0..7 ;
                      }
                    }
                    ncd:revise-date 2018-05-18 ;
                  }
                  case qinq {
                    // if-feature qinq ;
                    description 'QinQ VLAN priority.'
                                ;
                    leaf internal-pri {
                      description 'The internal priority parameter.'
                                  ;
                      type uint8 {
                        range 0..7 ;
                      }
                    }
                    leaf external-pri {
                      description 'The external priority parameter.'
                                  ;
                      type uint8 {
                        range 0..7 ;
                      }
                    }
                    ncd:revise-date 2018-05-18 ;
                  }
                }
                ncd:revise-date 2016-04-06 ;
              }
            }
          }
          leaf primary-vlan {
            status obsolete {
              ncd:revise-date 2017-12-05 ;
            }
            description 'Primary VLAN.'
                        ;
            type uint16 {
              range 1..4094 ;
            }
            ncd:revise-date 2015-05-06 ;
          }
          choice state-proactive-lmm {
            description 'The state of proactive single-ended loss measurements.'
                        ;
            case disable-proactive-lmm {
              description 'Disable proactive single-ended loss measurements.'
                          ;
              leaf disable-proactive-lmm {
                description 'Disable proactive single-ended loss measurements.'
                            ;
                type empty ;
              }
            }
            case enable-proactive-lmm {
              description 'Enable proactive single-ended loss measurements.'
                          ;
              leaf enable-proactive-lmm {
                description 'Enable proactive single-ended loss measurements.'
                            ;
                type empty ;
                mandatory true ;
              }
              leaf rmep-id-lmm {
                description 'Remote MEPID.'
                            ;
                type uint16 {
                  range 1..8191 {
                    description 'range from 1 to 8191'
                                ;
                  }
                }
              }
              leaf interval-lmm {
                description 'Packet transmission interval.'
                            ;
                type uint8 {
                  range 1..60 ;
                }
                units second ;
                default 1 ;
              }
              leaf oam-count-lmm {
                description 'Indicating whether OAM packets are counted. Set tr'
                          + 'ue if OAM packets need to be counted, else false.'
                            ;
                type enumeration {
                  enum false {
                    value 0 ;
                    description "OAM packets don't need to be counted."
                                ;
                  }
                  enum true {
                    value 1 ;
                    description 'OAM packets need to be counted.'
                                ;
                  }
                }
                default false ;
              }
              leaf priority-lmm {
                status obsolete {
                  ncd:revise-date 2018-05-18 ;
                }
                description Priority. ;
                type uint8 {
                  range 0..7 ;
                }
              }
              container lmm-priority {
                description 'Proactive LMM priority.'
                            ;
                choice priority {
                  description 'The priority parameter of message.'
                              ;
                  case dot1q {
                    // if-feature dot1q ;
                    description 'Dot1q VLAN priority.'
                                ;
                    leaf pri {
                      description 'The priority parameter.'
                                  ;
                      type uint8 {
                        range 0..7 ;
                      }
                    }
                  }
                  case qinq {
                    // if-feature qinq ;
                    description 'QinQ VLAN priority.'
                                ;
                    leaf internal-pri {
                      description 'The internal priority parameter.'
                                  ;
                      type uint8 {
                        range 0..7 ;
                      }
                    }
                    leaf external-pri {
                      description 'The external priority parameter.'
                                  ;
                      type uint8 {
                        range 0..7 ;
                      }
                    }
                  }
                }
                ncd:revise-date 2018-05-18 ;
              }
            }
            ncd:revise-date 2017-04-10 ;
          }
          leaf bnm-service-policy-adjust {
            // if-feature bnm-service-policy ;
            description 'The state of BNM adjusting service policy.'
                        ;
            type enumeration {
              enum enable {
                value 1 ;
                description 'Enable BNM adjusting service policy.'
                            ;
              }
              enum disable {
                value 0 ;
                description 'Disable BNM adjusting service policy.'
                            ;
              }
            }
            default disable ;
            ncd:revise-date 2017-05-11 ;
          }
          leaf interwork-mode {
            // if-feature interworkmode ;
            description 'The interwork mode.'
                        ;
            type enumeration {
              enum stopping-cc {
                value 0 ;
                description 'Stop sending CCM when interwork(default)'
                            ;
              }
              enum sending-csf {
                value 2 ;
                description 'Send CSF when interwork'
                            ;
              }
            }
            default stopping-cc ;
            ncd:revise-date 2018-05-18 ;
          }
          container csf {
            // if-feature csf ;
            description 'CSF function.'
                        ;
            choice state {
              description 'Function state.'
                          ;
              case disable {
                description 'Disable the function.'
                            ;
                leaf disable {
                  description 'Disable the function.'
                              ;
                  type empty ;
                }
              }
              case enable {
                description 'Enable the function.'
                            ;
                leaf enable {
                  description 'Enable the function.'
                              ;
                  type empty ;
                  mandatory true ;
                }
                leaf interval {
                  description 'The transmission interval.'
                              ;
                  type enumeration {
                    enum one-second {
                      value 1 ;
                      description 'Configure one second'
                                  ;
                    }
                    enum one-minute {
                      value 3 ;
                      description 'Configure one minute'
                                  ;
                    }
                  }
                  mandatory true ;
                }
                container priority {
                  description 'The priority parameter of message.'
                              ;
                  choice priority {
                    description 'The priority parameter of message.'
                                ;
                    mandatory true ;
                    case dot1q {
                      // if-feature dot1q ;
                      description 'Dot1q VLAN priority.'
                                  ;
                      leaf pri {
                        description 'The priority parameter.'
                                    ;
                        type uint8 {
                          range 0..7 ;
                        }
                        mandatory true ;
                      }
                    }
                    case qinq {
                      // if-feature qinq ;
                      description 'QinQ VLAN priority.'
                                  ;
                      leaf internal-pri {
                        description 'The internal priority parameter.'
                                    ;
                        type uint8 {
                          range 0..7 ;
                        }
                        mandatory true ;
                      }
                      leaf external-pri {
                        description 'The external priority parameter.'
                                    ;
                        type uint8 {
                          range 0..7 ;
                        }
                        mandatory true ;
                      }
                    }
                  }
                }
              }
            }
            ncd:revise-date 2018-05-18 ;
          }
          container mtu {
            // if-feature mtu ;
            description 'MTU monitor function.'
                        ;
            choice state {
              description 'Function state.'
                          ;
              case disable {
                description 'Disable the function.'
                            ;
                leaf disable {
                  description 'Disable the function.'
                              ;
                  type empty ;
                }
              }
              case enable {
                description 'Enable the function.'
                            ;
                leaf enable {
                  description 'Enable the function.'
                              ;
                  type empty ;
                  mandatory true ;
                }
                leaf dest-mac {
                  description 'Unicast destination MAC address.'
                              ;
                  type ncd:mac-address {
                    pattern '[1-9a-fA-F][0-9a-fA-F](:[0-9a-fA-F]{2}){5}|[0-9a-f'
                          + 'A-F][1-9a-fA-F](:[0-9a-fA-F]{2}){5}|[0-9a-fA-F]{2}'
                          + ':[1-9a-fA-F][0-9a-fA-F](:[0-9a-fA-F]{2}){4}|[0-9a-'
                          + 'fA-F]{2}:[0-9a-fA-F][1-9a-fA-F](:[0-9a-fA-F]{2}){4'
                          + '}|[0-9a-fA-F]{2}:[0-9a-fA-F]{2}:[1-9a-fA-F][0-9a-f'
                          + 'A-F](:[0-9a-fA-F]{2}){3}|[0-9a-fA-F]{2}:[0-9a-fA-F'
                          + ']{2}:[0-9a-fA-F][1-9a-fA-F](:[0-9a-fA-F]{2}){3}|[0'
                          + '-9a-fA-F]{2}(:[0-9a-fA-F]{2}){2}:[1-9a-fA-F][0-9a-'
                          + 'fA-F](:[0-9a-fA-F]{2}){2}|[0-9a-fA-F]{2}(:[0-9a-fA'
                          + '-F]{2}){2}:[0-9a-fA-F][1-9a-fA-F](:[0-9a-fA-F]{2})'
                          + '{2}|[0-9a-fA-F]{2}(:[0-9a-fA-F]{2}){3}:[1-9a-fA-F]'
                          + '[0-9a-fA-F]:[0-9a-fA-F]{2}|[0-9a-fA-F]{2}(:[0-9a-f'
                          + 'A-F]{2}){3}:[0-9a-fA-F][1-9a-fA-F]:[0-9a-fA-F]{2}|'
                          + '[0-9a-fA-F]{2}(:[0-9a-fA-F]{2}){4}:[1-9a-fA-F][0-9'
                          + 'a-fA-F]|[0-9a-fA-F]{2}(:[0-9a-fA-F]{2}){4}:[0-9a-f'
                          + 'A-F][1-9a-fA-F]'
                            ;
                  }
                  mandatory true ;
                }
                leaf size {
                  description 'Frame size.'
                              ;
                  type uint16 {
                    range 64..9216 ;
                  }
                  default 64 ;
                }
                leaf interval {
                  description 'The transmission interval.'
                              ;
                  type uint16 {
                    range 10..60 ;
                  }
                  units second ;
                  default 10 ;
                }
                leaf timeout {
                  description Timeout. ;
                  type uint16 {
                    range 1..10 ;
                  }
                  units second ;
                  default 5 ;
                }
              }
            }
            ncd:revise-date 2018-05-18 ;
          }
          leaf statistics-interval {
            description 'The statistics interval, ranges from 1s to 60s(default'
                      + ':15s).'
                        ;
            type uint16 {
              range 1..60 {
                description 'The statistics interval, ranges from 1s to 60s(def'
                          + 'ault:15s).'
                            ;
              }
            }
            default 15 ;
            ncd:revise-date 2019-07-10 ;
          }
          container ais {
            // if-feature ais-fun ;
            description 'AIS function.'
                        ;
            choice state {
              description 'Function state.'
                          ;
              case disable {
                description 'Disable the function.'
                            ;
                leaf disable {
                  description 'Disable the function.'
                              ;
                  type empty ;
                }
              }
              case enable {
                description 'Enable the function.'
                            ;
                leaf enable {
                  description 'Enable the function.'
                              ;
                  type empty ;
                  mandatory true ;
                }
                container priority {
                  description 'The priority parameter of message.'
                              ;
                  choice priority {
                    description 'The priority parameter of message.'
                                ;
                    case dot1q {
                      // if-feature dot1q ;
                      description 'Dot1q VLAN priority.'
                                  ;
                      leaf pri {
                        description 'The priority parameter.'
                                    ;
                        type uint8 {
                          range 0..7 ;
                        }
                      }
                    }
                    case qinq {
                      // if-feature qinq ;
                      description 'QinQ VLAN priority.'
                                  ;
                      leaf internal-pri {
                        description 'The internal priority parameter.'
                                    ;
                        type uint8 {
                          range 0..7 ;
                        }
                      }
                      leaf external-pri {
                        description 'The external priority parameter.'
                                    ;
                        type uint8 {
                          range 0..7 ;
                        }
                      }
                    }
                  }
                }
              }
            }
            leaf interval {
              description 'The transmission interval.'
                          ;
              type enumeration {
                enum one-second {
                  value 1 ;
                  description 'Configure one second'
                              ;
                }
                enum one-minute {
                  value 3 ;
                  description 'Configure one minute'
                              ;
                }
              }
              default one-second ;
            }
            ncd:revise-date 2019-10-09 ;
          }
        }
      }
      container rmeps {
        description 'CFM Remote MEP information.'
                    ;
        list rmep {
          description 'Remote MEP list.'
                      ;
          key 'md-index ma-index mp-id'
              ;
          leaf md-index {
            description 'MD index. Its maximum value depends on the performance'
                      + ' parameters.'
                        ;
            type uint16 {
              range 1..65535 ;
            }
          }
          leaf ma-index {
            description 'MA index. Its maximum value depends on the performance'
                      + ' parameters.'
                        ;
            type uint16 {
              range 1..65535 ;
            }
          }
          leaf mp-id {
            description 'Remote MEPID.'
                        ;
            type uint16 {
              range 1..8191 ;
            }
          }
          leaf mac-address {
            description 'Remote MEP MAC address.'
                        ;
            type ncd:mac-address {
              pattern '[1-9a-fA-F][0-9a-fA-F](:[0-9a-fA-F]{2}){5}|[0-9a-fA-F][1'
                    + '-9a-fA-F](:[0-9a-fA-F]{2}){5}|[0-9a-fA-F]{2}:[1-9a-fA-F]'
                    + '[0-9a-fA-F](:[0-9a-fA-F]{2}){4}|[0-9a-fA-F]{2}:[0-9a-fA-'
                    + 'F][1-9a-fA-F](:[0-9a-fA-F]{2}){4}|[0-9a-fA-F]{2}:[0-9a-f'
                    + 'A-F]{2}:[1-9a-fA-F][0-9a-fA-F](:[0-9a-fA-F]{2}){3}|[0-9a'
                    + '-fA-F]{2}:[0-9a-fA-F]{2}:[0-9a-fA-F][1-9a-fA-F](:[0-9a-f'
                    + 'A-F]{2}){3}|[0-9a-fA-F]{2}(:[0-9a-fA-F]{2}){2}:[1-9a-fA-'
                    + 'F][0-9a-fA-F](:[0-9a-fA-F]{2}){2}|[0-9a-fA-F]{2}(:[0-9a-'
                    + 'fA-F]{2}){2}:[0-9a-fA-F][1-9a-fA-F](:[0-9a-fA-F]{2}){2}|'
                    + '[0-9a-fA-F]{2}(:[0-9a-fA-F]{2}){3}:[1-9a-fA-F][0-9a-fA-F'
                    + ']:[0-9a-fA-F]{2}|[0-9a-fA-F]{2}(:[0-9a-fA-F]{2}){3}:[0-9'
                    + 'a-fA-F][1-9a-fA-F]:[0-9a-fA-F]{2}|[0-9a-fA-F]{2}(:[0-9a-'
                    + 'fA-F]{2}){4}:[1-9a-fA-F][0-9a-fA-F]|[0-9a-fA-F]{2}(:[0-9'
                    + 'a-fA-F]{2}){4}:[0-9a-fA-F][1-9a-fA-F]'
                      ;
            }
          }
        }
      }
      container mips {
        description 'CFM MIP information.'
                    ;
        list mip {
          description 'MIP list.'
                      ;
          key 'md-index ma-index mp-id'
              ;
          leaf md-index {
            description 'MD index. Its maximum value depends on the performance'
                      + ' parameters.'
                        ;
            type uint16 {
              range 1..65535 ;
            }
          }
          leaf ma-index {
            description 'MA index. Its maximum value depends on the performance'
                      + ' parameters.'
                        ;
            type uint16 {
              range 1..65535 ;
            }
          }
          leaf mp-id {
            description 'MIP session ID.'
                        ;
            type uint16 {
              range 1..8191 ;
            }
          }
          leaf if-name {
            description 'Interface name.'
                        ;
            type ncd:ifname ;
            mandatory true ;
          }
        }
      }
      container pw-mips {
        // if-feature pwmip ;
        description 'PW MIP information.'
                    ;
        list pw-mip {
          description 'PW MIP information list.'
                      ;
          key if-name ;
          leaf if-name {
            description 'Interface name.'
                        ;
            type ncd:ifname ;
          }
          leaf level {
            description 'MIP level.'
                        ;
            type uint8 {
              range 0..7 ;
            }
            mandatory true ;
          }
        }
        ncd:revise-date 2016-07-20 ;
      }
    }
  }
  container operation {
    config false ;
    description 'CFM operation information.'
                ;
    container cfm {
      description 'CFM operation information.'
                  ;
      container loopbacks {
        description 'CFM loopback operation.'
                    ;
        list loopback {
          description 'CFM loopback operation.'
                      ;
          key 'md-index ma-index lmep-id'
              ;
          leaf md-index {
            description 'MD index. Its maximum value depends on the performance'
                      + ' parameters.'
                        ;
            type uint16 {
              range 1..65535 ;
            }
          }
          leaf ma-index {
            description 'MA index. Its maximum value depends on the performance'
                      + ' parameters.'
                        ;
            type uint16 {
              range 1..65535 ;
            }
          }
          leaf lmep-id {
            description 'Local MEPID.'
                        ;
            type uint16 {
              range 1..8191 ;
            }
          }
          leaf serial-no {
            description 'Serial number of terminal.'
                        ;
            type string {
              length 1..8 {
                description 'Range from 1 to 8'
                            ;
              }
            }
          }
          choice state {
            description 'Status of Function.'
                        ;
            mandatory true ;
            case disable {
              description 'Disable the function.'
                          ;
              leaf disable {
                description 'Disable the function.'
                            ;
                type empty ;
              }
            }
            case enable {
              description 'Enable the function.'
                          ;
              container lb-type {
                description 'Loopback function type.'
                            ;
                choice lb-type {
                  description 'Loopback function type.'
                              ;
                  mandatory true ;
                  case multicast {
                    description 'Multicast LB function is used to verify bidire'
                              + 'ctional connectivity of a MEP with its peer ME'
                              + 'Ps.'
                                ;
                    leaf multicast {
                      description 'Null string.'
                                  ;
                      type empty ;
                    }
                  }
                  case unicast {
                    description 'Unicast LB is an on-demand OAM function that c'
                              + 'an be used to verify bidirectional connectivit'
                              + 'y of a MEP with a MIP or a peer MEP.'
                                ;
                    leaf dest-mac {
                      description 'Unicast destination MAC address.'
                                  ;
                      type ncd:mac-address ;
                    }
                  }
                }
                leaf repeat {
                  description 'Loopback messages will be sent.'
                              ;
                  type uint16 {
                    range 1..200 ;
                  }
                  default 3 ;
                }
                leaf size {
                  description 'Loopback messages data TLV length.'
                              ;
                  type uint16 {
                    range 0..400 ;
                  }
                  default 0 ;
                }
                leaf timeout {
                  description Timeout. ;
                  type uint16 {
                    range 1..10 ;
                  }
                  units second ;
                  default 5 ;
                }
              }
            }
          }
        }
      }
      container linktraces {
        description 'CFM linktrace operation.'
                    ;
        list linktrace {
          description 'CFM linktrace operation.'
                      ;
          key 'md-index ma-index lmep-id'
              ;
          leaf md-index {
            description 'MD index. Its maximum value depends on the performance'
                      + ' parameters.'
                        ;
            type uint16 {
              range 1..65535 ;
            }
          }
          leaf ma-index {
            description 'MA index. Its maximum value depends on the performance'
                      + ' parameters.'
                        ;
            type uint16 {
              range 1..65535 ;
            }
          }
          leaf lmep-id {
            description 'Local MEPID.'
                        ;
            type uint16 {
              range 1..8191 ;
            }
          }
          leaf serial-no {
            description 'Serial number of terminal.'
                        ;
            type string {
              length 1..8 ;
            }
          }
          choice state {
            description 'Status of Function.'
                        ;
            mandatory true ;
            case disable {
              description 'Disable the function.'
                          ;
              leaf disable {
                description 'Disable the function.'
                            ;
                type empty ;
              }
            }
            case enable {
              description 'Enable the function.'
                          ;
              leaf dest-mac {
                description 'Unicast destination MAC address.'
                            ;
                type ncd:mac-address ;
                mandatory true ;
              }
              leaf ttl {
                description 'An initial value for the LTM TTL field.'
                            ;
                type uint16 {
                  range 1..64 ;
                }
                default 64 ;
              }
              leaf timeout {
                description Timeout. ;
                type uint16 {
                  range 5..10 ;
                }
                units second ;
                default 5 ;
              }
            }
          }
        }
      }
      container on-demand-lmms {
        description 'On-demand loss measurement.'
                    ;
        list on-demand-lmm {
          description 'On-demand loss measurement.'
                      ;
          key 'md-index ma-index mp-id'
              ;
          leaf md-index {
            description 'MD index. Its maximum value depends on the performance'
                      + ' parameters.'
                        ;
            type uint16 {
              range 1..65535 {
                description 'Range from 1 to 65535.'
                            ;
              }
            }
          }
          leaf ma-index {
            description 'MA index. Its maximum value depends on the performance'
                      + ' parameters.'
                        ;
            type uint16 {
              range 1..65535 {
                description 'Range from 1 to 65535.'
                            ;
              }
            }
          }
          leaf mp-id {
            description 'Local MEPID.'
                        ;
            type uint16 {
              range 1..8191 {
                description 'Range from 1 to 8191.'
                            ;
              }
            }
          }
          choice state {
            description 'Status of Function.'
                        ;
            mandatory true ;
            case disable {
              description 'Disable the function.'
                          ;
              leaf disable {
                description 'Disable the function.'
                            ;
                type empty ;
              }
            }
            case enable {
              description 'Enable the function.'
                          ;
              leaf enable {
                description 'Enable the function.'
                            ;
                type empty ;
                mandatory true ;
              }
              leaf serial-no {
                description 'Serial number of terminal.'
                            ;
                type string {
                  length 1..8 ;
                }
              }
              leaf rmep-id {
                description 'Remote MEPID.'
                            ;
                type uint16 {
                  range 1..8191 {
                    description 'Range from 1 to 8191.'
                                ;
                  }
                }
              }
              leaf interval {
                description 'Packet transmission interval.'
                            ;
                type uint8 {
                  range 1..60 {
                    description 'Range from 1 to 60.'
                                ;
                  }
                }
                units second ;
                default 1 ;
              }
              leaf require-time {
                description 'On-demand measurement time.'
                            ;
                type uint32 {
                  range '10..86400 | 4294967295'
                        {
                    description 'Range from [10..86400, 4294967295].'
                                ;
                  }
                }
                units second ;
                default 4294967295 ;
              }
              leaf oam-count {
                description 'Indicating whether OAM packets are counted. Set tr'
                          + 'ue if OAM packets need to be counted, else false.'
                            ;
                type enumeration {
                  enum false {
                    value 0 ;
                    description "OAM packets don't need to be counted."
                                ;
                  }
                  enum true {
                    value 1 ;
                    description 'OAM packets need to be counted.'
                                ;
                  }
                }
                default false ;
              }
              container priority {
                description 'On-demand LMM priority.'
                            ;
                choice priority {
                  description 'The priority parameter of message.'
                              ;
                  case single-priority {
                    status obsolete {
                      ncd:revise-date 2018-05-18 ;
                    }
                    description 'Specify single priority.'
                                ;
                    leaf single-priority {
                      description Priority. ;
                      type uint8 {
                        range 0..7 ;
                      }
                    }
                  }
                  case dot1q {
                    // if-feature dot1q ;
                    description 'Dot1q VLAN priority.'
                                ;
                    leaf pri {
                      description 'The priority parameter.'
                                  ;
                      type uint8 {
                        range 0..7 ;
                      }
                      default 7 ;
                    }
                    ncd:revise-date 2018-05-18 ;
                  }
                  case qinq {
                    // if-feature qinq ;
                    description 'QinQ VLAN priority.'
                                ;
                    leaf internal-pri {
                      description 'The internal priority parameter.'
                                  ;
                      type uint8 {
                        range 0..7 ;
                      }
                      default 7 ;
                    }
                    leaf external-pri {
                      description 'The external priority parameter.'
                                  ;
                      type uint8 {
                        range 0..7 ;
                      }
                      default 7 ;
                    }
                    ncd:revise-date 2018-05-18 ;
                  }
                  case all {
                    // if-feature lmm-all-pri ;
                    description 'All VLAN priority.'
                                ;
                    leaf all {
                      description 'All priority.'
                                  ;
                      type empty ;
                    }
                    ncd:revise-date 2020-05-20 ;
                  }
                }
                ncd:revise-date 2016-04-06 ;
              }
            }
          }
        }
      }
      container on-demand-dms {
        description 'On-demand delay measurement.'
                    ;
        list on-demand-dm {
          description 'On-demand delay measurement.'
                      ;
          key 'md-index ma-index mp-id'
              ;
          leaf md-index {
            description 'MD index. Its maximum value depends on the performance'
                      + ' parameters.'
                        ;
            type uint16 {
              range 1..65535 ;
            }
          }
          leaf ma-index {
            description 'MA index. Its maximum value depends on the performance'
                      + ' parameters.'
                        ;
            type uint16 {
              range 1..65535 ;
            }
          }
          leaf mp-id {
            description 'Local MEPID.'
                        ;
            type uint16 {
              range 1..8191 ;
            }
          }
          leaf direction {
            description 'The direction of delay measurement.'
                        ;
            type enumeration {
              enum one-way {
                value 2 ;
                description 'One-way delay measurement'
                            ;
              }
              enum two-way {
                value 3 ;
                description 'Two-way delay measurement'
                            ;
              }
            }
            mandatory true ;
          }
          choice state {
            description 'Status of Function.'
                        ;
            mandatory true ;
            case disable {
              description 'Disable the function.'
                          ;
              leaf disable {
                description 'Disable the function.'
                            ;
                type empty ;
              }
            }
            case enable {
              description 'Enable the function.'
                          ;
              leaf enable {
                description 'Enable the function.'
                            ;
                type empty ;
                mandatory true ;
              }
              leaf serial-no {
                description 'Serial number of terminal.'
                            ;
                type string {
                  length 1..8 ;
                }
              }
              leaf rmep-id {
                description 'Remote MEPID.'
                            ;
                type uint16 {
                  range 1..8191 {
                    description 'Range from 1 to 8191.'
                                ;
                  }
                }
              }
              leaf interval {
                description 'Packet transmission interval.'
                            ;
                type uint8 {
                  range 1..60 {
                    description 'Range from 1 to 60.'
                                ;
                  }
                }
                units second ;
                default 1 ;
              }
              leaf require-time {
                description 'On-demand measurement time.'
                            ;
                type uint32 {
                  range '10..86400 | 4294967295'
                        {
                    description 'Range from [10..86400, 4294967295].'
                                ;
                  }
                }
                units second ;
                default 4294967295 ;
              }
              leaf frame-size {
                description 'Frame size.'
                            ;
                type enumeration {
                  enum 64 {
                    value 64 ;
                    description 'Configure frame size 64 bytes.'
                                ;
                  }
                  enum 128 {
                    value 128 ;
                    description 'Configure frame size 128 bytes.'
                                ;
                  }
                  enum 256 {
                    value 256 ;
                    description 'Configure frame size 256 bytes.'
                                ;
                  }
                  enum 512 {
                    value 512 ;
                    description 'Configure frame size 512 bytes.'
                                ;
                  }
                  enum 1024 {
                    value 1024 ;
                    description 'Configure frame size 1024 bytes.'
                                ;
                  }
                  enum 1280 {
                    value 1280 ;
                    description 'Configure frame size 1280 bytes.'
                                ;
                  }
                  enum 1518 {
                    value 1518 ;
                    description 'Configure frame size 1518 bytes.'
                                ;
                  }
                }
                default 64 ;
              }
              container priority {
                description 'On-demand DM priority.'
                            ;
                choice priority {
                  description 'The priority parameter of message.'
                              ;
                  case single-priority {
                    status obsolete {
                      ncd:revise-date 2018-05-18 ;
                    }
                    description 'Specify single priority.'
                                ;
                    leaf single-priority {
                      description 'Priority, value range [0..7].'
                                  ;
                      type uint8 {
                        range 0..7 ;
                      }
                    }
                  }
                  case dot1q {
                    // if-feature dot1q ;
                    description 'Dot1q VLAN priority.'
                                ;
                    leaf pri {
                      description 'The priority parameter.'
                                  ;
                      type uint8 {
                        range 0..7 ;
                      }
                      default 7 ;
                    }
                    ncd:revise-date 2018-05-18 ;
                  }
                  case qinq {
                    // if-feature qinq ;
                    description 'QinQ VLAN priority.'
                                ;
                    leaf internal-pri {
                      description 'The internal priority parameter.'
                                  ;
                      type uint8 {
                        range 0..7 ;
                      }
                      default 7 ;
                    }
                    leaf external-pri {
                      description 'The external priority parameter.'
                                  ;
                      type uint8 {
                        range 0..7 ;
                      }
                      default 7 ;
                    }
                    ncd:revise-date 2018-05-18 ;
                  }
                }
                ncd:revise-date 2016-04-06 ;
              }
            }
          }
        }
      }
      container mtu-detects {
        // if-feature mtu ;
        description 'CFM MTU detect operation.'
                    ;
        list mtu-detect {
          description 'CFM MTU detect operation.'
                      ;
          key 'md-index ma-index lmep-id'
              ;
          leaf md-index {
            description 'MD index. Its maximum value depends on the performance'
                      + ' parameters.'
                        ;
            type uint16 {
              range 1..65535 ;
            }
          }
          leaf ma-index {
            description 'MA index. Its maximum value depends on the performance'
                      + ' parameters.'
                        ;
            type uint16 {
              range 1..65535 ;
            }
          }
          leaf lmep-id {
            description 'Local MEPID.'
                        ;
            type uint16 {
              range 1..8191 ;
            }
          }
          leaf serial-no {
            description 'Serial number of terminal.'
                        ;
            type string {
              length 1..8 ;
            }
          }
          choice state {
            description 'Status of Function.'
                        ;
            mandatory true ;
            case disable {
              description 'Disable the function.'
                          ;
              leaf disable {
                description 'Disable the function.'
                            ;
                type empty ;
              }
            }
            case enable {
              description 'Enable the function.'
                          ;
              leaf dest-mac {
                description 'Unicast destination MAC address.'
                            ;
                type ncd:mac-address ;
                mandatory true ;
              }
              leaf timeout {
                description Timeout. ;
                type uint16 {
                  range 1..10 ;
                }
                units second ;
                default 5 ;
              }
            }
          }
        }
        ncd:revise-date 2018-05-18 ;
      }
      container tests {
        // if-feature test ;
        description 'CFM ETH-Test operation.'
                    ;
        list test {
          description 'CFM ETH-Test operation.'
                      ;
          key 'md-index ma-index lmep-id'
              ;
          leaf md-index {
            description 'MD index. Its maximum value depends on the performance'
                      + ' parameters.'
                        ;
            type uint16 {
              range 1..65535 ;
            }
          }
          leaf ma-index {
            description 'MA index. Its maximum value depends on the performance'
                      + ' parameters.'
                        ;
            type uint16 {
              range 1..65535 ;
            }
          }
          leaf lmep-id {
            description 'Local MEPID.'
                        ;
            type uint16 {
              range 1..8191 ;
            }
          }
          leaf serial-no {
            description 'Serial number of terminal.'
                        ;
            type uint64 ;
          }
          choice state {
            description 'Status of Function.'
                        ;
            mandatory true ;
            case disable {
              description 'Disable the function.'
                          ;
              leaf disable {
                description 'Disable the function.'
                            ;
                type empty ;
              }
            }
            case enable {
              description 'Enable the function.'
                          ;
              container dest-type {
                description 'Function destination type.'
                            ;
                choice dest-type {
                  description 'Function destination type.'
                              ;
                  mandatory true ;
                  case rmep-id {
                    description 'Remote MEPID.'
                                ;
                    leaf rmep-id {
                      description 'Remote MEPID.'
                                  ;
                      type uint16 {
                        range 1..8191 ;
                      }
                    }
                  }
                  case dest-mac {
                    description 'Unicast destination MAC address.'
                                ;
                    leaf dest-mac {
                      description 'Unicast destination MAC address.'
                                  ;
                      type ncd:mac-address ;
                    }
                  }
                }
              }
              leaf service-type {
                description 'Service type.'
                            ;
                type enumeration {
                  enum in-service {
                    value 1 ;
                    description 'In-service test.'
                                ;
                  }
                  enum out-service {
                    value 2 ;
                    description 'Out-service test.'
                                ;
                  }
                }
                mandatory true ;
              }
              leaf frame-size {
                description 'Frame size.'
                            ;
                type uint32 {
                  range 64..1518 ;
                }
                mandatory true ;
              }
              leaf frame-rate {
                description 'Frame rate.'
                            ;
                type uint32 {
                  range 1..200000 ;
                }
                units kbps ;
                mandatory true ;
              }
              leaf pattern-type {
                description 'TLV pattern type.'
                            ;
                type enumeration {
                  enum null-pattern {
                    value 0 ;
                    description 'Null signal without CRC-32 pattern.'
                                ;
                  }
                  enum null-pattern-crc32 {
                    value 1 ;
                    description 'Null signal with CRC-32 pattern.'
                                ;
                  }
                  enum prbs31 {
                    value 2 ;
                    description 'Prbs31 without CRC-32 pattern.'
                                ;
                  }
                  enum prbs31-crc32 {
                    value 3 ;
                    description 'Prbs31 with CRC-32 pattern'
                                ;
                  }
                }
                mandatory true ;
              }
              leaf duration-time {
                description 'Duration time. If not configured, function is enab'
                          + 'led all the time.'
                            ;
                type uint32 {
                  range 10..86400 ;
                }
                units second ;
              }
              leaf type {
                description 'The type of the ETH-test function.'
                            ;
                type enumeration {
                  enum send-only {
                    value 0 ;
                    description 'Only send TST packet.'
                                ;
                  }
                  enum receive-only {
                    value 1 ;
                    description 'Only receive TST packet.'
                                ;
                  }
                }
                default send-only ;
              }
              leaf upsend-interval {
                description 'The upsend interval.'
                            ;
                type uint32 {
                  range 5..86400 ;
                }
                units second ;
                default 5 ;
              }
              container priority {
                description 'The priority parameter.'
                            ;
                choice priority {
                  description 'The priority parameter of message.'
                              ;
                  case dot1q {
                    // if-feature dot1q ;
                    description 'Dot1q VLAN priority.'
                                ;
                    leaf pri {
                      description 'The priority parameter.'
                                  ;
                      type uint8 {
                        range 0..7 ;
                      }
                      default 7 ;
                    }
                  }
                  case qinq {
                    // if-feature qinq ;
                    description 'QinQ VLAN priority.'
                                ;
                    leaf internal-pri {
                      description 'The internal priority parameter.'
                                  ;
                      type uint8 {
                        range 0..7 ;
                      }
                      default 7 ;
                    }
                    leaf external-pri {
                      description 'The external priority parameter.'
                                  ;
                      type uint8 {
                        range 0..7 ;
                      }
                      default 7 ;
                    }
                  }
                }
              }
              leaf drop-eligibility {
                description 'Indicating the canonical format in VLAN TAG.'
                            ;
                type enumeration {
                  enum false {
                    value 0 ;
                    description 'Canonical format.'
                                ;
                  }
                  enum true {
                    value 1 ;
                    description 'Non-canonical format.'
                                ;
                  }
                }
                default false ;
                ncd:revise-date 2019-10-09 ;
              }
            }
          }
        }
        ncd:revise-date 2018-05-18 ;
      }
    }
  }
  container state {
    config false ;
    description 'CFM state information.'
                ;
    container cfm {
      description 'CFM state information.'
                  ;
      container lmep-defects {
        description 'The defect information of local MEP.'
                    ;
        list lmep-defect {
          description 'The defect information of local MEP.'
                      ;
          key 'md-index ma-index mp-id'
              ;
          leaf md-index {
            description 'MD index. Its maximum value depends on the performance'
                      + ' parameters.'
                        ;
            type uint16 {
              range 1..65535 ;
            }
          }
          leaf ma-index {
            description 'MA index. Its maximum value depends on the performance'
                      + ' parameters.'
                        ;
            type uint16 {
              range 1..65535 ;
            }
          }
          leaf mp-id {
            description 'Local MEPID.'
                        ;
            type uint16 {
              range 1..8191 ;
            }
          }
          leaf present-rdi {
            description 'Indicating the state of the RDI flag in CCMs transmitt'
                      + 'ed by this MEP.'
                        ;
            type uint8 ;
          }
          leaf ma-defect-indication {
            description 'Indicating that at least one of the remote MEP in MA d'
                      + 'etect a defect.'
                        ;
            type uint8 ;
          }
          leaf some-rdi-defect {
            description 'Reception of a CCM frame with the RDI flag.'
                        ;
            type uint8 ;
          }
          leaf some-mac-status-defect {
            description 'Reception of a CCM frame with a failure in its Port St'
                      + 'atus TLV or Interface Status TLV.'
                        ;
            type uint8 ;
          }
          leaf some-rmep-ccm-defect {
            description 'Indicating that at least one of the remote MEP in MA i'
                      + 's not receiving valid CCMs from its remote MEP.'
                        ;
            type uint8 ;
          }
          leaf error-ccm-defect {
            description 'Reception of a invalid CCM frame.'
                        ;
            type uint8 ;
          }
          leaf unexpected-period-defect {
            description 'Reception of a CCM frame with an unexpected Periodicit'
                      + 'y value.'
                        ;
            type uint8 ;
          }
          leaf unexpected-mac-defect {
            description 'Reception of a CCM frame with an unexpected MAC value.'
                        ;
            type uint8 ;
          }
          leaf unexpected-mepid-defect {
            description 'Reception of a CCM frame with an unexpected MEP value.'
                        ;
            type uint8 ;
          }
          leaf xcon-ccm-defect {
            description 'Reception of a CCM frame with an unexpected MEG value.'
                        ;
            type uint8 ;
          }
          leaf unexpected-level-defect {
            description 'Reception of a CCM frame with an unexpected MEL value.'
                        ;
            type uint8 ;
          }
          leaf ais-rcvd-flag {
            description 'Reception of a AIS frame.'
                        ;
            type uint8 ;
          }
          leaf lck-rcvd-flag {
            description 'Reception of an LCK frame.'
                        ;
            type uint8 ;
          }
          ncd:select 'md-index ma-index'
                     ;
          ncd:select 'md-index ma-index mp-id'
                     ;
        }
      }
      container lmep-statistics {
        description 'The statistics of local MEP.'
                    ;
        list lmep-statistic {
          description 'The statistics of local MEP.'
                      ;
          key 'md-index ma-index mp-id'
              ;
          leaf md-index {
            description 'MD index. Its maximum value depends on the performance'
                      + ' parameters.'
                        ;
            type uint16 {
              range 1..65535 ;
            }
          }
          leaf ma-index {
            description 'MA index. Its maximum value depends on the performance'
                      + ' parameters.'
                        ;
            type uint16 {
              range 1..65535 ;
            }
          }
          leaf mp-id {
            description 'Local MEPID.'
                        ;
            type uint16 {
              range 1..8191 ;
            }
          }
          leaf total-send-ccm {
            description 'The total number of send CCMs.'
                        ;
            type uint32 ;
          }
          leaf total-rcvd-ccm {
            description 'The total number of received CCMs.'
                        ;
            type uint32 ;
          }
          leaf right-rcvd-ccm {
            description 'The total number of received correct CCMs.'
                        ;
            type uint32 ;
          }
          leaf def-error-ccm {
            description 'The total number of received invalid CCMs.'
                        ;
            type uint32 ;
          }
          leaf discard-ccm {
            description 'The total number of discarded CCMs.'
                        ;
            type uint32 ;
          }
          leaf def-xcon-ccm {
            description 'The total number of received cross CCMs.'
                        ;
            type uint32 ;
          }
          leaf total-send-lbm {
            description 'The total number of sent LBMs.'
                        ;
            type uint32 ;
          }
          leaf total-rcvd-lbm {
            description 'The total number of received LBMs.'
                        ;
            type uint32 ;
          }
          leaf total-send-lbr {
            description 'The total number of sent LBRs.'
                        ;
            type uint32 ;
          }
          leaf total-rcvd-lbr {
            description 'The total number of received LBRs.'
                        ;
            type uint32 ;
          }
          ncd:select 'md-index ma-index'
                     ;
          ncd:select 'md-index ma-index mp-id'
                     ;
        }
      }
      container rmep-defects {
        description 'Defect information of remote MEP.'
                    ;
        list rmep-defect {
          description 'Defect information of remote MEP'
                      ;
          key 'md-index ma-index mp-id'
              ;
          leaf md-index {
            description 'MD index. Its maximum value depends on the performance'
                      + ' parameters.'
                        ;
            type uint16 {
              range 1..65535 ;
            }
          }
          leaf ma-index {
            description 'MA index. Its maximum value depends on the performance'
                      + ' parameters.'
                        ;
            type uint16 {
              range 1..65535 ;
            }
          }
          leaf mp-id {
            description 'Remote MEPID.'
                        ;
            type uint16 {
              range 1..8191 ;
            }
          }
          leaf rmep-last-rdi {
            description 'Indicating the RDI flag from the last-received CCM.'
                        ;
            type uint8 ;
          }
          leaf rmep-ccm-defect {
            description 'Indicating the remote MEP is not receiving valid CCMs '
                      + 'from its remote MEP.'
                        ;
            type uint8 ;
          }
          leaf remote-if-status {
            description 'Remote interface status(1-up, 2-down, 0-unknown).'
                        ;
            type uint8 ;
          }
          ncd:select 'md-index ma-index'
                     ;
          ncd:select 'md-index ma-index mp-id'
                     ;
        }
      }
      container rmep-on-demand-lms {
        description 'On-demand loss measurement of remote MEP.'
                    ;
        list rmep-on-demand-lm {
          description 'On-demand loss measurement of remote MEP.'
                      ;
          key 'md-index ma-index mp-id'
              ;
          leaf md-index {
            description 'MD index. Its maximum value depends on the performance'
                      + ' parameters.'
                        ;
            type uint16 {
              range 1..65535 ;
            }
          }
          leaf ma-index {
            description 'MA index. Its maximum value depends on the performance'
                      + ' parameters.'
                        ;
            type uint16 {
              range 1..65535 ;
            }
          }
          leaf mp-id {
            description 'Remote MEPID.'
                        ;
            type uint16 {
              range 1..8191 ;
            }
          }
          leaf measurement-time {
            description 'The times of frame loss measurement.'
                        ;
            type uint32 ;
          }
          leaf frame-send-newest-far {
            description 'The newest frame transmissions of far-end loss measure'
                      + 'ments.'
                        ;
            type uint32 ;
          }
          leaf frame-send-newest-near {
            description 'The newest frame transmissions of near-end loss measur'
                      + 'ements.'
                        ;
            type uint32 ;
          }
          leaf frame-loss-newest-far {
            description 'The newest frame losses of far-end loss measurements.'
                        ;
            type uint32 ;
          }
          leaf frame-loss-newest-near {
            description 'The newest frame losses of near-end loss measurements.'
                        ;
            type uint32 ;
          }
          leaf frame-loss-average-far {
            status obsolete {
              ncd:revise-date 2020-06-24 ;
            }
            description 'The average frame losses of far-end loss measurements.'
                        ;
            type uint32 ;
          }
          leaf frame-loss-average-near {
            status obsolete {
              ncd:revise-date 2020-06-24 ;
            }
            description 'The average frame losses of near-end loss measurements.'
                        ;
            type uint32 ;
          }
          leaf frame-loss-highest-far {
            status obsolete {
              ncd:revise-date 2020-06-24 ;
            }
            description 'The highest frame losses of far-end loss measurements.'
                        ;
            type uint32 ;
          }
          leaf frame-loss-highest-near {
            status obsolete {
              ncd:revise-date 2020-06-24 ;
            }
            description 'The highest frame losses of near-end loss measurements.'
                        ;
            type uint32 ;
          }
          leaf frame-loss-total-far {
            status obsolete {
              ncd:revise-date 2020-06-24 ;
            }
            description 'The total frame losses of far-end loss measurements.'
                        ;
            type uint32 ;
          }
          leaf frame-loss-total-near {
            status obsolete {
              ncd:revise-date 2020-06-24 ;
            }
            description 'The total frame losses of near-end loss measurements.'
                        ;
            type uint32 ;
          }
          leaf frame-loss-ratio-newest-far {
            description 'The newest frame loss ratio of far-end loss measuremen'
                      + 'ts.'
                        ;
            type uint64 ;
          }
          leaf frame-loss-ratio-newest-near {
            description 'The newest frame loss ratio of near-end loss measureme'
                      + 'nts.'
                        ;
            type uint64 ;
          }
          ncd:select 'md-index ma-index'
                     ;
          ncd:select 'md-index ma-index mp-id'
                     ;
        }
      }
      container rmep-on-demand-dms {
        description 'On-demand Delay Measurement of remote MEP'
                    ;
        list rmep-on-demand-dm {
          description 'On-demand Delay Measurement of remote MEP'
                      ;
          key 'md-index ma-index mp-id'
              ;
          leaf md-index {
            description 'MD index. Its maximum value depends on the performance'
                      + ' parameters.'
                        ;
            type uint16 {
              range 1..65535 ;
            }
          }
          leaf ma-index {
            description 'MA index. Its maximum value depends on the performance'
                      + ' parameters.'
                        ;
            type uint16 {
              range 1..65535 ;
            }
          }
          leaf mp-id {
            description 'Remote MEPID.'
                        ;
            type uint16 {
              range 1..8191 ;
            }
          }
          leaf frame-delay-1dm-s {
            description 'Frame delay of on-demand 1DM with units of second.'
                        ;
            type uint32 ;
            units second ;
          }
          leaf frame-delay-1dm-ns {
            description 'Frame delay of on-demand 1DM with units of nanosecond.'
                        ;
            type uint32 ;
            units nanosecond ;
          }
          leaf frame-delay-variation-1dm-s {
            description 'Frame delay variation of on-demand 1DM with units of s'
                      + 'econd.'
                        ;
            type uint32 ;
            units second ;
          }
          leaf frame-delay-variation-1dm-ns {
            description 'Frame delay variation of on-demand 1DM with units of n'
                      + 'anosecond.'
                        ;
            type uint32 ;
            units nanosecond ;
          }
          leaf frame-delay-dmm-s {
            description 'Frame delay of on-demand DMM with units of second.'
                        ;
            type uint32 ;
            units second ;
          }
          leaf frame-delay-dmm-ns {
            description 'Frame delay of on-demand DMM with units of nanosecond.'
                        ;
            type uint32 ;
            units nanosecond ;
          }
          leaf frame-delay-variation-dmm-s {
            description 'Frame delay variation of on-demand DMM with units of s'
                      + 'econd.'
                        ;
            type uint32 ;
            units second ;
          }
          leaf frame-delay-variation-dmm-ns {
            description 'Frame delay variation of on-demand DMM with units of n'
                      + 'anosecond.'
                        ;
            type uint32 ;
            units nanosecond ;
          }
          ncd:select 'md-index ma-index'
                     ;
          ncd:select 'md-index ma-index mp-id'
                     ;
        }
      }
      container lb-packet-reads {
        description 'Read the result of the latest unicast LB operation of one '
                  + 'MEP.'
                    ;
        list lb-packet-read {
          description 'Read the result of the latest unicast LB operation of on'
                    + 'e MEP. The system can store results up to a maximum of 5'
                    + '00 MEPs.'
                      ;
          key 'md-index ma-index lmep-id'
              ;
          leaf md-index {
            description 'MD index. Its maximum value depends on the performance'
                      + ' parameters.'
                        ;
            type uint16 {
              range 1..65535 ;
            }
          }
          leaf ma-index {
            description 'MA index. Its maximum value depends on the performance'
                      + ' parameters.'
                        ;
            type uint16 {
              range 1..65535 ;
            }
          }
          leaf lmep-id {
            description 'Local MEPID.'
                        ;
            type uint16 {
              range 1..8191 ;
            }
          }
          leaf total-send-lbm {
            description 'The total number of sent LBMs.'
                        ;
            type uint8 {
              range 0..200 ;
            }
          }
          leaf total-rcvd-lbr {
            description 'The total number of received LBRs.'
                        ;
            type uint8 {
              range 0..200 ;
            }
          }
          ncd:select 'md-index ma-index lmep-id'
                     ;
        }
      }
      container ltr-reads {
        description 'Read the result of specific LT operation.'
                    ;
        list ltr-read {
          description 'Read the result of specific LT operation. The system can'
                    + ' store 1000 results at most.'
                      ;
          key 'md-index ma-index lmep-id trans-id serial-no'
              ;
          leaf md-index {
            description 'MD index. Its maximum value depends on the performance'
                      + ' parameters.'
                        ;
            type uint16 {
              range 1..65535 ;
            }
          }
          leaf ma-index {
            description 'MA index. Its maximum value depends on the performance'
                      + ' parameters.'
                        ;
            type uint16 {
              range 1..65535 ;
            }
          }
          leaf lmep-id {
            description 'Local MEPID.'
                        ;
            type uint16 {
              range 1..8191 ;
            }
          }
          leaf trans-id {
            description 'LTM sequence number.'
                        ;
            type uint32 {
              range 0..4294967295 ;
            }
          }
          leaf serial-no {
            description 'Serial number of terminal.'
                        ;
            type string {
              length 1..8 ;
            }
          }
          leaf hops {
            description Hops. ;
            type uint32 {
              range 1..64 ;
            }
          }
          leaf mac-address {
            description 'LTR reply MAC address.'
                        ;
            type ncd:mac-address ;
          }
          leaf forwarded-flag {
            description 'Forward flag.'
                        ;
            type ncd:string-all ;
          }
          leaf ingress-action {
            description 'Ingress action.'
                        ;
            type ncd:string-all ;
          }
          leaf egress-action {
            description 'Egress action.'
                        ;
            type ncd:string-all ;
          }
          leaf relay-action {
            description 'Relay action.'
                        ;
            type ncd:string-all ;
          }
          ncd:select 'md-index ma-index lmep-id trans-id'
                     ;
          ncd:select 'md-index ma-index lmep-id serial-no'
                     ;
        }
      }
      container rmeps {
        description 'The state information of remote MEP.'
                    ;
        list rmep {
          description 'The state information of remote MEP.'
                      ;
          key 'md-index ma-index rmep-id'
              ;
          leaf md-index {
            description 'MD index. Its maximum value depends on the performance'
                      + ' parameters.'
                        ;
            type uint16 {
              range 1..65535 ;
            }
          }
          leaf ma-index {
            description 'MA index. Its maximum value depends on the performance'
                      + ' parameters.'
                        ;
            type uint16 {
              range 1..65535 ;
            }
          }
          leaf rmep-id {
            description 'Local MEPID.'
                        ;
            type uint16 {
              range 1..8191 ;
            }
          }
          leaf lmep-id {
            description 'Local MEPID.'
                        ;
            type uint16 {
              range 1..8191 ;
            }
          }
          container lm {
            description 'Frame loss measurement.'
                        ;
            container proactive-single-ended {
              description 'Proactive single-ended frame loss measurement.'
                          ;
              container current {
                description 'Current result.'
                            ;
                leaf near-loss-ratio {
                  description 'Near-end frame loss ratio, precision is 1/100000'
                            + '0.'
                              ;
                  type uint64 ;
                }
                leaf far-loss-ratio {
                  description 'Far-end frame loss ratio, precision is 1/1000000.'
                              ;
                  type uint64 ;
                }
                ncd:revise-date 2019-12-18 ;
              }
              container statistics {
                description 'Statistics result.'
                            ;
                leaf near-loss-ratio {
                  description 'Near-end frame loss ratio, precision is 1/100000'
                            + '0.'
                              ;
                  type uint64 ;
                }
                leaf far-loss-ratio {
                  description 'Far-end frame loss ratio, precision is 1/1000000.'
                              ;
                  type uint64 ;
                }
              }
            }
            container proactive-dual-ended {
              description 'Proactive dual-ended frame loss measurement.'
                          ;
              container current {
                description 'Current result.'
                            ;
                leaf near-loss-ratio {
                  description 'Near-end frame loss ratio, precision is 1/100000'
                            + '0.'
                              ;
                  type uint64 ;
                }
                leaf far-loss-ratio {
                  description 'Far-end frame loss ratio, precision is 1/1000000.'
                              ;
                  type uint64 ;
                }
                ncd:revise-date 2019-12-18 ;
              }
              container statistics {
                description 'Statistics result.'
                            ;
                leaf near-loss-ratio {
                  description 'Near-end frame loss ratio, precision is 1/100000'
                            + '0.'
                              ;
                  type uint64 ;
                }
                leaf far-loss-ratio {
                  description 'Far-end frame loss ratio, precision is 1/1000000.'
                              ;
                  type uint64 ;
                }
              }
            }
          }
          container dm {
            description 'Frame delay measurement.'
                        ;
            container proactive-single-ended {
              description 'Proactive single-ended frame delay measurement.'
                          ;
              container current {
                description 'Current result.'
                            ;
                leaf delay {
                  description Delay. ;
                  type uint64 ;
                  units ns ;
                }
                leaf delay-variation {
                  description 'Delay variation.'
                              ;
                  type uint64 ;
                  units ns ;
                }
                ncd:revise-date 2019-12-18 ;
              }
              container statistics {
                description 'Statistics result.'
                            ;
                leaf delay {
                  description Delay. ;
                  type uint64 ;
                  units ns ;
                }
                leaf delay-variation {
                  description 'Delay variation.'
                              ;
                  type uint64 ;
                  units ns ;
                }
              }
            }
            container proactive-dual-ended {
              description 'Proactive dual-ended frame delay measurement.'
                          ;
              container current {
                description 'Current result.'
                            ;
                leaf delay {
                  description Delay. ;
                  type uint64 ;
                  units ns ;
                }
                leaf delay-variation {
                  description 'Delay variation.'
                              ;
                  type uint64 ;
                  units ns ;
                }
                ncd:revise-date 2019-12-18 ;
              }
              container statistics {
                description 'Statistics result.'
                            ;
                leaf delay {
                  description Delay. ;
                  type uint64 ;
                  units ns ;
                }
                leaf delay-variation {
                  description 'Delay variation.'
                              ;
                  type uint64 ;
                  units ns ;
                }
              }
            }
          }
        }
        ncd:revise-date 2019-07-10 ;
      }
    }
  }
  notification loopback {
    description 'CFM loopback notification.'
                ;
    container lb-results {
      config false ;
      description 'CFM loopback notification.'
                  ;
      list lb-result {
        description 'CFM loopback notification.'
                    ;
        key 'md-index ma-index mep-id'
            ;
        leaf md-index {
          description 'MD index.'
                      ;
          type uint16 {
            range 1..65535 {
              description 'MD index, value range from [1..65535].'
                          ;
            }
          }
        }
        leaf ma-index {
          description 'MA index.'
                      ;
          type uint16 {
            range 1..65535 {
              description 'MA index, value range from [1..65535].'
                          ;
            }
          }
        }
        leaf mep-id {
          description 'Local MEPID.'
                      ;
          type uint16 {
            range 1..8191 {
              description 'Local MEP ID, value range from [1..8191].'
                          ;
            }
          }
        }
        leaf serial-no {
          description 'Serial number of terminal.'
                      ;
          type string {
            length 1..8 {
              description 'Range from 1 to 8'
                          ;
            }
          }
        }
        leaf rmep-id {
          description 'Remote MEPID.'
                      ;
          type uint16 {
            range 1..8191 {
              description 'Range from 1 to 8191'
                          ;
            }
          }
          ncd:revise-date 2016-11-21 ;
        }
        leaf total-send-lbm {
          description 'The total number of sent LBMs.'
                      ;
          type uint16 ;
        }
        leaf total-rcvd-lbr {
          description 'The total number of received LBRs.'
                      ;
          type uint16 ;
        }
        leaf total-lost-lbr {
          description 'The total number of lost LBRs.'
                      ;
          type uint16 ;
        }
      }
    }
  }
  notification linktrace {
    description 'CFM linktrace notification.'
                ;
    container ltr-entries {
      config false ;
      description 'CFM linktrace notification.'
                  ;
      list ltr-entry {
        description 'CFM linktrace notification.'
                    ;
        key 'md-index ma-index mep-id'
            ;
        leaf md-index {
          description 'MD index.'
                      ;
          type uint16 {
            range 1..65535 {
              description 'MD index, value range from [1..65535].'
                          ;
            }
          }
        }
        leaf ma-index {
          description 'MA index.'
                      ;
          type uint16 {
            range 1..65535 {
              description 'MA index, value range from [1..65535].'
                          ;
            }
          }
        }
        leaf mep-id {
          description 'Local MEPID.'
                      ;
          type uint16 {
            range 1..8191 {
              description 'Range from 1 to 8191'
                          ;
            }
          }
        }
        leaf serial-no {
          description 'Serial number of terminal.'
                      ;
          type string {
            length 1..8 {
              description 'Range from 1 to 8'
                          ;
            }
          }
        }
        leaf ingress-action {
          description 'Ingress action field of the LTR.'
                      ;
          type enumeration {
            enum IngOk {
              value 1 ;
              description 'The target data frame would be passed through to the'
                        + ' MAC Relay Entity.'
                          ;
            }
            enum IngDown {
              value 2 ;
              description 'The Bridge Port MAC Operational parameter is false.'
                          ;
            }
            enum IngBlocked {
              value 3 ;
              description 'The target data frame would not be forwarded if rece'
                        + 'ived on this port due to active topology enforcement'
                        + '.'
                          ;
            }
            enum IngVID {
              value 4 ;
              description 'The Ingress Port is not in the member set of the LTM'
                        + ' VID, and ingress filtering is enabled, so the targe'
                        + 't data frame would be filtered by ingress filtering.'
                          ;
            }
          }
        }
        leaf egress-action {
          description 'Egress Action field of the LTR.'
                      ;
          type enumeration {
            enum EgrOk {
              value 1 ;
              description 'The targeted data frame would be forwarded.'
                          ;
            }
            enum EgrDown {
              value 2 ;
              description 'The Egress Port can be identified, but that Bridge P'
                        + 'ort MAC Operational parameter is false.'
                          ;
            }
            enum EgrBlocked {
              value 3 ;
              description 'The Egress Port can be identified, but the data fram'
                        + 'e would not pass through the Egress Port due to acti'
                        + 've topology management.'
                          ;
            }
            enum EgrVID {
              value 4 ;
              description 'The Egress Port can be identified, but the Bridge Po'
                        + 'rt is not in the LTM VID member set, so would be fil'
                        + 'tered by egress filtering.'
                          ;
            }
          }
        }
        leaf reply-action {
          description 'The value returned in the Relay Action field.'
                      ;
          type enumeration {
            enum RlyHit {
              value 1 ;
              description 'The LTM reached an MP whose MAC address matches the '
                        + 'target MAC address.'
                          ;
            }
            enum RlyFDB {
              value 2 ;
              description 'The Egress Port was determined by consulting the Fil'
                        + 'tering Database.'
                          ;
            }
            enum RlyMPDB {
              value 3 ;
              description 'The Egress Port was determined by consulting the MIP'
                        + ' CCM Database.'
                          ;
            }
          }
        }
        leaf mac-address {
          description 'LTR reply MAC address.'
                      ;
          type ncd:mac-address ;
        }
        leaf hop {
          description Hop. ;
          type uint32 {
            range 1..64 {
              description 'Range from 1 to 64'
                          ;
            }
          }
        }
        leaf trans-id {
          description 'The value from the LTM Transaction Identifier field in t'
                    + 'he LTM that triggered the transmission of this LTR.'
                      ;
          type uint32 ;
        }
        leaf success-flag {
          description 'The trace status(0-unreached, 1-reached).'
                      ;
          type uint8 ;
        }
      }
    }
  }
  notification on-demand-lm {
    description 'On-demand loss measurement notification.'
                ;
    container lm-results {
      config false ;
      description 'On-demand loss measurement notification.'
                  ;
      list lm-result {
        description 'On-demand loss measurement notification.'
                    ;
        key 'md-index ma-index rmep-id lmep-id'
            ;
        leaf md-index {
          description 'MD index.'
                      ;
          type uint16 {
            range 1..65535 {
              description 'MD index, value range from [1..65535].'
                          ;
            }
          }
        }
        leaf ma-index {
          description 'MA index.'
                      ;
          type uint16 {
            range 1..65535 {
              description 'MA index, value range from [1..65535].'
                          ;
            }
          }
        }
        leaf rmep-id {
          description 'Remote MEPID.'
                      ;
          type uint16 {
            range 1..8191 {
              description 'Range from 1 to 8191'
                          ;
            }
          }
        }
        leaf lmep-id {
          description 'Local MEPID.'
                      ;
          type uint16 {
            range 1..8191 {
              description 'Range from 1 to 8191'
                          ;
            }
          }
        }
        leaf serial-no {
          description 'Serial number of terminal.'
                      ;
          type string {
            length 1..8 {
              description 'Range from 1 to 8'
                          ;
            }
          }
        }
        leaf frame-send-near {
          description 'The frame transmissions of near-end loss measurements.'
                      ;
          type uint32 ;
        }
        leaf frame-send-far {
          description 'The frame transmissions of far-end loss measurements.'
                      ;
          type uint32 ;
        }
        leaf frame-rcv-near {
          description 'The frames received of near-end loss measurements.'
                      ;
          type uint32 ;
        }
        leaf frame-rcv-far {
          description 'The frames received of far-end loss measurements.'
                      ;
          type uint32 ;
        }
        leaf frame-loss-near {
          description 'The lost frames of near-end loss measurements.'
                      ;
          type uint32 ;
        }
        leaf frame-loss-far {
          description 'The lost frames of on-demand loss measurements.'
                      ;
          type uint32 ;
        }
        leaf frame-loss-ratio-near {
          description 'The frame loss ratio of near-end loss measurements.'
                      ;
          type uint64 ;
        }
        leaf frame-loss-ratio-far {
          description 'The frame loss ratio of far-end loss measurements.'
                      ;
          type uint64 ;
        }
        leaf frame-loss-ratio-near-total {
          description 'The total frame loss ratio of near-end loss measurements.'
                      ;
          type uint64 ;
          ncd:revise-date 2018-03-20 ;
        }
        leaf frame-loss-ratio-far-total {
          description 'The total frame loss ratio of far-end loss measurements.'
                      ;
          type uint64 ;
          ncd:revise-date 2018-03-20 ;
        }
      }
    }
  }
  notification on-demand-dm {
    description 'On-demand delay measurement notification.'
                ;
    container dm-results {
      config false ;
      description 'On-demand delay measurement notification.'
                  ;
      list dm-result {
        description 'On-demand delay measurement notification.'
                    ;
        key 'md-index ma-index rmep-id lmep-id'
            ;
        leaf md-index {
          description 'MD index.'
                      ;
          type uint16 {
            range 1..65535 {
              description 'MA index, value range from [1..65535].'
                          ;
            }
          }
        }
        leaf ma-index {
          description 'MA index.'
                      ;
          type uint16 {
            range 1..65535 {
              description 'MA index, value range from [1..65535].'
                          ;
            }
          }
        }
        leaf rmep-id {
          description 'Remote MEPID.'
                      ;
          type uint16 {
            range 1..8191 {
              description 'Range from 1 to 8191'
                          ;
            }
          }
        }
        leaf lmep-id {
          description 'Local MEPID.'
                      ;
          type uint16 {
            range 1..8191 {
              description 'Range from 1 to 8191'
                          ;
            }
          }
        }
        leaf serial-no {
          description 'Serial number of terminal.'
                      ;
          type string {
            length 1..8 {
              description 'Range from 1 to 8'
                          ;
            }
          }
        }
        leaf ave-frame-delay-s {
          description 'The average frame delay of on-demand DM with units of se'
                    + 'cond.'
                      ;
          type uint32 ;
          units second ;
        }
        leaf ave-frame-delay-ns {
          description 'The average frame delay of on-demand DM with units of na'
                    + 'nosecond.'
                      ;
          type uint32 ;
          units nanosecond ;
        }
        leaf ave-frame-delay-variation-s {
          description 'The average frame delay variation of on-demand DM with u'
                    + 'nits of second.'
                      ;
          type uint32 ;
          units second ;
        }
        leaf ave-frame-delay-variation-ns {
          description 'The average frame delay variation of on-demand DM with u'
                    + 'nits of nanosecond.'
                      ;
          type uint32 ;
          units nanosecond ;
        }
        leaf frame-delay-s {
          description 'The frame delay of on-demand DM with units of second.'
                      ;
          type uint32 ;
          units second ;
        }
        leaf frame-delay-ns {
          description 'The frame delay of on-demand DM with units of nanosecond.'
                      ;
          type uint32 ;
          units nanosecond ;
        }
        leaf frame-delay-variation-s {
          description 'The frame delay variation of on-demand DM with units of '
                    + 'second.'
                      ;
          type uint32 ;
          units second ;
        }
        leaf frame-delay-variation-ns {
          description 'The frame delay variation of on-demand DM with units of '
                    + 'nanosecond.'
                      ;
          type uint32 ;
          units nanosecond ;
        }
        leaf frame-delay-var-ratio {
          description 'The frame delay variation ratio of on-demand DM.'
                      ;
          type uint64 ;
        }
        leaf ave-frame-delay-var-ratio {
          description 'The average frame delay variation ratio of on-demand DM.'
                      ;
          type uint64 ;
        }
        leaf average-delay {
          description 'The average frame delay of on-demand DM with units of na'
                    + 'nosecond.'
                      ;
          type uint64 ;
          units nanosecond ;
          ncd:revise-date 2018-05-18 ;
        }
        leaf average-delay-variation {
          description 'The average frame delay variation of on-demand DM with u'
                    + 'nits of nanosecond.'
                      ;
          type uint64 ;
          units nanosecond ;
          ncd:revise-date 2018-05-18 ;
        }
        leaf delay {
          description 'The frame delay of on-demand DM with units of nanosecond.'
                      ;
          type uint64 ;
          units nanosecond ;
          ncd:revise-date 2018-05-18 ;
        }
        leaf delay-variation {
          description 'The frame delay variation of on-demand DM with units of '
                    + 'nanosecond.'
                      ;
          type uint64 ;
          units nanosecond ;
          ncd:revise-date 2018-05-18 ;
        }
        leaf max-delay {
          description 'The max frame delay of on-demand DM with units of nanose'
                    + 'cond.'
                      ;
          type uint64 ;
          units nanosecond ;
          ncd:revise-date 2019-01-22 ;
        }
        leaf max-delay-variation {
          description 'The max frame delay variation of on-demand DM with units'
                    + ' of nanosecond.'
                      ;
          type uint64 ;
          units nanosecond ;
          ncd:revise-date 2019-01-22 ;
        }
        leaf min-delay {
          description 'The min frame delay of on-demand DM with units of nanose'
                    + 'cond.'
                      ;
          type uint64 ;
          units nanosecond ;
          ncd:revise-date 2019-01-22 ;
        }
        leaf min-delay-variation {
          description 'The min frame delay variation of on-demand DM with units'
                    + ' of nanosecond.'
                      ;
          type uint64 ;
          units nanosecond ;
          ncd:revise-date 2019-01-22 ;
        }
      }
    }
  }
  notification mtu-detect {
    description 'CFM MTU detect notification.'
                ;
    container mtu-results {
      config false ;
      description 'CFM MTU detect notification.'
                  ;
      list mtu-result {
        description 'CFM MTU detect notification.'
                    ;
        key 'md-index ma-index mep-id'
            ;
        leaf md-index {
          description 'MD index.'
                      ;
          type uint16 {
            range 1..65535 ;
          }
        }
        leaf ma-index {
          description 'MA index.'
                      ;
          type uint16 {
            range 1..65535 ;
          }
        }
        leaf mep-id {
          description 'Local MEPID.'
                      ;
          type uint16 {
            range 1..8191 ;
          }
        }
        leaf serial-no {
          description 'Serial number of terminal.'
                      ;
          type string {
            length 1..8 ;
          }
        }
        leaf mtu-size {
          description 'The MTU detected.'
                      ;
          type uint32 {
            range '0 | 64..9216'
                  ;
          }
        }
      }
    }
    ncd:revise-date 2018-05-18 ;
  }
  notification test {
    description 'CFM ETH-Test notification.'
                ;
    container test-results {
      config false ;
      description 'CFM ETH-Test notification.'
                  ;
      list test-result {
        description 'CFM ETH-Test notification.'
                    ;
        key 'md-index ma-index mep-id'
            ;
        leaf md-index {
          description 'MD index.'
                      ;
          type uint16 {
            range 1..65535 ;
          }
        }
        leaf ma-index {
          description 'MA index.'
                      ;
          type uint16 {
            range 1..65535 ;
          }
        }
        leaf mep-id {
          description 'Local MEPID.'
                      ;
          type uint16 {
            range 1..8191 ;
          }
        }
        leaf serial-no {
          description 'Serial number of terminal.'
                      ;
          type uint64 ;
        }
        leaf total-rcvd {
          description 'The total number of received TST packets.'
                      ;
          type uint32 ;
        }
        leaf total-lost {
          description 'The total number of lost TST packets.'
                      ;
          type uint32 ;
        }
        leaf bandwidth {
          description Bandwidth. ;
          type uint32 ;
          units kbps ;
        }
      }
    }
    ncd:revise-date 2018-05-18 ;
  }
}
