module zxr10-system-oc {

  yang-version "1";

  // namespace
  namespace "http://www.zte.com.cn/zxr10/netconf/schema/rosng/zxr10-system-oc";

  prefix "zte-sys";

  // import some basic types
  import openconfig-system { prefix oc-sys; }

  // meta
  organization "ZTE Corporation";

  contact "ZTE Corporation  \n"
        + "   Nanjing Institute of ZTE Corporation \n"
        + "   No.68 Zijinghua Rd. Yuhuatai District, Nanjing, China \n"
        + '   Tel: +86-25-52870000'
          ;

  description
    "The netconf module to describe the System Management.";

  revision "2020-07-07" {
    description
      "Initial revision.";
  }

  // grouping statements

  grouping system-operational-state {
    description
      "The operational state data for the system.";

    leaf uptime {
        type uint32;
        description
          "The system uptime.";
    }
  }

  // augment statements

  augment "/oc-sys:system/oc-sys:state" {
    description
      "The system uptime.";

    uses system-operational-state;
  }

  // rpc statements

  // notification statements
}
