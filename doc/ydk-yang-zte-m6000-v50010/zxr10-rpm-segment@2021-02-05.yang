module zxr10-rpm-segment {
  namespace 'http://www.zte.com.cn/zxr10/netconf/schema/rosng/rpm-segment'
            ;
  prefix rpm-segment ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2021-02-05 {
    description 'Add a new value END.M in enumeration SRV6-LOCAL-SID-FUNCTYPE.'
                ;
  }
  revision 2020-11-06 {
    description "Modify the max value of SRv6 locator's ipv6-prefix-length from"
              + " 92 to 120.
\nModify the max value of SRv6 locator's block-len"
              + "gthfrom 91 to 96."
                ;
  }
  revision 2020-10-29 {
    description 'Add a new leaf node vpls-name to support VPLS name.The paths i'
              + 's "state/srv6/local-sids/local-sid/vpls-name".'+"\n"
              + 'Add a new leaf node fa-id to support SRv6 in slice.The paths i'
              + 's "state/srv6/local-sids/local-sid/fa-id".'
                ;
  }
  revision 2020-09-22 {
    description '1. Obsolete the container srv6-sids, the path is "/rpm-segment'
              + ':state/rpm-segment:srv6/rpm-segment:srv6-sids";'+"\n"
              + '2. Add a container local-sids,the path is "/rpm-segment:state/'
              + 'rpm-segment:srv6/rpm-segment:local-sids"'+"\n"
              + '3. Add a container local-sid-summary,the path is "/rpm-segment'
              + ':state/rpm-segment:srv6/rpm-segment:local-sid-summary"'+"\n"
              + '4. Add a typedef "SRV6-LOCAL-SID-FUNCTYPE"'
                ;
  }
  revision 2020-09-06 {
    description "Add nodes for SRv6 locator's flex-algorithm ID configuration a"
              + "nd state."
                ;
  }
  revision 2020-08-18 {
    description 'Add new nodes for SR adjacency sid holdtime configuration. The'
              + ' path is "configuration/adj-sid-holdtime".'
                ;
  }
  revision 2020-07-25 {
    description '1. Obsolete the nodes of /rpm-segment:configuration/rpm-segmen'
              + 't:srv6/rpm-segment:locators/rpm-segment:locator/rpm-segment:is'
              + '-default;'+"\n"
              + '2. Obsolete the nodes of /rpm-segment:state/rpm-segment:srv6/r'
              + 'pm-segment:locators/rpm-segment:locator/rpm-segment:is-default'
              + ';'
                ;
  }
  revision 2020-06-20 {
    description 'Add new nodes for SR EPE configuration. The path is "configura'
              + 'tion/sr-epes".'
                ;
  }
  revision 2020-06-06 {
    description '1.Add nodes for SRv6 locator configuration and state.'+"\n"
              + '2.Obsolete the nodes of /rpm-segment:configueration/rpm-segmen'
              + 't:srv6/rpm-segment:sid-range;'+"\n"
              + '3.Obsolete the nodes of /rpm-segment:state/rpm-segment:srv6/rp'
              + 'm-segment:srv6-sid-range.'
                ;
  }
  revision 2020-05-19 {
    description 'Add a new node sr-policy-binding-sids. The paths is "configura'
              + 'tion/sr-policy-binding-sids".'
                ;
  }
  revision 2020-04-18 {
    description '1. Obsolete the nodes of /rpm-segment:state/rpm-segment:ipv4/r'
              + 'pm-segment:adjacency-sid;'+"\n"
              + '2. Obsolete the nodes of /rpm-segment:state/rpm-segment:ipv4/r'
              + 'pm-segment:adjacency-sid-new;'+"\n"
              + '3. Obsolete the nodes of /rpm-segment:state/rpm-segment:ipv6/r'
              + 'pm-segment:adjacency-sid;'+"\n"
              + '4. Obsolete the nodes of /rpm-segment:state/rpm-segment:ipv6/r'
              + 'pm-segment:adjacency-sid-new.'
                ;
  }
  revision 2020-03-30 {
    description 'Obsolete the nodes of configuration/ipv4/adjacency-protect-ips'
              + ' and configuration/ipv4/adjacency-protect-ids. Add the new nod'
              + 'es of configuration/ipv4/adjacency-ip-protect-tunnels and conf'
              + 'iguration/ipv4/adjacency-id-protect-tunnels.'
                ;
  }
  revision 2020-03-04 {
    description 'Modify node for static binding SID to a choice node. The path '
              + 'is configuration/binding-sids/binding-sid/label. Add a new typ'
              + 'e of assign binding SID automatically, the path is configurati'
              + 'on/binding-sids/binding-sid/label/auto.'
                ;
  }
  revision 2020-02-16 {
    description 'Add nodes for SRv6 configuration and state.'
                ;
  }
  revision 2020-02-04 {
    description 'Modify the range of prefix-sid index to 0-4294967294.'
                ;
  }
  revision 2020-01-15 {
    description 'Add new nodes adjacencys and adjacency-intfs in aii to support'
              + ' adj-sid in slice. The paths are "configuration/aiis/aii/ipv4/'
              + 'adjacencys " and "configuration/aiis/aii/ipv4/adjacency-intfs"'
              + '.'+"\n"
              + 'Delete feature in configuration container fa and state leaf fa'
              + '-id.'
                ;
  }
  revision 2019-12-21 {
    description 'Add new nodes for interface aii.The paths are "configuration/i'
              + 'nterface "and "configuration/interface/aii".'
                ;
  }
  revision 2019-11-20 {
    description 'Add new nodes for adjecency protect SID, the paths are configu'
              + 'ration/ipv4/adjacencys/adjacency/protect-sid, configuration/ip'
              + 'v4/adjacencys/adjacency-intfs/protect-sid. Add new nodes for a'
              + 'djecency protect sr-path, the paths are configuration/ipv4/adj'
              + 'acency-protect-ips, configuration/ipv4/adjacency-protect-ids.'
                ;
  }
  revision 2019-11-15 {
    description 'Add new nodes aiis and fas for SR slice. The paths are "config'
              + 'uration/aiis" and "configuration/fas".'
                ;
  }
  revision 2019-10-30 {
    description 'Add a new leaf node erld to support max-sid-depth erld.The pat'
              + 'hs is "configuration/max-sid-depths/erld-value".'
                ;
  }
  revision 2019-09-07 {
    description 'Add containers "state/ipv4/adjacency-sid-new" and "state/ipv6/'
              + 'adjacency-sid-new".'
                ;
  }
  revision 2019-09-01 {
    description 'Add new project label of MSR to support SR.'
                ;
  }
  revision 2019-06-10 {
    description 'Absolute this revision'+"\n"
              + 'Add the query node keys "local-id", "remote-id" and "local-int'
              + 'erface" for segment-routing adjacency SID information.'+"\n"
              + 'The paths are "state/ipv4/adjacency-sid" and "state/ipv6/adjac'
              + 'ency-sid".'+"\n"
              + 'Add container adjacency-intfs to support unnumbered interface '
              + 'ADJ-SID.The paths are "configuration/ipv4/adjacency-intfs" and'
              + ' "configuration/ipv6/adjacency-intfs"'
                ;
  }
  revision 2019-05-31 {
    description '1. Obsolete the leaf node router-id. The paths is "state/ipv6/'
              + 'remote-prefix-sid/infomation/router-id".'+"\n"
              + '2. Add a new leaf node router-id-str to support ipv6 address. '
              + 'The paths is "state/ipv6/remote-prefix-sid/infomation/router-i'
              + 'd-str".'
                ;
  }
  revision 2019-05-10 {
    description 'Add new project label of 6700 and T8000 to support SRMS.'
                ;
  }
  revision 2019-04-08 {
    description 'Add new project label of MW(NR8000) to support segment-routing.'
                ;
  }
  revision 2019-02-21 {
    description 'Add new project label of 6100/65v5/6700 to support msd.'
                ;
  }
  revision 2019-02-13 {
    description 'Add the query node for ipv6 segment-routing adjacency SID info'
              + 'rmation.'+"\n"
              + 'The path is "state/ipv6/adjacency-sid".'
                ;
  }
  revision 2018-12-27 {
    description 'Add a new node adjacencys. The paths is "configuration/ipv6/ad'
              + 'jacencys".'+"\n"
              + 'Add new project label.'
                ;
  }
  revision 2018-09-19 {
    description 'Add a new node maximum-sid-depths. The paths is "configuration'
              + '/maximum-sid-depths".'+"\n"
              + 'Add new nodes mapping-servers. The paths are "configuration/ip'
              + 'v4/mapping-servers" and "configuration/ipv6/mapping-servers".'+"\n"
              + 'Add new nodes prefix-sid-maps. The paths are "state/ipv4/prefi'
              + 'x-sid-map" and "state/ipv6/prefix-sid-map".'
                ;
  }
  revision 2018-08-13 {
    description 'Add a new node adjacencys. The paths is "configuration/ipv4/ad'
              + 'jacencys".'
                ;
  }
  revision 2018-08-07 {
    description 'Add a new node binding-sids. The paths is "configuration/bindi'
              + 'ng-sids".'
                ;
  }
  revision 2018-05-29 {
    description '1. Obsolete the node remote-srgb. The paths is "state/ipv4/rem'
              + 'ote-srgb".'+"\n"
              + '2. Add a new node remote-srgbs. The paths is "state/ipv4/remot'
              + 'e-srgbs".'
                ;
  }
  revision 2017-08-21 {
    description '1.Add the node for IPv6 segment-routing.'+"\n"
              + 'The path is "configuration/ipv6".'+"\n"
              + 'The path is "state/ipv6".'
                ;
  }
  revision 2017-01-05 {
    description '1.Add the query node for segment-routing local prefix SID info'
              + 'rmation.'+"\n"
              + 'The path is "state/ipv4/local-prefix-sid".'+"\n"
              + '2.Add the query node for segment-routing remote prefix SID inf'
              + 'ormation.'+"\n"
              + 'The path is "state/ipv4/remote-prefix-sid".'+"\n"
              + '3.Add the query node for segment-routing local SRGB informatio'
              + 'n.'+"\n"
              + 'The path is "state/ipv4/local-srgb".'+"\n"
              + '4.Add the query node for segment-routing remote SRGB informati'
              + 'on.'+"\n"
              + 'The path is "state/ipv4/remote-srgb".'
                ;
  }
  revision 2016-12-20 {
    description 'Add the query node for segment-routing adjacency SID informati'
              + 'on.'+"\n"
              + 'The path is "state/adjacency-sid".'
                ;
  }
  revision 2016-10-19 {
    description 'The initial version.'
                ;
  }
  feature mapping-server {
    description 'This configuration is used to configure the map of prefix and '
              + 'sid.'
                ;
  }
  feature msd {
    description 'This configuration is used to configure maximum SID depth.'
                ;
  }
  feature network-slice ;
  typedef GLOBAL-STATUS {
    type enumeration {
      enum ENABLE {
        value 0 ;
      }
      enum DISABLE {
        value 1 ;
      }
    }
    default ENABLE ;
    description 'Value of segment routing status.'
                ;
  }
  typedef LOCAL-PREFIX-PHP-FLAG {
    type enumeration {
      enum EXPLICIT {
        value 1 ;
      }
      enum IMPLICIT {
        value 2 ;
      }
      enum NULL {
        value 0 ;
      }
    }
    default NULL ;
    description 'The php-flag of local prefix sid.'
                ;
  }
  typedef LOCAL-PREFIX-NODE-FLAG {
    type enumeration {
      enum TRUE {
        value 1 ;
        description 'Node flag.'
                    ;
      }
      enum FALSE {
        value 0 ;
        description 'No node flag.'
                    ;
      }
    }
    default FALSE ;
    description 'The node-flag of local prefix sid.'
                ;
  }
  typedef ADJ-TYPE {
    type enumeration {
      enum INVALID {
        value 0 ;
      }
      enum LOCAL {
        value 1 ;
      }
      enum REMOTE {
        value 2 ;
      }
    }
    default INVALID ;
    description 'The type of adjacency SID.'
                ;
  }
  typedef REMOTE-PREFIX-FLAG {
    type enumeration {
      enum NULL {
        value 0 ;
      }
      enum IMPLICIT {
        value 1 ;
      }
      enum EXPLICIT {
        value 2 ;
      }
      enum NODE {
        value 3 ;
      }
      enum IMPLICIT-NODE {
        value 4 ;
      }
      enum EXPLICIT-NODE {
        value 5 ;
      }
    }
    default NULL ;
    description 'The sid flag of remote prefix sid.'
                ;
  }
  typedef SRV6-LOCAL-SID-FUNCTYPE {
    type enumeration {
      enum END {
        value 1 ;
      }
      enum END.X {
        value 2 ;
      }
      enum END.B6 {
        value 3 ;
      }
      enum END.BM {
        value 4 ;
      }
      enum L3VPN.DX4 {
        value 5 ;
      }
      enum L3VPN.DX6 {
        value 6 ;
      }
      enum L3VPN.DT4 {
        value 7 ;
      }
      enum L3VPN.DT6 {
        value 8 ;
      }
      enum L3VPN.DT46 {
        value 9 ;
      }
      enum VPWS.DX2 {
        value 10 ;
      }
      enum VPWS.DX2V {
        value 11 ;
      }
      enum QVPLS.DT2U {
        value 12 ;
      }
      enum VPLS.DT2U {
        value 13 ;
      }
      enum VPLS.DX2 {
        value 14 ;
      }
      enum QVPLS.DX2 {
        value 15 ;
      }
      enum VPLS.DT2M {
        value 16 ;
      }
      enum QVPLS.DT2M {
        value 17 ;
      }
      enum END.OP {
        value 18 ;
      }
      enum END.M {
        value 19 ;
      }
    }
    description 'The function type of srv6 local sid.'
                ;
  }
  container configuration {
    description 'The configuration information processing of segment-routing mo'
              + 'dule.'
                ;
    container ipv4 {
      description 'The node for IPv4 segment-routing.'
                  ;
      container global-status {
        description 'The node of global segment-routing status.'
                    ;
        leaf status {
          description 'Enable or disable the status of global IPv4 segment-rout'
                    + 'ing.'
                      ;
          type GLOBAL-STATUS ;
          default ENABLE ;
        }
      }
      container local-prefix-sid {
        description 'The configuration node of local prefix sid.'
                    ;
        list local-prefix-sid {
          description 'The configuration node of local prefix sid.'
                      ;
          key 'dest-addr mask-addr'
              ;
          leaf dest-addr {
            description 'The destination address of local prefix sid.'
                        ;
            type ncd:ipv4-address ;
          }
          leaf mask-addr {
            description 'The mask address of local prefix sid.'
                        ;
            type ncd:ipv4-address ;
          }
          leaf index {
            description 'The index value of local prefix sid.'
                        ;
            type uint32 {
              range 0..4294967294 ;
            }
            default 0 ;
          }
          leaf node-flag {
            description 'The node-flag of local prefix sid.'
                        ;
            type LOCAL-PREFIX-NODE-FLAG ;
            default FALSE ;
          }
          leaf php-flag {
            description 'The label operation of penultimate hop.'
                        ;
            type LOCAL-PREFIX-PHP-FLAG ;
            default NULL ;
          }
        }
      }
      container adjacencys {
        description 'The configuration node of SR adjacency-SID.'
                    ;
        list adjacency {
          description 'The configuration node of SR adjacency-SID.'
                      ;
          key 'local-ip remote-ip'
              ;
          leaf local-ip {
            description 'The local IP address of SR adjacency-SID.'
                        ;
            type ncd:ipv4-address ;
          }
          leaf remote-ip {
            description 'The remote IP address of SR adjacency-SID.'
                        ;
            type ncd:ipv4-address ;
          }
          leaf sid {
            description 'The SID value of SR adjacency-SID.'
                        ;
            type int32 ;
          }
          leaf protect-sid {
            description 'The SID of protect path.'
                        ;
            type uint32 {
              range 16..1048575 ;
            }
            ncd:revise-date 2019-11-20 ;
          }
        }
        ncd:revise-date 2018-08-13 ;
      }
      container mapping-server {
        // if-feature mapping-server ;
        description 'The configuration node of prefix-sid-map in ipv4.'
                    ;
        list prefix-sid-map {
          description 'The configuration node of prefix-sid-map in ipv4.'
                      ;
          key 'dest-addr mask-addr'
              ;
          leaf dest-addr {
            description 'The first prefix mapped with sid.'
                        ;
            type ncd:ipv4-address ;
          }
          leaf mask-addr {
            description 'The mask address of first v4 prefix mapped with sid.'
                        ;
            type ncd:ipv4-address ;
          }
          leaf first-sid {
            description 'The first SID.'
                        ;
            type int32 {
              range 0..1048559 ;
            }
            mandatory true ;
          }
          leaf range {
            description 'The quantity of maps of prefix and sid.'
                        ;
            type int32 {
              range 1..65535 ;
            }
            mandatory true ;
          }
        }
        ncd:revise-date 2018-09-19 ;
      }
      container adjacency-intfs {
        description 'The configuration node of SR adjacency-SID-interface unnum'
                  + 'bered.'
                    ;
        list adjacency-intf {
          description 'The configuration node of SR adjacency-SID-interface unn'
                    + 'umbered.'
                      ;
          key 'local-interface remote-router-id'
              ;
          leaf local-interface {
            description 'the local interface of SR adjacency-SID.'
                        ;
            type ncd:ifname ;
          }
          leaf remote-router-id {
            description 'The remote router ID SR adjacency-SID.'
                        ;
            type ncd:ipv4-address ;
          }
          leaf sid {
            description 'The SID value of SR adjacency-SID.'
                        ;
            type int32 ;
          }
          leaf protect-sid {
            description 'The SID of protect path.'
                        ;
            type uint32 {
              range 16..1048575 ;
            }
            ncd:revise-date 2019-11-20 ;
          }
        }
        ncd:revise-date 2019-06-10 ;
      }
      container adjacency-ip-protect-tunnels {
        description 'Set the protect tunnel of adjacency(IP type).'
                    ;
        presence primary-tunnel-id ;
        list adjacency-ip-protect-tunnel {
          key 'loca-ip remote-ip'
              ;
          leaf loca-ip {
            description 'The local IP address of SR adjacency.'
                        ;
            type ncd:ipv4-address-none-zero ;
          }
          leaf remote-ip {
            description 'The remote IP address of SR adjacency.'
                        ;
            type ncd:ipv4-address-none-zero ;
          }
          leaf primary-tunnel-id {
            description 'The primary protect tunnel ID.'
                        ;
            type uint32 {
              range 1..65535 ;
            }
            mandatory true ;
          }
          leaf secondary-tunnel-id {
            description 'The secondary protect tunnel ID.'
                        ;
            type uint32 {
              range 1..65535 ;
            }
          }
        }
        ncd:revise-date 2020-03-30 ;
      }
      container adjacency-id-protect-tunnels {
        description 'Set the protect tunnel of adjacency(ID type).'
                    ;
        presence primary-tunnel-id ;
        list adjacency-id-protect-tunnel {
          key 'local-interface remote-router-id'
              ;
          leaf local-interface {
            description 'The local interface of SR adjacency.'
                        ;
            type ncd:ifname ;
          }
          leaf remote-router-id {
            description 'The remote router ID SR adjacency.'
                        ;
            type ncd:ipv4-address-none-zero ;
          }
          leaf primary-tunnel-id {
            description 'The primary protect tunnel ID.'
                        ;
            type uint32 {
              range 1..65535 ;
            }
            mandatory true ;
          }
          leaf secondary-tunnel-id {
            description 'The secondary protect tunnel ID.'
                        ;
            type uint32 {
              range 1..65535 ;
            }
          }
        }
        ncd:revise-date 2020-03-30 ;
      }
      container adjacency-protect-ips {
        status obsolete {
          ncd:revise-date 2020-03-30 ;
        }
        list adjacency-protect-ip {
          key 'loca-ip remote-ip sr-path-identifier'
              ;
          leaf loca-ip {
            description 'The local IP address of SR adjacency.'
                        ;
            type ncd:ipv4-address-none-zero ;
          }
          leaf remote-ip {
            description 'The remote IP address of SR adjacency.'
                        ;
            type ncd:ipv4-address-none-zero ;
          }
          leaf sr-path-identifier {
            description 'The protect SR path identifier.'
                        ;
            type uint32 {
              range 1..65535 ;
            }
          }
          leaf bfd-rd {
            description 'Remote discriminator for BFD.'
                        ;
            type ncd:ipv4-address ;
          }
          leaf bfd-template-name {
            description 'The template name for BFD.'
                        ;
            type string {
              length 0..31 ;
            }
          }
        }
        ncd:revise-date 2019-11-20 ;
      }
      container adjacency-protect-ids {
        status obsolete {
          ncd:revise-date 2020-03-30 ;
        }
        list adjacency-protect-id {
          key 'local-interface remote-router-id sr-path-identifier'
              ;
          leaf local-interface {
            description 'The local interface of SR adjacency.'
                        ;
            type ncd:ifname ;
          }
          leaf remote-router-id {
            description 'The remote router ID SR adjacency.'
                        ;
            type ncd:ipv4-address-none-zero ;
          }
          leaf sr-path-identifier {
            description 'The protect SR path identifier.'
                        ;
            type uint32 {
              range 1..65535 ;
            }
          }
          leaf bfd-rd {
            description 'Remote discriminator for BFD.'
                        ;
            type ncd:ipv4-address ;
          }
          leaf bfd-template-name {
            description 'The template name for BFD.'
                        ;
            type string {
              length 0..31 ;
            }
          }
        }
        ncd:revise-date 2019-11-20 ;
      }
    }
    container ipv6 {
      description 'The node for IPv6 segment-routing.'
                  ;
      container global-status {
        description 'The node of global segment-routing status.'
                    ;
        leaf status {
          description 'Enable or disable the status of global IPv6 segment-rout'
                    + 'ing.'
                      ;
          type GLOBAL-STATUS ;
          default ENABLE ;
        }
      }
      container local-prefix-sid {
        description 'The configuration node of local prefix sid.'
                    ;
        list local-prefix-sid {
          description 'The configuration node of local prefix sid.'
                      ;
          key 'prefix prefix-length'
              ;
          leaf prefix {
            description 'The destination address of local prefix sid.'
                        ;
            type ncd:ipv6-address ;
          }
          leaf prefix-length {
            description 'The prefix length of local prefix sid.'
                        ;
            type uint8 {
              range 0..128 ;
            }
          }
          leaf index {
            description 'The index value of local prefix sid.'
                        ;
            type uint32 {
              range 0..4294967294 ;
            }
            default 0 ;
          }
          leaf node-flag {
            description 'The node-flag of local prefix sid.'
                        ;
            type LOCAL-PREFIX-NODE-FLAG ;
            default FALSE ;
          }
          leaf php-flag {
            description 'The label operation of penultimate hop.'
                        ;
            type LOCAL-PREFIX-PHP-FLAG ;
            default NULL ;
          }
        }
      }
      container mapping-server {
        // if-feature mapping-server ;
        description 'The configuration node of prefix-sid-map in ipv6.'
                    ;
        list prefix-sid-map {
          description 'The configuration node of prefix-sid-map in ipv6.'
                      ;
          key 'prefix prefix-len'
              ;
          leaf prefix {
            description 'The first ipv6 prefix mapped with sid.'
                        ;
            type ncd:ipv6-address ;
          }
          leaf prefix-len {
            description 'The lenth of first ipv6 prefix mapped with sid.'
                        ;
            type uint8 {
              range 1..128 ;
            }
          }
          leaf first-sid {
            description 'The first SID.'
                        ;
            type int32 {
              range 0..1048559 ;
            }
            mandatory true ;
          }
          leaf range {
            description 'The quantity of maps of prefix and sid.'
                        ;
            type int32 {
              range 1..65535 ;
            }
            mandatory true ;
          }
        }
        ncd:revise-date 2018-09-19 ;
      }
      container adjacencys {
        description 'The configuration node of SR adjacency-SID.'
                    ;
        list adjacency {
          description 'The configuration node of IPv6 SR adjacency-SID.'
                      ;
          key 'local-ipv6 remote-ipv6'
              ;
          leaf local-ipv6 {
            description 'the local IPv6 address of IPv6 SR adjacency-SID.'
                        ;
            type ncd:ipv6-address ;
          }
          leaf remote-ipv6 {
            description 'The remote IPv6 address of IPv6 SR adjacency-SID.'
                        ;
            type ncd:ipv6-address ;
          }
          leaf sid {
            description 'The SID value of IPv6 SR adjacency-SID.'
                        ;
            type int32 {
              range 16..1048575 ;
            }
            mandatory true ;
          }
        }
        ncd:revise-date 2018-12-27 ;
      }
      container adjacency-intfs {
        description 'The configuration node of SR adjacency-SID-interface unnum'
                  + 'bered.'
                    ;
        list adjacency-intf {
          description 'The configuration node of SR adjacency-SID-interface unn'
                    + 'umbered.'
                      ;
          key 'local-interface remote-router-id'
              ;
          leaf local-interface {
            description 'the local interface of SR adjacency-SID.'
                        ;
            type ncd:ifname ;
          }
          leaf remote-router-id {
            description 'The remote router ID SR adjacency-SID.'
                        ;
            type ncd:ipv6-address ;
          }
          leaf sid {
            description 'The SID value of SR adjacency-SID.'
                        ;
            type int32 {
              range 16..1048575 ;
            }
            mandatory true ;
          }
        }
        ncd:revise-date 2019-06-10 ;
      }
      ncd:revise-date 2017-08-21 ;
    }
    container binding-sids {
      description 'The configuration node of SR binding-SID.'
                  ;
      list binding-sid {
        description 'The configuration node of SR binding-SID.'
                    ;
        key tunnel-id ;
        leaf tunnel-id {
          description 'The tunnel id of SR binding-SID.'
                      ;
          type uint32 {
            range 1..4294967295 ;
          }
        }
        choice label {
          description 'Choose the type of assigning binding SID.'+"\n"
                    + 'sid: Specify the SID value.'+"\n"
                    + 'auto: Assign the SID automatically.'
                      ;
          case sid {
            description 'Specify the SID value case.'
                        ;
            leaf sid {
              description 'The SID of SR binding-SID.'
                          ;
              type uint32 {
                range 16..1048575 ;
              }
              mandatory true ;
            }
          }
          case auto {
            description 'Assign SID automatically case.'
                        ;
            leaf auto {
              description 'Assign SID automatically.'
                          ;
              type enumeration {
                enum auto {
                  value 1 ;
                }
              }
              mandatory true ;
            }
            ncd:revise-date 2020-03-04 ;
          }
        }
      }
      ncd:revise-date 2018-08-07 ;
    }
    container max-sid-depths {
      // if-feature msd ;
      description 'The configuration of maximum SID depth.'
                  ;
      list max-sid-depth {
        description 'The configuration of maximum SID depth.'
                    ;
        key type ;
        leaf type {
          description 'The sub type of MSD,such as MPLS.'
                      ;
          type enumeration {
            enum mpls {
              value 1 ;
              description 'MPLS MSD'
                          ;
            }
          }
        }
        leaf value {
          description 'The value of MSD.'
                      ;
          type uint32 {
            range 0..254 {
              description 'MSD value'
                          ;
            }
          }
          mandatory true ;
        }
      }
      leaf erld-value {
        description 'The configuration of max-sid-depth erld.'
                    ;
        type int32 {
          range 0..254 {
            description 'ERLD value'
                        ;
          }
        }
        ncd:revise-date 2019-10-30 ;
      }
      ncd:revise-date 2018-09-19 ;
    }
    container aiis {
      // if-feature network-slice ;
      description 'The node for segment-routing zdministrative instance.'
                  ;
      list aii {
        description 'The node for segment-routing zdministrative instances.'
                    ;
        key id ;
        leaf id {
          description 'Segment-routing slice identifier.'
                      ;
          type uint32 {
            range 1..4294967295 ;
          }
        }
        container ipv4 {
          description 'The node for IPv4 segment-routing.'
                      ;
          container local-prefix-sids {
            description 'The configuration node of local prefix sid.'
                        ;
            list local-prefix-sid {
              description 'The configuration node of local prefix sid.'
                          ;
              key 'dest-addr mask-addr'
                  ;
              leaf dest-addr {
                description 'The destination address of local prefix sid.'
                            ;
                type ncd:ipv4-address ;
              }
              leaf mask-addr {
                description 'The mask address of local prefix sid.'
                            ;
                type ncd:ipv4-address ;
              }
              leaf index {
                description 'The index value of local prefix sid.'
                            ;
                type uint32 {
                  range 0..4294967294 ;
                }
                default 0 ;
              }
              leaf node-flag {
                description 'The node-flag of local prefix sid.'
                            ;
                type LOCAL-PREFIX-NODE-FLAG ;
                default FALSE ;
              }
              leaf php-flag {
                description 'The label operation of penultimate hop.'
                            ;
                type LOCAL-PREFIX-PHP-FLAG ;
                default NULL ;
              }
            }
          }
          container adjacencys {
            description 'The configuration node of SR adjacency-SID.'
                        ;
            list adjacency {
              description 'The configuration node of SR adjacency-SID.'
                          ;
              key 'local-ip remote-ip'
                  ;
              leaf local-ip {
                description 'the local IP address of SR adjacency-SID.'
                            ;
                type ncd:ipv4-address ;
              }
              leaf remote-ip {
                description 'The remote IP address of SR adjacency-SID.'
                            ;
                type ncd:ipv4-address ;
              }
              leaf sid {
                description 'The SID value of SR adjacency-SID.'
                            ;
                type int32 {
                  range 16..1048575 ;
                }
                mandatory true ;
              }
            }
            ncd:revise-date 2020-01-15 ;
          }
          container adjacency-intfs {
            description 'The configuration node of SR adjacency-SID-interface u'
                      + 'nnumbered.'
                        ;
            list adjacency-intf {
              description 'The configuration node of SR adjacency-SID-interface'
                        + ' unnumbered.'
                          ;
              key 'local-interface remote-router-id'
                  ;
              leaf local-interface {
                description 'the local interface of SR adjacency-SID.'
                            ;
                type ncd:ifname ;
              }
              leaf remote-router-id {
                description 'The remote router ID SR adjacency-SID.'
                            ;
                type ncd:ipv4-address ;
              }
              leaf sid {
                description 'The SID value of SR adjacency-SID.'
                            ;
                type int32 {
                  range 16..1048575 ;
                }
                mandatory true ;
              }
            }
            ncd:revise-date 2020-01-15 ;
          }
        }
      }
      ncd:revise-date 2019-11-15 ;
    }
    container fas {
      description 'The node for segment-routing Flex-Algorithm.'
                  ;
      list fa {
        description 'The node for segment-routing Flex-Algorithm.'
                    ;
        key fa-id ;
        leaf fa-id {
          description 'The node for segment-routing Flex-Algorithm identifier.'
                      ;
          type uint32 {
            range 128..255 ;
          }
        }
        container ipv4 {
          description 'The node for IPv4 segment-routing.'
                      ;
          container local-prefix-sids {
            description 'The configuration node of local prefix sid.'
                        ;
            list local-prefix-sid {
              description 'The configuration node of local prefix sid.'
                          ;
              key 'dest-addr mask-addr'
                  ;
              leaf dest-addr {
                description 'The destination address of local prefix sid.'
                            ;
                type ncd:ipv4-address ;
              }
              leaf mask-addr {
                description 'The mask address of local prefix sid.'
                            ;
                type ncd:ipv4-address ;
              }
              leaf index {
                description 'The index value of local prefix sid.'
                            ;
                type uint32 {
                  range 0..4294967294 ;
                }
                default 0 ;
              }
              leaf node-flag {
                description 'The node-flag of local prefix sid.'
                            ;
                type LOCAL-PREFIX-NODE-FLAG ;
                default FALSE ;
              }
              leaf php-flag {
                description 'The label operation of penultimate hop.'
                            ;
                type LOCAL-PREFIX-PHP-FLAG ;
                default NULL ;
              }
            }
          }
        }
      }
      ncd:revise-date 2019-11-15 ;
    }
    container interfaces-aiis {
      // if-feature network-slice ;
      description 'The configuration of interface aii.'
                  ;
      list interface-aii {
        description 'The configuration of interface aiis.'
                    ;
        key 'interface-name aii'
            ;
        leaf interface-name {
          description 'The interface name of needing AII.'
                      ;
          type ncd:ifname ;
        }
        leaf aii {
          description 'The configuration of interface AII.'
                      ;
          type uint32 {
            range 1..4294967295 {
              description aii-value ;
            }
          }
        }
      }
      ncd:revise-date 2019-12-21 ;
    }
    container srv6 {
      leaf global-status {
        description 'SRv6 global status configuration.'
                    ;
        type GLOBAL-STATUS ;
        default DISABLE ;
      }
      container sid-range {
        status obsolete {
          ncd:revise-date 2020-06-06 ;
        }
        choice range-type {
          case hybrid {
            description 'Specify the SRv6 SID range is hybrid.'
                        ;
            container hybird {
              leaf hybrid {
                description 'Specify the SRv6 SID range is hybrid.'
                            ;
                type empty ;
                mandatory true ;
              }
              leaf prefix {
                description 'Specify the prefix.'
                            ;
                type ncd:ipv6-address ;
                mandatory true ;
              }
              leaf prefix-length {
                description 'Specify the length of prefix.'
                            ;
                type ncd:ipv6-mask-length {
                  range 8..68 ;
                }
                mandatory true ;
              }
              leaf static-sub-range {
                description 'Specify static sub range type in hybrid mode'
                            ;
                type enumeration {
                  enum RANDOM {
                    value 1 ;
                  }
                }
                mandatory true ;
              }
            }
          }
          case dynamic-only {
            description 'Specify the SRv6 SID range is dynamic only'
                        ;
            container dynamic-ony {
              leaf dynamic-only {
                description 'Specify the SRv6 SID range is dynamic only.'
                            ;
                type empty ;
                mandatory true ;
              }
              leaf dynamic-prefix {
                description 'Specify the prefix.'
                            ;
                type ncd:ipv6-address ;
                mandatory true ;
              }
              leaf dynamic-prefix-length {
                description 'Specify the length of prefix.'
                            ;
                type ncd:ipv6-mask-length {
                  range 8..68 ;
                }
                mandatory true ;
              }
            }
          }
          case static-only {
            description 'Specify the SRv6 SID range is static only.'
                        ;
            container static {
              leaf static-only {
                description 'Specify the SRv6 SID range is static only.'
                            ;
                type empty ;
                mandatory true ;
              }
              leaf static-prefix {
                description 'Specify the prefix.'
                            ;
                type ncd:ipv6-address ;
                mandatory true ;
              }
              leaf static-prefix-length {
                description 'Specify the length of prefix.'
                            ;
                type ncd:ipv6-mask-length {
                  range 8..120 ;
                }
                mandatory true ;
              }
            }
          }
        }
      }
      container locators {
        description 'The configuration of SRv6 locator.'
                    ;
        list locator {
          description 'The configuration of SRv6 locator.'
                      ;
          key locator-name ;
          leaf locator-name {
            description "The locator's name.The max length of locator-name is 3"
                      + "1."
                        ;
            type string {
              length 1..31 ;
            }
          }
          leaf is-default {
            status obsolete {
              ncd:revise-date 2020-07-25 ;
            }
            description "Configure this locator's default attribute.True means "
                      + "configure the locator to default locator,and false mea"
                      + "ns not. There is at most one default locator on a devi"
                      + "ce."
                        ;
            type boolean ;
          }
          container sid-range {
            description 'The configuration of SRv6 locator sid-range.'
                        ;
            presence locator-range ;
            leaf ipv6-prefix {
              description 'Specify the IPv6 prefix of locator.'
                          ;
              type ncd:ipv6-address-none-zero ;
              mandatory true ;
            }
            leaf ipv6-prefix-length {
              description 'Specify the length of prefix.'
                          ;
              type ncd:ipv6-mask-length {
                range 8..120 ;
              }
              mandatory true ;
            }
            leaf static-length {
              description 'Specify the static opcode length of locator.'
                          ;
              type uint8 {
                range 0..120 ;
              }
            }
            leaf args-length {
              description 'Specify the argumments length of locator.'
                          ;
              type uint8 {
                range 16 ;
              }
            }
            container compress {
              description "The configuration of SRv6 locator's compress attribu"
                        + "te."
                          ;
              presence compress ;
              leaf c-target {
                description 'Specify the compress target.'
                            ;
                type enumeration {
                  enum 32 {
                    value 32 ;
                  }
                }
                mandatory true ;
              }
              leaf block-length {
                description 'Specify the block length.'
                            ;
                type uint8 {
                  range 0..96 ;
                }
                mandatory true ;
              }
            }
          }
          leaf fa-id {
            description "The node for SRv6 locator's Flex-Algorithm identifier."
                      + "It's range is 128-255."
                        ;
            type uint32 {
              range 128..255 ;
            }
            ncd:revise-date 2020-09-06 ;
          }
        }
        ncd:revise-date 2020-06-06 ;
      }
      ncd:revise-date 2020-02-16 ;
    }
    container sr-policys {
      description 'The configuration node of SR-policy.'
                  ;
      presence end-point ;
      container ipv4 {
        description 'The ipv4 node of SR-policy.'
                    ;
        container binding-sids {
          list binding-sid {
            description "The configuration of SR-policy's binding-SID."
                        ;
            key 'color end-point-ipv4'
                ;
            leaf color {
              description 'The color of SR-policy.'
                          ;
              type uint32 {
                range 1..4294967295 ;
              }
            }
            leaf end-point-ipv4 {
              description 'Specify the IPv4 address at the end-point end.'
                          ;
              type ncd:ipv4-address-none-zero ;
            }
            choice label {
              description 'Choose the type of assigning binding SID.'+"\n"
                        + 'sid: Specify the SID value.'+"\n"
                        + 'auto: Assign the SID automatically.'
                          ;
              case sid {
                description 'Specify the SID value case.'
                            ;
                leaf sid {
                  description "The SID of SR-policy's binding-SID."
                              ;
                  type uint32 {
                    range 16..1048575 ;
                  }
                  mandatory true ;
                }
              }
              case auto {
                description 'Assign SID automatically case.'
                            ;
                leaf auto {
                  description 'Assign SID automatically.'
                              ;
                  type enumeration {
                    enum auto {
                      value 1 ;
                    }
                  }
                  mandatory true ;
                }
              }
            }
          }
        }
      }
      container ipv6 {
        description 'The ipv6 node of SR-policy.'
                    ;
        container binding-sids {
          list binding-sid {
            description "The configuration of SR-policy's binding-SID."
                        ;
            key 'color end-point-ipv6'
                ;
            leaf color {
              description 'The color of SR-policy.'
                          ;
              type uint32 {
                range 1..4294967295 ;
              }
            }
            leaf end-point-ipv6 {
              description 'Specify the IPv6 address at the end-point end.'
                          ;
              type ncd:ipv6-address-none-zero ;
            }
            choice label {
              description 'Choose the type of assigning binding SID.'+"\n"
                        + 'sid: Specify the SID value.'+"\n"
                        + 'auto: Assign the SID automatically.'
                          ;
              case sid {
                description 'Specify the SID value case.'
                            ;
                leaf sid {
                  description "The SID of SR-policy's binding-SID."
                              ;
                  type uint32 {
                    range 16..1048575 ;
                  }
                  mandatory true ;
                }
              }
              case auto {
                description 'Assign SID automatically case.'
                            ;
                leaf auto {
                  description 'Assign SID automatically.'
                              ;
                  type enumeration {
                    enum auto {
                      value 1 ;
                    }
                  }
                  mandatory true ;
                }
              }
            }
          }
        }
      }
      ncd:revise-date 2020-05-19 ;
    }
    container sr-epes {
      description 'The configuration node of SR EPE.'
                  ;
      container ipv4-peer-sids {
        description "The IPv4 node of SR EPE's peer node."
                    ;
        list ipv4-peer-sid {
          description "The configuration node of SR EPE's IPv4 peer node."
                      ;
          key ipv4-address ;
          leaf ipv4-address {
            description 'The IPv4 address of peer node.'
                        ;
            type ncd:ipv4-address-none-zero ;
          }
          leaf sid {
            description "The SID of SR EPE's peer node."
                        ;
            type uint32 {
              range 16..1048575 ;
            }
          }
        }
      }
      container ipv6-peer-sids {
        description "The IPv6 node of SR EPE's peer node."
                    ;
        list ipv6-peer-sid {
          description "The configuration node of SR EPE's IPv6 peer node."
                      ;
          key ipv6-address ;
          leaf ipv6-address {
            description 'The IPv6 address of peer node.'
                        ;
            type ncd:ipv6-address-none-zero ;
          }
          leaf sid {
            description "The SID of SR EPE's peer node."
                        ;
            type uint32 {
              range 16..1048575 ;
            }
          }
        }
      }
      container peer-set-sids {
        description 'The peer set node of SR EPE.'
                    ;
        list peer-set-sid {
          description "The configuration node of SR EPE's peer set."
                      ;
          key name ;
          leaf name {
            description "The peer set's name.The max length of name is 31."
                        ;
            type ncd:string-all ;
          }
          leaf sid {
            description "The SID of SR EPE's peer set."
                        ;
            type uint32 {
              range 16..1048575 ;
            }
          }
        }
      }
      ncd:revise-date 2020-06-20 ;
    }
    container adj-sid-holdtime {
      description "The configuration node  of SR dynamic adjacency-SID's holdti"
                + "me."
                  ;
      leaf holdtime {
        description "Holdtime in minutes.It's range is 1-10080,and default valu"
                  + "e is 30."
                    ;
        type uint32 {
          range 1..10080 ;
        }
        default 30 ;
      }
      ncd:revise-date 2020-08-18 ;
    }
  }
  container state {
    config false ;
    description 'The query node for segment-routing information.'
                ;
    container ipv4 {
      description 'The query node for IPv4 segment-routing information.'
                  ;
      container global-status {
        description 'The query node for segment-routing global status informati'
                  + 'on.'
                    ;
        leaf status {
          description 'The query node for segment-routing global status informa'
                    + 'tion.'
                      ;
          type GLOBAL-STATUS ;
          default ENABLE ;
        }
      }

      container local-prefix-sid {
        description 'The query node for segment-routing local prefix SID inform'
                  + 'ation.'
                    ;
        list information {
          description 'Segment-routing local prefix SID information.'
                      ;
          key 'dest-addr mask-addr'
              ;
          leaf dest-addr {
            description 'The destination address of local prefix sid.'
                        ;
            type ncd:ipv4-address ;
          }
          leaf mask-addr {
            description 'The mask address of local prefix sid.'
                        ;
            type ncd:ipv4-address ;
          }
          leaf index {
            description 'The index value of local prefix sid.'
                        ;
            type uint32 {
              range 0..4294967295 ;
            }
            default 0 ;
          }
          leaf node-flag {
            description 'The node-flag of local prefix sid.'
                        ;
            type LOCAL-PREFIX-NODE-FLAG ;
            default FALSE ;
          }
          leaf php-flag {
            description 'The label operation of penultimate hop.'
                        ;
            type LOCAL-PREFIX-PHP-FLAG ;
            default NULL ;
          }
          leaf aii {
            // if-feature network-slice ;
            description 'The segment-routing slice identifier.'
                        ;
            type uint32 {
              range 0..4294967295 ;
            }
            default 0 ;
            ncd:revise-date 2019-11-15 ;
          }
          leaf fa-id {
            description 'The node for segment-routing Flex-Algorithm identifier.'
                        ;
            type uint32 {
              range 0..255 ;
            }
            ncd:revise-date 2019-11-15 ;
          }
          ncd:select 'dest-addr mask-addr'
                     ;
          ncd:select aii ;
          ncd:select fa-id ;
          ncd:select 'dest-addr mask-addr aii'
                     ;
          ncd:select 'dest-addr mask-addr fa-id'
                     ;
        }
      }
      container remote-prefix-sid {
        description 'The query node for segment-routing remote prefix SID infor'
                  + 'mation.'
                    ;
        list information {
          description 'Segment-routing remote prefix SID information.'
                      ;
          key 'dest-addr mask-addr nexthop-index'
              ;
          leaf dest-addr {
            description 'The destination address of remote prefix sid.'
                        ;
            type ncd:ipv4-address ;
          }
          leaf mask-addr {
            description 'The mask address of remote prefix sid.'
                        ;
            type ncd:ipv4-address ;
          }
          leaf nexthop-index {
            description 'The index value of nexthop.'
                        ;
            type uint32 {
              range 0..4294967295 ;
            }
          }
          leaf prefix-sid {
            description 'The index value of remote prefix sid.'
                        ;
            type uint32 {
              range 0..4294967295 ;
            }
            default 0 ;
          }
          leaf prefix-flag {
            description 'The flag of remote prefix sid flag.'
                        ;
            type REMOTE-PREFIX-FLAG ;
            default NULL ;
          }
          leaf router-id {
            description 'The router ID.'
                        ;
            type ncd:ipv4-address ;
          }
          leaf nexthop {
            description 'The nexthop address of remote prefix sid.'
                        ;
            type ncd:ipv4-address ;
          }
          leaf nexthop-sid {
            description 'The sid value of nexthop.'
                        ;
            type uint32 {
              range 0..4294967295 ;
            }
            default 0 ;
          }
          leaf nexthop-flag {
            description 'The flag of nexthop sid flag.'
                        ;
            type REMOTE-PREFIX-FLAG ;
            default NULL ;
          }
          leaf aii {
            // if-feature network-slice ;
            description 'The segment-routing slice identifier.'
                        ;
            type uint32 {
              range 0..4294967295 ;
            }
            default 0 ;
            ncd:revise-date 2019-11-15 ;
          }
          leaf fa-id {
            description 'The node for segment-routing Flex-Algorithm identifier.'
                        ;
            type uint32 {
              range 0..255 ;
            }
            default 0 ;
            ncd:revise-date 2019-11-15 ;
          }
          ncd:select 'dest-addr mask-addr'
                     ;
          ncd:select aii ;
          ncd:select fa-id ;
          ncd:select 'dest-addr mask-addr aii'
                     ;
          ncd:select 'dest-addr mask-addr fa-id'
                     ;
        }
      }
      container local-srgb {
        description 'The query node for segment-routing local srgb information.'
                    ;
        leaf label-begin {
          description 'The start label.'
                      ;
          type uint32 {
            range 0..4294967295 ;
          }
          default 0 ;
        }
        leaf label-end {
          description 'The end label.'
                      ;
          type uint32 {
            range 0..4294967295 ;
          }
          default 0 ;
        }
      }
      container remote-srgb {
        status obsolete {
          ncd:revise-date 2018-05-29 ;
        }
        description 'The query node for segment-routing remote srgb information.'
                    ;
        list information {
          status obsolete {
            ncd:revise-date 2018-05-29 ;
          }
          description 'Segment-routing remote srgb information.'
                      ;
          key 'router-id range-index'
              ;
          leaf router-id {
            description 'Router ID'
                        ;
            type ncd:ipv4-address ;
          }
          leaf range-index {
            description 'The range index.'
                        ;
            type uint32 {
              range 0..4294967295 ;
            }
          }
          leaf label-begin {
            description 'The start label.'
                        ;
            type uint32 {
              range 0..4294967295 ;
            }
            default 0 ;
          }
          leaf label-end {
            description 'The end label.'
                        ;
            type uint32 {
              range 0..4294967295 ;
            }
            default 0 ;
          }
        }
      }
      container remote-srgbs {
        description 'The query node for segment-routing remote srgb information.'
                    ;
        list information {
          description 'Segment-routing remote srgb information.'
                      ;
          key 'router-id address-family range-index'
              ;
          leaf router-id {
            description 'Router ID'
                        ;
            type ncd:ipv4-address ;
          }
          leaf address-family {
            description 'Address family.'
                        ;
            type enumeration {
              enum ipv4 {
                value 1 ;
              }
              enum ipv6 {
                value 2 ;
              }
            }
          }
          leaf range-index {
            description 'The range index.'
                        ;
            type uint32 {
              range 0..4294967295 ;
            }
          }
          leaf label-begin {
            description 'The start label.'
                        ;
            type uint32 {
              range 0..4294967295 ;
            }
            default 0 ;
          }
          leaf label-end {
            description 'The end label.'
                        ;
            type uint32 {
              range 0..4294967295 ;
            }
            default 0 ;
          }
        }
        ncd:revise-date 2018-05-29 ;
      }
      container prefix-sid-map {
        // if-feature mapping-server ;
        description 'The query node for segment-routing mapping-server ipv4 pre'
                  + 'fix-sid-map information.'
                    ;
        list information {
          description 'Segment-routing mapping-server ipv4 prefix-sid-map infor'
                    + 'mation.'
                      ;
          key 'first-dest-addr first-mask-addr'
              ;
          leaf first-dest-addr {
            description 'The destination address of the first prefix sid.'
                        ;
            type ncd:ipv4-address ;
          }
          leaf first-mask-addr {
            description 'The mask address of the first prefix sid.'
                        ;
            type ncd:ipv4-address ;
          }
          leaf first-sid {
            description 'The sid value of the first prefix sid.'
                        ;
            type uint32 {
              range 0..4294967295 ;
            }
            default 0 ;
          }
          leaf range {
            description 'The quantity of maps of prefix and sid.'
                        ;
            type uint32 ;
            default 0 ;
          }
          leaf last-dest-addr {
            description 'The destination address of the last prefix sid.'
                        ;
            type ncd:ipv4-address ;
          }
          leaf last-mask-addr {
            description 'The mask address of the last prefix sid.'
                        ;
            type ncd:ipv4-address ;
          }
          leaf last-sid {
            description 'The sid value of the last prefix sid.'
                        ;
            type uint32 {
              range 0..4294967295 ;
            }
            default 0 ;
          }
        }
        ncd:revise-date 2018-09-19 ;
      }
      container adjacency-sid-new {
        status obsolete {
          ncd:revise-date 2020-04-18 ;
        }
        description 'The query node for segment-routing adjacency SID informati'
                  + 'on.'
                    ;
        list information {
          description 'Segment-routing adjacency SID information.'
                      ;
          key 'type local-router-id local-ip remote-router-id remote-ip sid-ind'
            + 'ex local-id remote-id'
              ;
          leaf type {
            description 'The type of adjacency SID.'
                        ;
            type ADJ-TYPE ;
          }
          leaf local-router-id {
            description 'The local router ID.'
                        ;
            type ncd:ipv4-address ;
          }
          leaf local-ip {
            description 'The local IP address.'
                        ;
            type ncd:ipv4-address ;
          }
          leaf remote-router-id {
            description 'The remote router ID.'
                        ;
            type ncd:ipv4-address ;
          }
          leaf remote-ip {
            description 'The remote IP address.'
                        ;
            type ncd:ipv4-address ;
          }
          leaf sid-index {
            description 'The SID index in IP-pair.'
                        ;
            type uint32 {
              range 0..4294967295 ;
            }
          }
          leaf sid-label {
            description 'The label of adjacency SID.'
                        ;
            type uint32 {
              range 0..4294967295 ;
            }
          }
          leaf weight {
            description 'The weight of adjacency SID.'
                        ;
            type uint32 {
              range 0..4294967295 ;
            }
          }
          leaf local-id {
            description 'The local ID.'
                        ;
            type uint32 ;
          }
          leaf remote-id {
            description 'The remote ID.'
                        ;
            type int32 ;
          }
          leaf local-interface {
            description 'The local interface.'
                        ;
            type ncd:string-all ;
          }
          leaf aii {
            // if-feature network-slice ;
            description 'The segment-routing slice identifier.'
                        ;
            type uint32 {
              range 0..4294967295 ;
            }
            default 0 ;
            ncd:revise-date 2020-01-15 ;
          }
          ncd:select type ;
          ncd:select 'type local-router-id local-ip remote-router-id remote-ip'
                     ;
          ncd:select 'type local-router-id remote-router-id local-id remote-id'
                     ;
          ncd:select 'type aii'
                     ;
          ncd:select 'type local-router-id local-ip remote-router-id remote-ip '
                   + 'aii'
                     ;
          ncd:select 'type local-router-id remote-router-id local-id remote-id '
                   + 'aii'
                     ;
        }
        ncd:revise-date 2019-09-07 ;
      }
    }
    container ipv6 {
      description 'The query node for IPv6 segment-routing information.'
                  ;
      container global-status {
        description 'The query node for segment-routing global status informati'
                  + 'on.'
                    ;
        leaf status {
          description 'The query node for segment-routing global status informa'
                    + 'tion.'
                      ;
          type GLOBAL-STATUS ;
          default ENABLE ;
        }
      }
      container local-prefix-sid {
        description 'The query node for segment-routing local prefix SID inform'
                  + 'ation.'
                    ;
        list information {
          description 'Segment-routing local prefix SID information.'
                      ;
          key 'prefix prefix-length'
              ;
          leaf prefix {
            description 'The destination address of local prefix sid.'
                        ;
            type ncd:ipv6-address ;
          }
          leaf prefix-length {
            description 'The prefix length of local prefix sid.'
                        ;
            type uint8 {
              range 0..128 ;
            }
          }
          leaf index {
            description 'The index value of local prefix sid.'
                        ;
            type uint32 {
              range 0..4294967295 ;
            }
            default 0 ;
          }
          leaf node-flag {
            description 'The node-flag of local prefix sid.'
                        ;
            type LOCAL-PREFIX-NODE-FLAG ;
            default FALSE ;
          }
          leaf php-flag {
            description 'The label operation of penultimate hop.'
                        ;
            type LOCAL-PREFIX-PHP-FLAG ;
            default NULL ;
          }
          ncd:select 'prefix prefix-length'
                     ;
        }
      }
      container remote-prefix-sid {
        description 'The query node for segment-routing remote prefix SID infor'
                  + 'mation.'
                    ;
        list information {
          description 'Segment-routing remote prefix SID information.'
                      ;
          key 'prefix prefix-length nexthop-index'
              ;
          leaf prefix {
            description 'The destination address of remote prefix sid.'
                        ;
            type ncd:ipv6-address ;
          }
          leaf prefix-length {
            description 'The prefix length of remote prefix sid.'
                        ;
            type uint8 {
              range 0..128 ;
            }
          }
          leaf nexthop-index {
            description 'The index value of nexthop.'
                        ;
            type uint32 {
              range 0..4294967295 ;
            }
          }
          leaf prefix-sid {
            description 'The index value of remote prefix sid.'
                        ;
            type uint32 {
              range 0..4294967295 ;
            }
            default 0 ;
          }
          leaf prefix-flag {
            description 'The flag of remote prefix sid flag.'
                        ;
            type REMOTE-PREFIX-FLAG ;
            default NULL ;
          }
          leaf router-id {
            status obsolete {
              ncd:revise-date 2019-05-31 ;
            }
            description 'The router ID.'
                        ;
            type ncd:ipv4-address ;
          }
          leaf nexthop {
            description 'The nexthop address of remote prefix sid.'
                        ;
            type ncd:ipv6-address ;
          }
          leaf nexthop-sid {
            description 'The sid value of nexthop.'
                        ;
            type uint32 {
              range 0..4294967295 ;
            }
            default 0 ;
          }
          leaf nexthop-flag {
            description 'The flag of nexthop sid flag.'
                        ;
            type REMOTE-PREFIX-FLAG ;
            default NULL ;
          }
          leaf router-id-str {
            description 'The router ID.'
                        ;
            type string ;
            ncd:revise-date 2019-05-31 ;
          }
          ncd:select 'prefix prefix-length'
                     ;
        }
      }
      container prefix-sid-map {
        // if-feature mapping-server ;
        description 'The query node for segment-routing mapping-server ipv6 pre'
                  + 'fix-sid-map information.'
                    ;
        list information {
          description 'Segment-routing mapping-server ipv6 prefix-sid-map infor'
                    + 'mation.'
                      ;
          key 'first-prefix first-prefix-len'
              ;
          leaf first-prefix {
            description 'The destination address of the first prefix sid.'
                        ;
            type ncd:ipv6-address ;
          }
          leaf first-prefix-len {
            description 'The prefix length of the first prefix sid.'
                        ;
            type uint8 {
              range 1..128 ;
            }
          }
          leaf first-sid {
            description 'The sid value of the first prefix sid.'
                        ;
            type uint32 {
              range 0..4294967295 ;
            }
            default 0 ;
          }
          leaf range {
            description 'The quantity of maps of prefix and sid.'
                        ;
            type uint32 {
              range 1..65535 ;
            }
          }
          leaf last-prefix {
            description 'The destination address of the last prefix sid.'
                        ;
            type ncd:ipv6-address ;
          }
          leaf last-prefix-len {
            description 'The prefix length of the last prefix sid.'
                        ;
            type uint8 {
              range 1..128 ;
            }
          }
          leaf last-sid {
            description 'The sid value of the last prefix sid.'
                        ;
            type uint32 {
              range 0..4294967295 ;
            }
            default 0 ;
          }
        }
        ncd:revise-date 2018-09-19 ;
      }

      container adjacency-sid-new {
        status obsolete {
          ncd:revise-date 2020-04-18 ;
        }
        description 'The query node for ipv6 segment-routing adjacency SID info'
                  + 'rmation.'
                    ;
        list information {
          description 'Segment-routing adjacency SID information.'
                      ;
          key 'type local-router-id local-ipv6 remote-router-id remote-ipv6 sid'
            + '-index local-id remote-id'
              ;
          leaf type {
            description 'The type of adjacency SID.'
                        ;
            type ADJ-TYPE ;
          }
          leaf local-router-id {
            description 'The local router ID.'
                        ;
            type ncd:ipv6-address ;
          }
          leaf local-ipv6 {
            description 'The local IPv6 address.'
                        ;
            type ncd:ipv6-address ;
          }
          leaf remote-router-id {
            description 'The remote router ID.'
                        ;
            type ncd:ipv6-address ;
          }
          leaf remote-ipv6 {
            description 'The remote IPv6 address.'
                        ;
            type ncd:ipv6-address ;
          }
          leaf sid-index {
            description 'The SID index in IP-pair.'
                        ;
            type uint32 {
              range 0..4294967295 ;
            }
          }
          leaf sid-label {
            description 'The label of adjacency SID.'
                        ;
            type uint32 {
              range 0..4294967295 ;
            }
          }
          leaf weight {
            description 'The weight of adjacency SID.'
                        ;
            type uint32 {
              range 0..4294967295 ;
            }
          }
          leaf local-id {
            description 'The local ID.'
                        ;
            type uint32 ;
          }
          leaf remote-id {
            description 'The remote ID.'
                        ;
            type int32 ;
          }
          leaf local-interface {
            description 'The local interface.'
                        ;
            type ncd:string-all ;
          }
          ncd:select type ;
          ncd:select 'type local-router-id local-ipv6 remote-router-id remote-i'
                   + 'pv6'
                     ;
          ncd:select 'type local-router-id remote-router-id local-id remote-id'
                     ;
        }
        ncd:revise-date 2019-09-07 ;
      }
      ncd:revise-date 2017-08-21 ;
    }
    container srv6 {
      leaf global-status {
        description 'Show the SRv6 global switch status.'
                    ;
        type GLOBAL-STATUS ;
      }
      container srv6-sids {
        status obsolete {
          ncd:revise-date 2020-09-22 ;
        }
        description 'The SRv6 SID information.'
                    ;
        list srv6-sid {
          key type ;
          leaf type {
            description 'The type of SRv6 SID (local or remote).'
                        ;
            type enumeration {
              enum local {
                value 1 ;
              }
              enum remote {
                value 2 ;
              }
            }
          }
          leaf sid-prefix {
            description 'The prefix of SID.'
                        ;
            type ncd:ipv6-prefix ;
          }
          leaf sid-length {
            description 'The prefix length of SID.'
                        ;
            type ncd:ipv6-mask-length ;
          }
          leaf function-type {
            description 'Function type of SID.'
                        ;
            type string ;
          }
          leaf flavor {
            description 'Flavor of SID.'
                        ;
            type string ;
          }
          leaf nexthop {
            description 'Nexthop address.'
                        ;
            type ncd:ipv6-address ;
          }
          leaf interface {
            description 'Output interface.'
                        ;
            type string ;
          }
        }
      }
      container srv6-sid-range {
        status obsolete {
          ncd:revise-date 2020-06-06 ;
        }
        description 'The SRv6 SID range information.'
                    ;
        list sid-range {
          key type ;
          leaf type {
            description 'The type of SID range.'
                        ;
            type string ;
          }
          leaf range-prefix {
            description 'The SID range.'
                        ;
            type ncd:ipv6-prefix ;
          }
        }
      }
      container locators {
        description 'The SRv6 locator information.'
                    ;
        list locator {
          description 'The SRv6 locator information.'
                      ;
          key locator-name ;
          leaf locator-name {
            description "The locator's name.The max length of locator-name is 3"
                      + "1."
                        ;
            type string ;
          }
          leaf range-prefix {
            description 'The locator SID range.'
                        ;
            type ncd:ipv6-prefix ;
          }
          leaf is-default {
            status obsolete {
              ncd:revise-date 2020-07-25 ;
            }
            description "The locator's default attribute."
                        ;
            type boolean ;
          }
          leaf static-length {
            description "The locator's static opcode length."
                        ;
            type uint8 ;
          }
          leaf auto-sid-begin {
            description "The begin of the locator's auto SID range."
                        ;
            type string ;
          }
          leaf auto-sid-end {
            description "The end of the locator's auto SID range."
                        ;
            type string ;
          }
          leaf args-length {
            description "The locator's arguments opcode length."
                        ;
            type uint8 ;
          }
          leaf compress-target {
            description "The locator's compress target."
                        ;
            type uint8 ;
          }
          leaf block-length {
            description "The locator's block length."
                        ;
            type uint8 ;
          }
          leaf node-length {
            description "The locator's node length."
                        ;
            type uint8 ;
          }
          leaf function-length {
            description "The locator's function length."
                        ;
            type uint8 ;
          }
          leaf fa-id {
            description "The node for SRv6 locator's Flex-Algorithm identifier."
                        ;
            type uint32 ;
            ncd:revise-date 2020-09-06 ;
          }
        }
        ncd:revise-date 2020-06-06 ;
      }
      container local-sids {
        description 'The SRv6 local SID information.'
                    ;
        list local-sid {
          description 'The SRv6 local SID information.'
                      ;
          key sid ;
          leaf sid {
            description 'The SRv6 local SID.'
                        ;
            type ncd:ipv6-prefix ;
          }
          leaf locator-name {
            description 'The locator name of SID.'
                        ;
            type string ;
          }
          leaf vrf-name {
            description 'The vrf name of SID.'
                        ;
            type string ;
          }
          leaf function-type {
            description 'Function type of SID.'
                        ;
            type SRV6-LOCAL-SID-FUNCTYPE ;
          }
          leaf owner {
            description 'Owner of SID.'
                        ;
            type string ;
          }
          leaf block-length {
            description "The SID's block length."
                        ;
            type uint8 ;
          }
          leaf node-length {
            description "The SID's node length."
                        ;
            type uint8 ;
          }
          leaf function-length {
            description "The SID's function length."
                        ;
            type uint8 ;
          }
          leaf flavor {
            description 'Flavor of SID.'
                        ;
            type string ;
          }
          leaf nexthop {
            description 'Nexthop address.'
                        ;
            type string ;
          }
          leaf out-interface {
            description 'Output interface.'
                        ;
            type string ;
          }
          leaf color {
            description "The SID's color."
                        ;
            type uint32 ;
          }
          leaf end-point {
            description "SID's end-point."
                        ;
            type string ;
          }
          leaf vpls-name {
            description 'The VPLS name of SID.'
                        ;
            type string ;
            ncd:revise-date 2020-10-29 ;
          }
          leaf fa-id {
            description "The node for SRv6 local SID's Flex-Algorithm identifie"
                      + "r."
                        ;
            type uint8 ;
            ncd:revise-date 2020-10-29 ;
          }
          ncd:select locator-name ;
          ncd:select function-type ;
          ncd:select sid ;
        }
        ncd:revise-date 2020-09-22 ;
      }
      container local-sid-summary {
        description 'The querying of SRv6 local SID statistics.'
                    ;
        leaf total {
          description 'The total of all SRv6 local SID.'
                      ;
          type uint32 ;
        }
        list statistics {
          description 'The querying of SRv6 local SID statistics by function ty'
                    + 'pe.'
                      ;
          key function-type ;
          leaf function-type {
            description 'The function type of SRv6 local SID.'
                        ;
            type SRV6-LOCAL-SID-FUNCTYPE ;
          }
          leaf count {
            description 'The statistics of SRv6 local SID in special function t'
                      + 'ype.'
                        ;
            type uint32 ;
          }
        }
        ncd:revise-date 2020-09-22 ;
      }
      ncd:revise-date 2020-02-16 ;
    }
  }
}
