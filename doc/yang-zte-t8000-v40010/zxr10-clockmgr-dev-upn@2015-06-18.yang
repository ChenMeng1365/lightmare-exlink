module zxr10-clockmgr-dev-upn {
  namespace 'http://www.zte.com.cn/zxr10/netconf/schema/rosng/clockmgr-dev-upn'
            ;
  prefix clockmgr-dev-upn ;
  import zxr10-clockmgr {
    prefix clockmgr ;
    revision-date 2015-04-01 ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2015-06-18 {
    description 'Initial version.'
                ;
  }
  deviation '/clockmgr:configuration/clockmgr:clock/clockmgr:summer-time/clockm'
          + 'gr:offset-sign'
            {
    deviate not-supported ;
  }
}
