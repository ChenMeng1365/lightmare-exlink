module zxr10-bfd {
  namespace 'http://www.zte.com.cn/zxr10/netconf/schema/rosng/bfd'
            ;
  prefix bfd ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe BFD. BFD is designed to detect fa'
            + 'ilures in communication with a forwarding plane next hop. It is '
            + 'intended to be implemented in some component of the forwarding e'
            + 'ngine of a system, in cases where the forwarding and control eng'
            + 'ines are separated.'
              ;
  revision 2020-11-17 {
    description '1)Add emu value:/bfd:state/bfd:bfd/bfd:global/bfd:statistic/bf'
              + 'd:show-detect-type:Srv6EvpnVpws;'+"\n"
              + '2)Add emu value:/bfd:state/bfd:bfd/bfd:session-results/bfd:ses'
              + 'sion-result/bfd:bfd-detect-type:Srv6EvpnVpws;'+"\n"
              + '3)Add emu value:/bfd:state/bfd:bfd/bfd:session-results/bfd:ses'
              + 'sion-result/bfd:summary-detect-type:Srv6EvpnVpws;'+"\n"
              + '4)Add emu value:/bfd:notification-bfd-sessions/bfd:bfd-session'
              + 's/bfd:bfd-session/bfd:detect-type:Srv6EvpnVpws.'
                ;
  }
  revision 2020-10-14 {
    description '1)add ipv6-source leaf in configuraion/bfd/auto-sessions/sr-be'
              + '-sbfd/sessions'+"\n"
              + '2)add SRv6 type in configuraion/bfd/auto-sessions/sr-be-sbfd/s'
              + 'essions/bfd-type'
                ;
  }
  revision 2020-09-30 {
    description '1)Add leaf:configuration/bfd/seamless-sessions/session/detect-'
              + 'type/srv6-be-bfd/mask-length'
                ;
  }
  revision 2020-09-15 {
    description '1) Add leaf:/configuration/bfd/template-paras/dscp.'
                ;
  }
  revision 2020-08-28 {
    description '1)Set leaf /bfd:configuration/bfd:bfd/bfd:seamless-sessions/bf'
              + 'd:session/bfd:rsvp-bfd/bfd:rd range from 1 to 4294967295'+"\n"
              + '2)Set leaf /bfd:configuration/bfd:bfd/bfd:seamless-sessions/bf'
              + 'd:session/bfd:v4-sr-be-bfd/bfd:rd range from 1 to 4294967295'+"\n"
              + '3)Set leaf /bfd:configuration/bfd:bfd/bfd:seamless-sessions/bf'
              + 'd:session/bfd:srv6-te-bfd/bfd:rd range from 1 to 4294967295'+"\n"
              + '4)Set leaf /bfd:configuration/bfd:bfd/bfd:seamless-sessions/bf'
              + 'd:session/bfd:v4-gen-lsp-bfd/bfd:rd range from 1 to 4294967295'
                ;
  }
  revision 2020-08-26 {
    description '1) Add containter /bfd:configuration/bfd:bfd/bfd:sessions/bfd:'
              + 'session/bfd:session-description;'+"\n"
              + '2) Add leaf  /bfd:configuration/bfd:bfd/bfd:sessions/bfd:sessi'
              + 'on/bfd:session-description/bfd:description;'+"\n"
              + '3) Add containter /bfd:configuration/bfd:bfd/bfd:seamless-sess'
              + 'ions/bfd:session/bfd:session-description;'+"\n"
              + '4) Add leaf  /bfd:configuration/bfd:bfd/bfd:seamless-sessions/'
              + 'bfd:session/bfd:session-description/bfd:description;'+"\n"
              + '5) Add containter  /bfd:configuration/bfd:bfd/bfd:interface-pa'
              + 'ras/bfd:interface-para/bfd:interface-description;'+"\n"
              + '6) Add leaf /bfd:configuration/bfd:bfd/bfd:interface-paras/bfd'
              + ':interface-para/bfd:interface-description/bfd::description;'
                ;
  }
  revision 2020-08-08 {
    description '1)Add emu value:/bfd:state/bfd:bfd/bfd:global/bfd:statistic/bf'
              + 'd:show-detect-type:Srv6Be;'+"\n"
              + '2)Add emu value:/bfd:state/bfd:bfd/bfd:session-results/bfd:ses'
              + 'sion-result/bfd:bfd-detect-type:Srv6Be;'+"\n"
              + '3)Add emu value:/bfd:state/bfd:bfd/bfd:session-results/bfd:ses'
              + 'sion-result/bfd:summary-detect-type:Srv6Be;'+"\n"
              + '4)Add emu value:/bfd:notification-bfd-sessions/bfd:bfd-session'
              + 's/bfd:bfd-session/bfd:detect-type:Srv6Be.'+"\n"
              + '5)Add case:configuration/bfd/seamless-sessions/session/detect-'
              + 'type/srv6-be-bfd;'+"\n"
              + '6)Add feature:srv6-be;'+"\n"
              + '7)Modify description :/bfd:state/bfd:bfd/bfd:session-results/b'
              + 'fd:session-result/bfd:local-address;'+"\n"
              + '8)Modify description :/bfd:state/bfd:bfd/bfd:session-results/b'
              + 'fd:session-result/bfd:remote-address;'+"\n"
              + '9)Modify description :/bfd:state/bfd:bfd/bfd:session-results/b'
              + 'fd:session-result/bfd:fec-address.'
                ;
  }
  revision 2020-07-23 {
    description '1) Add extend-max-ld-set configuration in configuration/bfd/gl'
              + 'obal'
                ;
  }
  revision 2020-07-21 {
    description '1)Add emu value:/bfd:state/bfd:bfd/bfd:global/bfd:statistic/bf'
              + 'd:show-detect-type:SrMplsPolicySL;'+"\n"
              + '2)Add emu value:/bfd:state/bfd:bfd/bfd:session-results/bfd:ses'
              + 'sion-result/bfd:bfd-detect-type:SrMplsPolicySL;'+"\n"
              + '3)Add emu value:/bfd:state/bfd:bfd/bfd:session-results/bfd:ses'
              + 'sion-result/bfd:summary-detect-type:SrMplsPolicySL;'+"\n"
              + '4)Add emu value:/bfd:notification-bfd-sessions/bfd:bfd-session'
              + 's/bfd:bfd-session/bfd:detect-type:SrMplsPolicySL.'
                ;
  }
  revision 2020-07-11 {
    description '1) Change the "Status" of leaf /bfd:state/bfd:bfd/bfd:session-'
              + 'results/bfd:session-result/bfd:fec-address;'+"\n"
              + '2) Add leaf /bfd:configuration/bfd:bfd/bfd:sessions/bfd:sessio'
              + 'n/bfd:detect-type/bfd:pw-bfd/bfd:pw-bfd/bfd:ld;'+"\n"
              + '3) Add leaf /bfd:configuration/bfd:bfd/bfd:sessions/bfd:sessio'
              + 'n/bfd:detect-type/bfd:pw-bfd/bfd:pw-bfd/bfd:rd;'+"\n"
              + '4) Add leaf /bfd:configuration/bfd:bfd/bfd:template-paras/bfd:'
              + 'template-para/bfd:min-echo-rx-interval.'
                ;
  }
  revision 2020-07-07 {
    description '1) Add a node named "v4-gen-lsp-bfd" under /configuration/bfd/'
              + 'sessions/session/detect-type;'+"\n"
              + '2) Add a node named "v4-gen-lsp-bfd" under /configuration/bfd/'
              + 'seamless-sessions/session/detect-type;'+"\n"
              + '3) Add a type named "GEN-LSP-Active" under /state/bfd/global/s'
              + 'tatistic/show-detect-type;'+"\n"
              + '4) Add a type named "GEN-LSP-Passive" under /state/bfd/global/'
              + 'statistic/show-detect-type;'+"\n"
              + '5) Add a type named "GEN-LSP-Active" under /state/bfd/session-'
              + 'results/session-result/bfd-detect-type;'+"\n"
              + '6) Add a type named "GEN-LSP-Passive" under /state/bfd/session'
              + '-results/session-result/bfd-detect-type;'+"\n"
              + '7) Add a type named "GEN-LSP" under /state/bfd/session-results'
              + '/session-result/summary-detect-type;'+"\n"
              + '8) Add a type named "GEN-LSP-Active" under /notification-bfd-s'
              + 'essions/bfd-sessions/bfd-session/detect-type;'+"\n"
              + '9) Add a type named "GEN-LSP-Passive" under /notification-bfd-'
              + 'sessions/bfd-sessions/bfd-session/detect-type.'
                ;
  }
  revision 2020-07-02 {
    description '1)Add emu value:/bfd:state/bfd:bfd/bfd:global/bfd:statistic/bf'
              + 'd:show-detect-type;'+"\n"
              + '2)Add emu value:/bfd:state/bfd:bfd/bfd:session-results/bfd:ses'
              + 'sion-result/bfd:bfd-detect-type;'+"\n"
              + '3)Add emu value:/bfd:state/bfd:bfd/bfd:session-results/bfd:ses'
              + 'sion-result/bfd:summary-detect-type;'+"\n"
              + '4)Add emu value:/bfd:notification-bfd-sessions/bfd:bfd-session'
              + 's/bfd:bfd-session/bfd:detect-type.'+"\n"
              + '5)Add leaf:state/bfd/session-results/session-result/sub-domain'
              + '-id.'+"\n"
              + '6)Add leaf:state/bfd/session-results/session-result/bfr-id.'+"\n"
              + '7)Add leaf:state/bfd/session-results/session-result/mpls-label'
              + '.'+"\n"
              + '8)Add leaf:notification-bfd-sessions/bfd-sessions/bfd-session/'
              + 'sub-domain-id.'+"\n"
              + '9)Add leaf:notification-bfd-sessions/bfd-sessions/bfd-session/'
              + 'bfr-id.'+"\n"
              + '10)Add leaf:notification-bfd-sessions/bfd-sessions/bfd-session'
              + '/mpls-label.'
                ;
  }
  revision 2020-07-01 {
    description '1) Add mode configuration in configuration/bfd/global'
                ;
  }
  revision 2020-06-19 {
    description '1)Change emu range of /bfd:configuration/bfd:bfd/bfd:auto-sess'
              + 'ions/bfd:sr-be-sbfd/bfd:sessions:ip-prefix-name.'
                ;
  }
  revision 2020-06-03 {
    description '1)Add emu value:/bfd:state/bfd:bfd/bfd:global/bfd:statistic/bf'
              + 'd:show-detect-type;'+"\n"
              + '2)Add emu value:/bfd:state/bfd:bfd/bfd:session-results/bfd:ses'
              + 'sion-result/bfd:bfd-detect-type;'+"\n"
              + '3)Add emu value:/bfd:state/bfd:bfd/bfd:session-results/bfd:ses'
              + 'sion-result/bfd:summary-detect-type;'+"\n"
              + '4)Add emu value:/bfd:notification-bfd-sessions/bfd:bfd-session'
              + 's/bfd:bfd-session/bfd:detect-type.'+"\n"
              + '5)Change emu name of /bfd:state/bfd:bfd/bfd:global/bfd:statist'
              + 'ic/bfd:show-detect-type:SrMplsPolicy;'+"\n"
              + '6)Change emu name of /bfd:state/bfd:bfd/bfd:session-results/bf'
              + 'd:session-result/bfd:bfd-detect-type:SrMplsPolicy;'+"\n"
              + '7)Change emu name of /bfd:state/bfd:bfd/bfd:session-results/bf'
              + 'd:session-result/bfd:summary-detect-type:SrMplsPolicy;'+"\n"
              + '8)Change emu name of /bfd:notification-bfd-sessions/bfd:bfd-se'
              + 'ssions/bfd:bfd-session/bfd:detect-type:SrMplsPolicy.'
                ;
  }
  revision 2020-05-22 {
    description '1)Add emu value:/bfd:state/bfd:bfd/bfd:global/bfd:statistic/bf'
              + 'd:show-detect-type;'+"\n"
              + '2)Add emu value:/bfd:state/bfd:bfd/bfd:session-results/bfd:ses'
              + 'sion-result/bfd:bfd-detect-type;'+"\n"
              + '3)Add emu value:/bfd:state/bfd:bfd/bfd:session-results/bfd:ses'
              + 'sion-result/bfd:summary-detect-type;'+"\n"
              + '4)Add emu value:/bfd:notification-bfd-sessions/bfd:bfd-session'
              + 's/bfd:bfd-session/bfd:detect-type.'
                ;
  }
  revision 2020-05-20 {
    description 'Add new leaf /bfd:configuration/bfd:bfd/bfd:auto-sessions/bfd:'
              + 'sr-be-sbfd/bfd:sessions/bfd:source'
                ;
  }
  revision 2020-05-15 {
    description '1)Change one leaf(/bfd:configuration/bfd:bfd/bfd:sessions/bfd:'
              + 'session/bfd:detect-type/bfd:v4-link-bfd/bfd:v4-link-bfd/bfd:vr'
              + 'f-name) to two leafs(/bfd:configuration/bfd:bfd/bfd:sessions/b'
              + 'fd:session/bfd:detect-type/bfd:v4-link-bfd/bfd:v4-link-bfd/bfd'
              + ':vrf/bfd:vrf-name/bfd:vrf-name and /bfd:configuration/bfd:bfd/'
              + 'bfd:sessions/bfd:session/bfd:detect-type/bfd:v4-link-bfd/bfd:v'
              + '4-link-bfd/bfd:vrf/bfd:dcn/bfd:dcn),these two leafs are in "ch'
              + 'oice".'+"\n"
              + '2)Change one leaf(/bfd:configuration/bfd:bfd/bfd:sessions/bfd:'
              + 'session/bfd:detect-type/bfd:v6-link-bfd/bfd:v6-link-bfd/bfd:vr'
              + 'f-name) to two leafs(/bfd:configuration/bfd:bfd/bfd:sessions/b'
              + 'fd:session/bfd:detect-type/bfd:v6-link-bfd/bfd:v6-link-bfd/bfd'
              + ':vrf/bfd:vrf-name/bfd:vrf-name and /bfd:configuration/bfd:bfd/'
              + 'bfd:sessions/bfd:session/bfd:detect-type/bfd:v6-link-bfd/bfd:v'
              + '6-link-bfd/bfd:vrf/bfd:dcn/bfd:dcn),these two leafs are in "ch'
              + 'oice".'+"\n"
              + '3)Add feature of dcn.'
                ;
  }
  revision 2020-04-20 {
    description '1)Add case:/configuration/seamless-sessions/session/detect-tpy'
              + 'e/srv6-te-bfd,and all nodes under it.'+"\n"
              + '2)Add container:/configuration/bfd/seamless-paras/remote-targe'
              + 't/ipv6-remote-targets,and all nodes under it.'+"\n"
              + '3)Add leaf:/configuration/bfd/seamless-paras/reflector-source-'
              + 'ipv6.'
                ;
  }
  revision 2020-03-24 {
    description '1)Add container:/configuration/auto-sessions'+"\n"
              + '2)Add container:/configuration/auto-sessions/sr-be-sbfd'+"\n"
              + '3)Add      list:/configuration/auto-sessions/sbfd/sr-be-sbfd/s'
              + 'essions'+"\n"
              + '4)Add      leaf:/configuration/auto-sessions/sbfd/sr-be-sbfd/s'
              + 'essions/bfd-type'+"\n"
              + '5)Add      leaf:/configuration/auto-sessions/sbfd/sr-be-sbfd/s'
              + 'essions/ip-prefix-name'+"\n"
              + '6)Add      leaf:/configuration/auto-sessions/sbfd/sr-be-sbfd/s'
              + 'essions/template-name'
                ;
  }
  revision 2020-02-20 {
    description '1)Add typedef:policy-set'+"\n"
              + '2)Add feature:location-board'+"\n"
              + '3)Add feature:template-for-session'+"\n"
              + '4)Add container:/configuration/bfd/global/board-paras'+"\n"
              + '4.1)Add leaf:/configuration/bfd/global/board-paras/policy   '+"\n"
              + '4.2)Add list:/configuration/bfd/global/board-paras/board'+"\n"
              + '4.3)Add leaf:/configuration/bfd/global/board-paras/board/name '
              + '     '+"\n"
              + '5.1)Add leaf:/configuration/bfd/sessions/session/v4-link-bfd/t'
              + 'emplate-name'+"\n"
              + '6)Add leaf:/configuration/bfd/sessions/session/v6-link-bfd/tem'
              + 'plate-name'+"\n"
              + '7)Add leaf:/configuration/bfd/sessions/session/v4-peer-bfd/tem'
              + 'plate-name'+"\n"
              + '8)Add leaf:/configuration/bfd/sessions/session/v6-peer-bfd/tem'
              + 'plate-name'+"\n"
              + '9)Add leaf:/configuration/bfd/sessions/session/ldp-bfd/templat'
              + 'e-name'+"\n"
              + '10)Add leaf:/configuration/bfd/sessions/session/v6-ldp-bfd/tem'
              + 'plate-name'+"\n"
              + '11)Add leaf:/configuration/bfd/sessions/session/rsvp-bfd/templ'
              + 'ate-name'+"\n"
              + '12)Add leaf:/configuration/bfd/sessions/session/pw-bfd/templat'
              + 'e-name'+"\n"
              + '13)Add leaf:/configuration/bfd/sessions/session/v4-sr-be-bfd/t'
              + 'emplate-name'+"\n"
              + '14)Add leaf:/configuration/bfd/seamless-sessions/session/rsvp-'
              + 'bfd/template-name'+"\n"
              + '15)Add leaf:/configuration/bfd/seamless-sessions/session/v4-sr'
              + '-be-bfd/template-name   '+"\n"
              + '16)Add leaf:/configuration/bfd/template-paras/template-para/lo'
              + 'cation-policy'+"\n"
              + '17)Add container:/configuration/bfd/template-paras/template-pa'
              + 'ra/location-board'+"\n"
              + '17.1)Add    list:/configuration/bfd/template-paras/template-pa'
              + 'ra/location-board/board'+"\n"
              + '17.2)Add    leaf:/configuration/bfd/template-paras/template-pa'
              + 'ra/location-board/board/name'+"\n"
              + '17.3)Add    leaf:/configuration/bfd/template-paras/template-pa'
              + 'ra/location-board/board/secondary'+"\n"
              + '18)Add leaf:/state/bfd/session-results/session-result/template'
              + '-name'+"\n"
              + '19)Add leaf:/state/bfd/session-results/session-result/working-'
              + 'board'+"\n"
              + '20)Add leaf:/state/bfd/session-results/session-result/standby-'
              + 'board'
                ;
  }
  revision 2019-11-21 {
    description '1)Add container:configuration/bfd/template-paras'+"\n"
              + '2)Add leaf:state/bfd/session-results/session-result/path-id'+"\n"
              + '3)Add leaf:notification-bfd-sessions/bfd-sessions/bfd-session/'
              + 'path-id'+"\n"
              + '4)Add types for state/bfd/session-results/session-result/bfd-d'
              + 'etect-type'+"\n"
              + '5)Add types for state/bfd/global/statistic/show-detect-type'+"\n"
              + '6)Add types for state/bfd/session-results/session-result/summa'
              + 'ry-detect-type'+"\n"
              + '7)Add types for notification-bfd-sessions/bfd-sessions/bfd-ses'
              + 'sion/detect-type'+"\n"
              + '8)Add select for state/bfd/session-results/session-result'
                ;
  }
  revision 2019-10-24 {
    description '1)Add types for notification-bfd-sessions/bfd-sessions/bfd-ses'
              + 'sion/down-reason'
                ;
  }
  revision 2019-10-15 {
    description '1)Modify the leaf to optional: /configuration/bfd/sessions/ses'
              + 'sion/detect-type/l2-bfd/local-address.'
                ;
  }
  revision 2019-09-29 {
    description '1)Add container:configuration/bfd/sessions/session/shutdown-pa'
              + 'ras'+"\n"
              + '2)Add container:configuration/bfd/seamless-sessions/session/sh'
              + 'utdown-paras'
                ;
  }
  revision 2019-09-26 {
    description 'Add a container in configuration/bfd/global/backpath-check.'
                ;
  }
  revision 2019-07-12 {
    description '1)Add container:configuration/bfd/global/ipv4-echo-paras'+"\n"
              + '2)Add container:configuration/bfd/global/ipv6-echo-paras'+"\n"
              + '3)Add container:configuration/bfd/interface-paras/interface-pa'
              + 'ra/single-arm-echo-paras'+"\n"
              + '4)Add container:configuration/bfd/interface-paras/interface-pa'
              + 'ra/echo-paras'+"\n"
              + '5)Add enumaration:detect-mode'+"\n"
              + '6)Add enumaration:interface-check'+"\n"
              + '7)Add leaf:configuration/bfd/sessions/session/v4-link-bfd/v4-l'
              + 'ink-bfd/detect-mode'+"\n"
              + '8)Add leaf:configuration/bfd/sessions/session/v6-link-bfd/v6-l'
              + 'ink-bfd/detect-mode'+"\n"
              + '9)Add leaf:configuration/bfd/sessions/session/v4-link-bfd/v4-l'
              + 'ink-bfd/interface-check'+"\n"
              + '10)Add leaf:configuration/bfd/sessions/session/v6-link-bfd/v6-'
              + 'link-bfd/interface-check'+"\n"
              + '11)Add leaf:state/bfd/session-results/session-result/detect-mo'
              + 'de'
                ;
  }
  revision 2019-06-06 {
    description '1.Add a contianer v6-ldp-bfd in configuration/bfd/sessions/ses'
              + 'sion/detect-type'+"\n"
              + '2.Add a leaf source-address in configuration/bfd/sessions/sess'
              + 'ion/detect-type/ldp-bfd/ldp-bfd'
                ;
  }
  revision 2019-05-31 {
    description '1)Add container :configuration/bfd/seamless-sessions'+"\n"
              + '2)Add container :configuration/bfd/seamless-paras'+"\n"
              + '3)Add leaf:state/bfd/session-results/session-result/seamless-m'
              + 'ode'+"\n"
              + '4)Add leaf:state/bfd/session-results/session-result/seamless-r'
              + 'ole'
                ;
  }
  revision 2019-05-20 {
    description '1)Add 3 leafs,leaf-id, opaque-type, '+"\n"
              + 'p2mp-id in notification-bfd-sessions/bfd-sessions/bfd-session'+"\n"
              + '2)Add 3 leafs,leaf-id, opaque-type, '+"\n"
              + 'p2mp-id in state/bfd/session-results/session-result'
                ;
  }
  revision 2019-05-09 {
    description '1)Add container :configuration/bfd/gloabl/location-paras'+"\n"
              + '2)Add container :configuration/bfd/gloabl/passive-suppresses'
                ;
  }
  revision 2019-04-16 {
    description 'Add a node named "v4-sr-be-bfd" under /configuration/bfd/sessi'
              + 'ons/session/detect-type.'
                ;
  }
  revision 2019-04-01 {
    description '1.The default value modified to be performance parameter for /'
              + 'configuration/bfd/sessions/session/detect-type/v4-peer-bfd/tim'
              + 'e-negotiation/interval;'+"\n"
              + '2.The default value modified to be performance parameter for /'
              + 'configuration/bfd/sessions/session/detect-type/v4-peer-bfd/tim'
              + 'e-negotiation/min-rx;'+"\n"
              + '3.The default value modified to be performance parameter for /'
              + 'configuration/bfd/sessions/session/detect-type/v4-peer-bfd/tim'
              + 'e-negotiation/multiplier;'+"\n"
              + '4.The default value modified to be performance parameter for /'
              + 'configuration/bfd/sessions/session/detect-type/v6-peer-bfd/tim'
              + 'e-negotiation/interval;'+"\n"
              + '5.The default value modified to be performance parameter for /'
              + 'configuration/bfd/sessions/session/detect-type/v6-peer-bfd/tim'
              + 'e-negotiation/min-rx;'+"\n"
              + '6.The default value modified to be performance parameter for /'
              + 'configuration/bfd/sessions/session/detect-type/v6-peer-bfd/tim'
              + 'e-negotiation/multiplier;'+"\n"
              + '7.The default value modified to be performance parameter for /'
              + 'configuration/bfd/sessions/session/detect-type/ldp-bfd/time-ne'
              + 'gotiation/interval;'+"\n"
              + '8.The default value modified to be performance parameter for /'
              + 'configuration/bfd/sessions/session/detect-type/ldp-bfd/time-ne'
              + 'gotiation/min-rx;'+"\n"
              + '9.The default value modified to be performance parameter for /'
              + 'configuration/bfd/sessions/session/detect-type/ldp-bfd/time-ne'
              + 'gotiation/multiplier;'+"\n"
              + '10.The default value modified to be performance parameter for '
              + '/configuration/bfd/sessions/session/detect-type/rsvp-bfd/time-'
              + 'negotiation/interval;'+"\n"
              + '11.The default value modified to be performance parameter for '
              + '/configuration/bfd/sessions/session/detect-type/rsvp-bfd/time-'
              + 'negotiation/min-rx;'+"\n"
              + '12.The default value modified to be performance parameter for '
              + '/configuration/bfd/sessions/session/detect-type/rsvp-bfd/time-'
              + 'negotiation/multiplier;'+"\n"
              + '13.The default value modified to be performance parameter for '
              + '/configuration/bfd/sessions/session/detect-type/pw-bfd/time-ne'
              + 'gotiation/interval;'+"\n"
              + '14.The default value modified to be performance parameter for '
              + '/configuration/bfd/sessions/session/detect-type/pw-bfd/time-ne'
              + 'gotiation/min-rx;'+"\n"
              + '15.The default value modified to be performance parameter for '
              + '/configuration/bfd/sessions/session/detect-type/pw-bfd/time-ne'
              + 'gotiation/multiplier;'+"\n"
              + '16.The default value modified to be performance parameter for '
              + '/configuration/bfd/sessions/session/detect-type/l2-bfd/time-ne'
              + 'gotiation/interval;'+"\n"
              + '17.The default value modified to be performance parameter for '
              + '/configuration/bfd/sessions/session/detect-type/l2-bfd/time-ne'
              + 'gotiation/min-rx;'+"\n"
              + '18.The default value modified to be performance parameter for '
              + '/configuration/bfd/sessions/session/detect-type/l2-bfd/time-ne'
              + 'gotiation/multiplier;'+"\n"
              + '19.The default value modified to be performance parameter for '
              + '/configuration/bfd/interface-paras/interface-para/interval;'+"\n"
              + '20.The default value modified to be performance parameter for '
              + '/configuration/bfd/interface-paras/interface-para/min-rx;'+"\n"
              + '21.The default value modified to be performance parameter for '
              + '/configuration/bfd/interface-paras/interface-para/multiplier;'+"\n"
              + '22.Add configuration/sessions/session/detect-type/v4-link-bfd/'
              + 'v4-link-bfd/ld'+"\n"
              + '23.Add configuration/sessions/session/detect-type/v4-link-bfd/'
              + 'v4-link-bfd/rd'
                ;
  }
  revision 2019-02-19 {
    description '1)Add 5 new types to /bfd:notification-bfd-sessions/bfd:bfd-se'
              + 'ssions/bfd:bfd-session/bfd:detect-type:13 SubSingleHop, 14 Srb'
              + 'e, 15 Mldp, 16 Mldp-Passive, 17 Mte, 18Mte-Passive'+"\n"
              + '2)Add 5 new types to /bfd:state/bfd:bfd/bfd:session-results/bf'
              + 'd:session-result/bfd:bfd-detect-type :13 SubSingleHop, 14 Srbe'
              + ', 15 Mldp, 16 Mldp-Passive, 17 Mte, 18 Mte-Passive'+"\n"
              + '3)Add 5 new types to /bfd:state/bfd:bfd/bfd:global/bfd:statist'
              + 'ic :12 SubSingleHop, 13 Srbe, 14 Mldp, 15 Mldp-Passive, 16 Mte'
              + ', 17 Mte-Passive'+"\n"
              + '4 ) Add 3 new types to /bfd:state/bfd:bfd/bfd:session-results/'
              + 'bfd:session-result/bfd:summary-detect-type : 6 srbe,7 mldp, 8 '
              + 'mte'
                ;
  }
  revision 2018-12-05 {
    description '1) add /configuration/bfd/sessions/session/l2-bfd/notify-port-'
              + 'states/enable/enable'+"\n"
              + '2) add /configuration/bfd/sessions/session/l2-bfd/notify-port-'
              + 'states/enable/enable/exclude-notify-port-admin-down'+"\n"
              + '3) add  /configuration/bfd/sessions/session/l2-bfd/notify-port'
              + '-states/disable/disable'
                ;
  }
  revision 2018-10-22 {
    description '1)Add configuration\bfd\sessions\session\detect-type\l2-bfd\no'
              + 'tify-port-states.'
                ;
  }
  revision 2018-03-22 {
    description '1)Add configuration\bfd\sessions\session\detect-type\rsvp-bfd\r'
              + 'everse-tunnel-id'+"\n"
              + '2)Add configuration\bfd\sessions\session\detect-type\rsvp-bfd\s'
              + 'ource-address'
                ;
  }
  revision 2016-11-23 {
    description 'Add two leaves:'+"\n"
              + '1)configuration\bfd\ipv4-lag-para\ipv4-lag-src.'+"\n"
              + '2)configuration\bfd\ipv6-lag-para\ipv6-lag-src.'
                ;
  }
  revision 2015-11-02 {
    description 'Add notification /notification-bfd-sessions.'
                ;
  }
  revision 2015-08-05 {
    description '1 Add leaf /configuration/bfd/sessions/session/cv-stop/cv-stop.'
                ;
  }
  revision 2015-06-24 {
    description 'Add three leaves:'+"\n"
              + '1)configuration\bfd\sessions\session\detect-type\pw-bfd\lsp-pi'
              + 'ng.'+"\n"
              + '2)configuration\bfd\sessions\session\detect-type\pw-bfd\peer-r'
              + 'outer-ip.'+"\n"
              + '2)configuration\bfd\sessions\session\detect-type\pw-bfd\vc-id.'
                ;
  }
  revision 2014-10-14 {
    description '1.Modify the DerivedType of configuration/bfd/sessions/session'
              + '/detect-type/pw-bfd/pw-bfd/local-address '+"\n"
              + '2.Modify the DerivedType of configuration/bfd/sessions/session'
              + '/detect-type/pw-bfd/pw-bfd/remote-address'
                ;
  }
  revision 2014-05-28 {
    description '1.Add leaf state/bfd/global/statistic/device-total-num and sta'
              + 'te/bfd/global/statistic/device-left-num'+"\n"
              + '2.Modify the range of state/bfd/global/statistic/show-detect-t'
              + 'ype'+"\n"
              + '3.Modify the range of state/bfd/session-results/session-result'
              + '/bfd-detect-type'+"\n"
              + '4.Modify the range of state/bfd/session-results/session-result'
              + '/summary-detect-type'
                ;
  }
  revision 2014-02-14 {
    description '1.Modify the description and the range of the tunnel-id.'+"\n"
              + '2.Remove the default value of rd.'+"\n"
              + '3.Modify the description and add the range of ld.'+"\n"
              + '4.Modify the description of the interval.'+"\n"
              + '5.Modify the description of the min-rx.'
                ;
  }
  revision 2014-01-03 {
    description '1.The type of if-name is changed from string to ncd:ifname.'+"\n"
              + '2.Modify the description and remove the range of the interval.'
              + ''+"\n"
              + '3.Modify the description and remove the range of the min-rx.'+"\n"
              + '4.Modify the description and remove the range of the ld.'+"\n"
              + '5.The type of up-time is changed from string to ncd:string-wit'
              + 'h-blank.'+"\n"
              + '6.Modify the uniques of session,interface-para,session-result.'
                ;
  }
  revision 2013-10-14 {
    description 'Initial version.'
                ;
  }
  feature backpath-check ;
  feature session-admin-down {
    description 'Session admin-down'
                ;
  }
  feature location-board {
    description 'BFD location board configuration.'
                ;
  }
  feature template-for-session {
    description 'BFD session configration with template name.'
                ;
  }
  feature dcn {
    description 'BFD session configration with DCN.'
                ;
  }
  feature mode {
    description 'BFD negotiation mode'
                ;
  }
  feature gen-lsp-bfd {
    description 'Generic LSP BFD detect type.'
                ;
  }
  feature extend-max-ld-set ;
  feature srv6-be {
    description 'SRv6 BE BFD function.'
                ;
  }
  typedef detect-mode {
    type enumeration {
      enum Asynchronous {
        value 1 ;
        description 'Asynchronous mode'
                    ;
      }
      enum Single-arm-echo {
        value 2 ;
        description 'Single-arm-echo mode'
                    ;
      }
    }
    description 'Detect mode.'
                ;
  }
  typedef interface-check {
    type enumeration {
      enum disable {
        value 0 ;
        description 'Do not check receiving interface.'
                    ;
      }
      enum enable {
        value 1 ;
        description 'Check receiving interface.'
                    ;
      }
    }
    description 'Whether check receiving interface is same with sending interfa'
              + 'ce of ECHO BFD.'
                ;
  }
  typedef switch-set {
    type enumeration {
      enum disable {
        value 0 ;
        description Disable. ;
      }
      enum enable {
        value 1 ;
        description Enable. ;
      }
    }
    description 'Configure is enable or disable.'
                ;
  }
  typedef policy-set {
    type enumeration {
      enum standalone {
        value 1 ;
        description 'Choose only one board.'
                    ;
      }
      enum redundant {
        value 2 ;
        description 'Choose two boards.'
                    ;
      }
    }
    description 'Configure location board policy.'
                ;
  }
  container configuration {
    description 'Configuration model info.'
                ;
    container bfd {
      description 'Configure BFD parameters.'
                  ;
      container global {
        description 'Configure BFD global parameters.'
                    ;
        leaf multiport {
          description 'Configure multicast IPv4 address for l2-bfd.'
                      ;
          type ncd:ipv4-address ;
          default 224.0.0.250 ;
        }
        container location-paras {
          description 'Configure BFD local parameters.'
                      ;
          list resource-board {
            description 'Configure BFD resource board'
                        ;
            key if-name ;
            leaf if-name {
              description 'Configure BFD location interface.'
                          ;
              type ncd:ifname {
                length 1..31 {
                  description 'Output interface for p2mp'
                              ;
                }
              }
            }
          }
          ncd:revise-date 2019-05-09 ;
        }
        container passive-suppresses {
          description 'Configure BFD passive suppression'
                      ;
          list passive-suppress {
            description 'Suppress passive BFD'
                        ;
            key suppress-type ;
            leaf suppress-type {
              description 'Suppress passive BFD'
                          ;
              type enumeration {
                enum p2mp-passive {
                  value 1 ;
                  description 'p2mp passive BFD'
                              ;
                }
              }
            }
          }
          ncd:revise-date 2019-05-09 ;
        }
        container ipv4-echo-paras {
          description 'IPv4 echo parameters.'
                      ;
          leaf ipv4-echo-source {
            description 'Global source address of IPv4 echo BFD.'
                        ;
            type ncd:ipv4-address-none-zero ;
          }
          ncd:revise-date 2019-07-12 ;
        }
        container ipv6-echo-paras {
          description 'IPv6 echo parameters.'
                      ;
          leaf ipv6-echo-source {
            description 'Global source address of IPv6 echo BFD.'
                        ;
            type ncd:ipv6-address ;
          }
          ncd:revise-date 2019-07-12 ;
        }
        container backpath-check {
          if-feature backpath-check ;
          description 'Check RSVP-TE back-path if match with forward path.'
                      ;
          leaf backpath-check {
            description 'Check RSVP-TE back-path if match with forward path.'
                        ;
            type enumeration {
              enum disable {
                value 0 ;
                description 'Disable RSVP BFD backpath check with forward path'
                            ;
              }
              enum enable {
                value 1 ;
                description 'Enable RSVP BFD backpath check with forward path'
                            ;
              }
            }
          }
          container exclude-tunnels {
            description 'Add exception which not do back-path check.'
                        ;
            list exclude {
              description 'Add exception which not do back-path check.'
                          ;
              key tunnel-id ;
              leaf tunnel-id {
                description 'The tunnel-id which not do back-path check.'
                            ;
                type uint32 {
                  range 1..4294967295 {
                    description 'TE TunnelID for RSVP TUNNEL BFD,the range of t'
                              + 'his parameter depends on the device.'
                                ;
                  }
                }
              }
            }
          }
          ncd:revise-date 2019-09-26 ;
        }
        container board-paras {
          description 'Configure BFD location board parameters.'
                      ;
          leaf policy {
            if-feature location-board ;
            description 'BFD location policy.'
                        ;
            type policy-set ;
          }
          list board {
            if-feature location-board ;
            description 'BFD location board.'
                        ;
            key name ;
            leaf name {
              description 'Board name.'
                          ;
              type ncd:board {
                length 1..31 {
                  description 'Board name.'
                              ;
                }
              }
            }
          }
          ncd:revise-date 2020-02-20 ;
        }
        container mode {
          if-feature mode ;
          description 'Configure BFD negotiation mode.'
                      ;
          leaf mode {
            type enumeration {
              enum software {
                value 0 ;
                description 'Negotiate by software.'
                            ;
              }
              enum hardware {
                value 1 ;
                description 'Negotiate by hardware'
                            ;
              }
            }
            default software ;
          }
          ncd:revise-date 2020-07-01 ;
        }
        container extend-max-ld-set {
          if-feature extend-max-ld-set ;
          description 'Configure BFD extend max discriminator'
                      ;
          leaf extend-max-ld-set {
            description 'Configure BFD extend maximum discriminator'
                        ;
            type enumeration {
              enum disable {
                value 0 ;
                description 'Disable the extended maximum LD.'
                            ;
              }
              enum enable {
                value 1 ;
                description 'Enable the extended maximum LD.'
                            ;
              }
            }
            default disable ;
          }
          ncd:revise-date 2020-07-23 ;
        }
      }
      container sessions {
        description 'Configure BFD instance parameters.'
                    ;
        list session {
          description 'Configure BFD instance parameters.'
                      ;
          key instance-name ;
          leaf instance-name {
            description 'Instance name for BFD session.'
                        ;
            type string {
              length 1..32 {
                description 'Instance name for BFD session.'
                            ;
              }
            }
          }
          choice detect-type {
            description 'Detect type for BFD session.'
                        ;
            mandatory true ;
            case v4-link-bfd {
              description 'Single-hop IPv4 BFD.'
                          ;
              container v4-link-bfd {
                description 'Single-hop IPv4 BFD.'
                            ;
                leaf local-address {
                  description 'Local address for IPv4 link BFD.'
                              ;
                  type ncd:ipv4-address ;
                  mandatory true ;
                }
                leaf remote-address {
                  description 'Remote address for IPv4 link BFD.'
                              ;
                  type ncd:ipv4-address ;
                  mandatory true ;
                }
                leaf if-name {
                  description 'Output interface for IPv4 link BFD.'
                              ;
                  type ncd:ifname {
                    length 1..31 {
                      description 'Output interface for IPv4 link BFD.'
                                  ;
                    }
                  }
                  mandatory true ;
                }
                leaf ld {
                  description 'Local discriminator for IPv4 link BFD,the range '
                            + 'of this parameter depends on the device,default '
                            + 'range 1-4294967295.'
                              ;
                  type uint32 {
                    range 1..4294967295 {
                      description 'Local discriminator for IPv4 link BFD,the ra'
                                + 'nge of this parameter depends on the device,'
                                + 'default range 1-4294967295.'
                                  ;
                    }
                  }
                  ncd:revise-date 2019-04-01 ;
                }
                leaf rd {
                  description 'Remote discriminator for IPv4 link BFD.'
                              ;
                  type uint32 {
                    range 1..4294967295 {
                      description 'Remote discriminator for IPv4 link BFD.'
                                  ;
                    }
                  }
                  ncd:revise-date 2019-04-01 ;
                }
                leaf detect-mode {
                  description 'Detect mode.'
                              ;
                  type detect-mode ;
                  ncd:revise-date 2019-07-12 ;
                }
                leaf interface-check {
                  description 'Whether check receiving interface is same with s'
                            + 'ending interface of ECHO BFD.'
                              ;
                  type interface-check ;
                  default enable ;
                  ncd:revise-date 2019-07-12 ;
                }
                container big-pkt {
                  description 'Configure BFD packet len parameters.'
                              ;
                  leaf min-pkt-len {
                    description 'Minimum packet length of BFD.'
                                ;
                    type uint16 {
                      range 24..512 {
                        description 'Minimum packet length of BFD.'
                                    ;
                      }
                    }
                    default 24 ;
                  }
                  leaf max-pkt-len {
                    description 'Maximum packet length of BFD.'
                                ;
                    type uint16 {
                      range 24..512 {
                        description 'Maximum packet length of BFD.'
                                    ;
                      }
                    }
                    default 24 ;
                  }
                }
                leaf template-name {
                  if-feature template-for-session ;
                  description 'Template name.'
                              ;
                  type string {
                    length 1..31 {
                      description 'Template name.'
                                  ;
                    }
                  }
                  ncd:revise-date 2020-02-20 ;
                }
                choice vrf {
                  description 'Configuration of VRF.'
                              ;
                  case vrf-name {
                    description 'VRF name for IPv4 link BFD.'
                                ;
                    leaf vrf-name {
                      description 'VRF name for IPv4 link BFD.'
                                  ;
                      type string {
                        length 1..32 {
                          description 'VRF name for IPv4 link BFD(1-32 characte'
                                    + 'rs).'
                                      ;
                        }
                      }
                    }
                  }
                  case dcn {
                    description 'Specify DCN VRF.'
                                ;
                    leaf dcn {
                      if-feature dcn ;
                      description 'Specify DCN VRF.'
                                  ;
                      type uint8 {
                        range 1 {
                          description 'DCN VRF specified.'
                                      ;
                        }
                      }
                    }
                    ncd:revise-date 2020-05-15 ;
                  }
                }
              }
            }
            case v6-link-bfd {
              description 'Single-hop IPv6 BFD.'
                          ;
              container v6-link-bfd {
                description 'Single-hop IPv6 BFD.'
                            ;
                leaf local-address {
                  description 'Local address for IPv6 link BFD.'
                              ;
                  type ncd:ipv6-address ;
                  mandatory true ;
                }
                leaf remote-address {
                  description 'Remote address for IPv6 link BFD.'
                              ;
                  type ncd:ipv6-address ;
                  mandatory true ;
                }
                leaf if-name {
                  description 'Output interface for IPv6 link BFD.'
                              ;
                  type ncd:ifname {
                    length 1..31 {
                      description 'Output interface for IPv6 link BFD.'
                                  ;
                    }
                  }
                  mandatory true ;
                }
                leaf detect-mode {
                  description 'Detect mode.'
                              ;
                  type detect-mode ;
                  ncd:revise-date 2019-07-12 ;
                }
                leaf interface-check {
                  description 'Whether check receiving interface is same with s'
                            + 'ending interface of ECHO BFD.'
                              ;
                  type interface-check ;
                  default enable ;
                  ncd:revise-date 2019-07-12 ;
                }
                container big-pkt {
                  description 'Configure BFD packet len parameters.'
                              ;
                  leaf min-pkt-len {
                    description 'Minimum packet length of BFD.'
                                ;
                    type uint16 {
                      range 24..512 {
                        description 'Minimum packet length of BFD.'
                                    ;
                      }
                    }
                    default 24 ;
                  }
                  leaf max-pkt-len {
                    description 'Maximum packet length of BFD.'
                                ;
                    type uint16 {
                      range 24..512 {
                        description 'Maximum packet length of BFD.'
                                    ;
                      }
                    }
                    default 24 ;
                  }
                }
                leaf template-name {
                  if-feature template-for-session ;
                  description 'Template name.'
                              ;
                  type string {
                    length 1..31 ;
                  }
                  ncd:revise-date 2020-02-20 ;
                }
                choice vrf {
                  description 'Configuration of VRF.'
                              ;
                  case vrf-name {
                    description 'VRF name for IPv6 link BFD.'
                                ;
                    leaf vrf-name {
                      description 'VRF name for IPv6 link BFD.'
                                  ;
                      type string {
                        length 1..32 {
                          description 'VRF name for IPv6 link BFD(1-32 characte'
                                    + 'rs).'
                                      ;
                        }
                      }
                    }
                  }
                  case dcn {
                    description 'Specify DCN VRF.'
                                ;
                    leaf dcn {
                      if-feature dcn ;
                      description 'Specify DCN VRF.'
                                  ;
                      type uint8 {
                        range 1 {
                          description 'DCN VRF specified.'
                                      ;
                        }
                      }
                    }
                    ncd:revise-date 2020-05-15 ;
                  }
                }
              }
            }
            case v4-peer-bfd {
              description 'Multi-hop IPv4 BFD.'
                          ;
              container v4-peer-bfd {
                description 'Multi-hop IPv4 BFD.'
                            ;
                leaf local-address {
                  description 'Local address for IPv4 peer BFD.'
                              ;
                  type ncd:ipv4-address ;
                  mandatory true ;
                }
                leaf remote-address {
                  description 'Remote address for IPv4 peer BFD.'
                              ;
                  type ncd:ipv4-address ;
                  mandatory true ;
                }
                leaf vrf-name {
                  description 'VRF name for IPv4 peer BFD.'
                              ;
                  type string {
                    length 1..32 {
                      description 'VRF name for IPv4 peer BFD(1-32 characters).'
                                  ;
                    }
                  }
                }
                leaf ld {
                  description 'Local discriminator for IPv4 peer BFD,the range '
                            + 'of this parameter depends on the device,default '
                            + 'range 1-4294967295.'
                              ;
                  type uint32 {
                    range 1..4294967295 {
                      description 'Local discriminator for IPv4 peer BFD,the ra'
                                + 'nge of this parameter depends on the device,'
                                + 'default range 1-4294967295.'
                                  ;
                    }
                  }
                }
                leaf rd {
                  description 'Remote discriminator for IPv4 peer BFD.'
                              ;
                  type uint32 {
                    range 1..4294967295 {
                      description 'Remote discriminator for IPv4 peer BFD.'
                                  ;
                    }
                  }
                }
                container big-pkt {
                  description 'Configure BFD packet len parameters.'
                              ;
                  leaf min-pkt-len {
                    description 'Minimum packet length of BFD.'
                                ;
                    type uint16 {
                      range 24..512 {
                        description 'Minimum packet length of BFD.'
                                    ;
                      }
                    }
                    default 24 ;
                  }
                  leaf max-pkt-len {
                    description 'Maximum packet length of BFD.'
                                ;
                    type uint16 {
                      range 24..512 {
                        description 'Maximum packet length of BFD.'
                                    ;
                      }
                    }
                    default 24 ;
                  }
                }
                container multiport {
                  description 'Configure dest UDP port of multi-hop BFD.'
                              ;
                  leaf enable-disable {
                    description 'Configure dest UDP port of multi-hop BFD.'
                                ;
                    type enumeration {
                      enum disable {
                        value 0 ;
                        description 'Specify port to 4784.'
                                    ;
                      }
                      enum enable {
                        value 1 ;
                        description 'Specify port to 3784.'
                                    ;
                      }
                    }
                    default disable ;
                  }
                }
                container time-negotiation {
                  description 'Configure BFD time negotiation parameter.'
                              ;
                  leaf interval {
                    description 'BFD control packets TX interval in millisecond'
                              + 's,the range and default value of this paramete'
                              + 'r depends on the device,default range is 10-99'
                              + '0, default value is 50.'
                                ;
                    type uint32 ;
                  }
                  leaf min-rx {
                    description 'BFD control packets min RX in milliseconds,the'
                              + ' range and default value of this parameter dep'
                              + 'ends on the device,default range is 10-990, de'
                              + 'fault value is 50.'
                                ;
                    type uint32 ;
                  }
                  leaf multiplier {
                    description 'BFD detect multiplier, the default value of th'
                              + 'is parameter depends on the device,  default i'
                              + 's 3.'
                                ;
                    type uint8 {
                      range 3..50 {
                        description 'BFD detect multiplier.'
                                    ;
                      }
                    }
                  }
                }
                leaf template-name {
                  if-feature template-for-session ;
                  description 'Template name.'
                              ;
                  type string {
                    length 1..31 ;
                  }
                  ncd:revise-date 2020-02-20 ;
                }
              }
            }
            case v6-peer-bfd {
              description 'Multi-hop IPv6 BFD.'
                          ;
              container v6-peer-bfd {
                description 'Multi-hop IPv6 BFD.'
                            ;
                leaf local-address {
                  description 'Local address for IPv6 peer BFD.'
                              ;
                  type ncd:ipv6-address ;
                  mandatory true ;
                }
                leaf remote-address {
                  description 'Remote address for IPv6 peer BFD.'
                              ;
                  type ncd:ipv6-address ;
                  mandatory true ;
                }
                leaf vrf-name {
                  description 'VRF name for IPv6 peer BFD.'
                              ;
                  type string {
                    length 1..32 {
                      description 'VRF name for IPv6 peer BFD(1-32 characters).'
                                  ;
                    }
                  }
                }
                container big-pkt {
                  description 'Configure BFD packet len parameters.'
                              ;
                  leaf min-pkt-len {
                    description 'Minimum packet length of BFD.'
                                ;
                    type uint16 {
                      range 24..512 {
                        description 'Minimum packet length of BFD.'
                                    ;
                      }
                    }
                    default 24 ;
                  }
                  leaf max-pkt-len {
                    description 'Maximum packet length of BFD.'
                                ;
                    type uint16 {
                      range 24..512 {
                        description 'Maximum packet length of BFD.'
                                    ;
                      }
                    }
                    default 24 ;
                  }
                }
                container multiport {
                  description 'Configure dest UDP port of multi-hop BFD.'
                              ;
                  leaf enable-disable {
                    description 'Configure dest UDP port of multi-hop BFD.'
                                ;
                    type enumeration {
                      enum disable {
                        value 0 ;
                        description 'Specify port to 4784.'
                                    ;
                      }
                      enum enable {
                        value 1 ;
                        description 'Specify port to 3784.'
                                    ;
                      }
                    }
                    default disable ;
                  }
                }
                container time-negotiation {
                  description 'Configure BFD time negotiation parameter.'
                              ;
                  leaf interval {
                    description 'BFD control packets TX interval in millisecond'
                              + 's, the range and default value of this paramet'
                              + 'er depends on the device,default range is 10-9'
                              + '90, default value is 50.'
                                ;
                    type uint32 ;
                  }
                  leaf min-rx {
                    description 'BFD control packets min RX in milliseconds, th'
                              + 'e range and default value of this parameter de'
                              + 'pends on the device,default range is 10-990, d'
                              + 'efault value is 50.'
                                ;
                    type uint32 ;
                  }
                  leaf multiplier {
                    description 'BFD detect multiplier, the default value of th'
                              + 'is parameter depends on the device,  default i'
                              + 's 3.'
                                ;
                    type uint8 {
                      range 3..50 {
                        description 'BFD detect multiplier.'
                                    ;
                      }
                    }
                  }
                }
                leaf template-name {
                  if-feature template-for-session ;
                  description 'Template name.'
                              ;
                  type string {
                    length 1..31 ;
                  }
                  ncd:revise-date 2020-02-20 ;
                }
              }
            }
            case ldp-bfd {
              description 'LDP BFD.'
                          ;
              container ldp-bfd {
                description 'LDP BFD.'
                            ;
                leaf fec-address {
                  description 'FEC address for LDP BFD.'
                              ;
                  type ncd:ipv4-address ;
                  mandatory true ;
                }
                leaf mask-length {
                  description 'FEC mask length for LDP BFD.'
                              ;
                  type uint32 {
                    range 0..32 {
                      description 'FEC mask length for LDP BFD.'
                                  ;
                    }
                  }
                  mandatory true ;
                }
                leaf source-address {
                  description 'source address for LDP BFD.'
                              ;
                  type ncd:ipv4-address-none-zero ;
                  ncd:revise-date 2019-06-06 ;
                }
                leaf vrf-name {
                  description 'VRF name for LDP BFD.'
                              ;
                  type string {
                    length 1..32 {
                      description 'VRF name for LDP BFD(1-32 characters).'
                                  ;
                    }
                  }
                }
                leaf ld {
                  description 'Local discriminator for LDP BFD,the range of thi'
                            + 's parameter depends on the device,default range '
                            + '1-4294967295.'
                              ;
                  type uint32 {
                    range 1..4294967295 {
                      description 'Local discriminator for LDP BFD,the range of'
                                + ' this parameter depends on the device,defaul'
                                + 't range 1-4294967295.'
                                  ;
                    }
                  }
                }
                leaf rd {
                  description 'Remote discriminator for LDP BFD.'
                              ;
                  type uint32 {
                    range 1..4294967295 {
                      description 'Remote discriminator for LDP BFD.'
                                  ;
                    }
                  }
                }
                container protect-binding {
                  description 'Configure switching rules of LDP BFD.'
                              ;
                  leaf enable-disable {
                    description 'Configure switching rules of LDP BFD.'
                                ;
                    type enumeration {
                      enum enable {
                        value 0 ;
                        description 'Protect binding.'
                                    ;
                      }
                      enum disable {
                        value 1 ;
                        description 'Protect unbinding.'
                                    ;
                      }
                    }
                    default enable ;
                  }
                }
                container time-negotiation {
                  description 'Configure BFD time negotiation parameter.'
                              ;
                  leaf interval {
                    description 'BFD control packets TX interval in millisecond'
                              + 's, the range and default value of this paramet'
                              + 'er depends on the device, default range is 10-'
                              + '990, default value is 50.'
                                ;
                    type uint32 ;
                  }
                  leaf min-rx {
                    description 'BFD control packets min RX in milliseconds, th'
                              + 'e range and default value of this parameter de'
                              + 'pends on the device,default range is 10-990, d'
                              + 'efault value is 50.'
                                ;
                    type uint32 ;
                  }
                  leaf multiplier {
                    description 'BFD detect multiplier, the default value of th'
                              + 'is parameter depends on the device,  default i'
                              + 's 3.'
                                ;
                    type uint8 {
                      range 3..50 {
                        description 'BFD detect multiplier.'
                                    ;
                      }
                    }
                  }
                }
                leaf template-name {
                  if-feature template-for-session ;
                  description 'Template name.'
                              ;
                  type string {
                    length 1..31 ;
                  }
                  ncd:revise-date 2020-02-20 ;
                }
              }
            }
            case v6-ldp-bfd {
              description 'LDP BFD.'
                          ;
              container v6-ldp-bfd {
                description 'LDP BFD.'
                            ;
                leaf fec-address {
                  description 'FEC address for LDP BFD.'
                              ;
                  type ncd:ipv6-address ;
                  mandatory true ;
                }
                leaf mask-length {
                  description 'FEC mask length for LDP BFD.'
                              ;
                  type uint32 {
                    range 0..128 {
                      description 'FEC mask length for LDP BFD.'
                                  ;
                    }
                  }
                  mandatory true ;
                }
                leaf source-address {
                  description 'source address for LDP BFD.'
                              ;
                  type ncd:ipv6-address ;
                }
                leaf vrf-name {
                  description 'VRF name for LDP BFD.'
                              ;
                  type string {
                    length 1..32 {
                      description 'VRF name for LDP BFD(1-32 characters).'
                                  ;
                    }
                  }
                }
                leaf ld {
                  description 'Local discriminator for LDP BFD,the range of thi'
                            + 's parameter depends on the device,default range '
                            + '1-4294967295.'
                              ;
                  type uint32 {
                    range 1..4294967295 {
                      description 'Local discriminator for LDP BFD,the range of'
                                + ' this parameter depends on the device,defaul'
                                + 't range 1-4294967295.'
                                  ;
                    }
                  }
                }
                leaf rd {
                  description 'Remote discriminator for LDP BFD.'
                              ;
                  type uint32 {
                    range 1..4294967295 {
                      description 'Remote discriminator for LDP BFD.'
                                  ;
                    }
                  }
                }
                container protect-binding {
                  description 'Configure switching rules of LDP BFD.'
                              ;
                  leaf enable-disable {
                    description 'Configure switching rules of LDP BFD.'
                                ;
                    type enumeration {
                      enum enable {
                        value 0 ;
                        description 'Protect binding.'
                                    ;
                      }
                      enum disable {
                        value 1 ;
                        description 'Protect unbinding.'
                                    ;
                      }
                    }
                    default enable ;
                  }
                }
                container time-negotiation {
                  description 'Configure BFD time negotiation parameter.'
                              ;
                  leaf interval {
                    description 'BFD control packets TX interval in millisecond'
                              + 's, the range and default value of this paramet'
                              + 'er depends on the device, default range is 10-'
                              + '990, default value is 50.'
                                ;
                    type uint32 ;
                  }
                  leaf min-rx {
                    description 'BFD control packets min RX in milliseconds, th'
                              + 'e range and default value of this parameter de'
                              + 'pends on the device,default range is 10-990, d'
                              + 'efault value is 50.'
                                ;
                    type uint32 ;
                  }
                  leaf multiplier {
                    description 'BFD detect multiplier, the default value of th'
                              + 'is parameter depends on the device,  default i'
                              + 's 3.'
                                ;
                    type uint8 {
                      range 3..50 {
                        description 'BFD detect multiplier.'
                                    ;
                      }
                    }
                  }
                }
                leaf template-name {
                  if-feature template-for-session ;
                  description 'Template name.'
                              ;
                  type string {
                    length 1..31 ;
                  }
                  ncd:revise-date 2020-02-20 ;
                }
              }
              ncd:revise-date 2019-06-06 ;
            }
            case rsvp-bfd {
              description 'RSVP TUNNEL BFD.'
                          ;
              container rsvp-bfd {
                description 'RSVP TUNNEL BFD.'
                            ;
                leaf tunnel-id {
                  description 'TE TunnelID for RSVP TUNNEL BFD,the range of thi'
                            + 's parameter depends on the device.'
                              ;
                  type uint32 {
                    range 1..4294967295 {
                      description 'TE TunnelID for RSVP TUNNEL BFD,the range of'
                                + ' this parameter depends on the device.'
                                  ;
                    }
                  }
                  mandatory true ;
                }
                leaf ld {
                  description 'Local discriminator for RSVP TUNNEL BFD,the rang'
                            + 'e of this parameter depends on the device,defaul'
                            + 't range 1-4294967295.'
                              ;
                  type uint32 {
                    range 1..4294967295 {
                      description 'Local discriminator for RSVP TUNNEL BFD,the '
                                + 'range of this parameter depends on the devic'
                                + 'e,default range 1-4294967295.'
                                  ;
                    }
                  }
                }
                leaf rd {
                  description 'Remote discriminator for RSVP TUNNEL BFD.'
                              ;
                  type uint32 {
                    range 1..4294967295 {
                      description 'Remote discriminator for RSVP TUNNEL BFD.'
                                  ;
                    }
                  }
                }
                leaf reverse-tunnel-id {
                  description 'Tunnel ID of reverse RSVP TUNNEL,the range of th'
                            + 'is parameter is [1,65535].'
                              ;
                  type uint32 {
                    range 1..65535 {
                      description 'Tunnel ID of reverse RSVP TUNNEL.'
                                  ;
                    }
                  }
                  ncd:revise-date 2018-03-22 ;
                }
                leaf source-address {
                  description 'Local address for RSVP TUNNEL BFD.'
                              ;
                  type ncd:ipv4-address-none-zero ;
                  ncd:revise-date 2018-03-22 ;
                }
                container time-negotiation {
                  description 'Configure BFD time negotiation parameter.'
                              ;
                  leaf interval {
                    description 'BFD control packets TX interval in millisecond'
                              + 's, the range and default value of this paramet'
                              + 'er depends on the device, default range is 10-'
                              + '990, default value is 50.'
                                ;
                    type uint32 ;
                  }
                  leaf min-rx {
                    description 'BFD control packets min RX in milliseconds, th'
                              + 'e range and default value of this parameter de'
                              + 'pends on the device, default range is 10-990, '
                              + 'default value is 50.'
                                ;
                    type uint32 ;
                  }
                  leaf multiplier {
                    description 'BFD detect multiplier, the default value of th'
                              + 'is parameter depends on the device,  default i'
                              + 's 3.'
                                ;
                    type uint8 {
                      range 3..50 {
                        description 'BFD detect multiplier.'
                                    ;
                      }
                    }
                  }
                }
                leaf template-name {
                  if-feature template-for-session ;
                  description 'Template name.'
                              ;
                  type string {
                    length 1..31 ;
                  }
                  ncd:revise-date 2020-02-20 ;
                }
              }
            }
            case pw-bfd {
              description 'PW BFD.'
                          ;
              container pw-bfd {
                description 'PW BFD.'
                            ;
                leaf pw-name {
                  description 'PW name for PW BFD.'
                              ;
                  type string {
                    length 1..31 {
                      description 'PW name for PW BFD(1-31 characters).'
                                  ;
                    }
                  }
                  mandatory true ;
                }
                leaf local-address {
                  description 'Local address for PW BFD.'
                              ;
                  type ncd:ipv4-address-none-zero ;
                }
                leaf remote-address {
                  description 'Remote address for PW BFD.'
                              ;
                  type ncd:ipv4-address-none-zero ;
                }
                leaf pw-ttl {
                  description 'PW TTL value for PW BFD.'
                              ;
                  type uint8 {
                    range 1..255 {
                      description 'PW TTL value for PW BFD.'
                                  ;
                    }
                  }
                }
                leaf lsp-ping {
                  description 'Whether bootstrap BFD by LSP ping.'
                              ;
                  type enumeration {
                    enum disable {
                      value 0 ;
                      description 'Bootstrap by BFD control packet.'
                                  ;
                    }
                    enum enable {
                      value 1 ;
                      description 'Bootstrap by LSP ping.'
                                  ;
                    }
                  }
                  default disable ;
                  ncd:revise-date 2016-11-23 ;
                }
                leaf peer-router-ip {
                  description 'Peer router IP.'
                              ;
                  type ncd:ipv4-address-none-zero ;
                  ncd:revise-date 2016-11-23 ;
                }
                leaf vc-id {
                  description 'VC ID.'
                              ;
                  type uint32 {
                    range 1..4294967295 {
                      description 'Range of VC ID.'
                                  ;
                    }
                  }
                  ncd:revise-date 2016-11-23 ;
                }
                container time-negotiation {
                  description 'Configure BFD time negotiation parameter.'
                              ;
                  leaf interval {
                    description 'BFD control packets TX interval in millisecond'
                              + 's, the range and default value of this paramet'
                              + 'er depends on the device, default range is 10-'
                              + '990, default value is 50.'
                                ;
                    type uint32 ;
                  }
                  leaf min-rx {
                    description 'BFD control packets min RX in milliseconds, th'
                              + 'e range and default value of this parameter de'
                              + 'pends on the device, default range is 10-990, '
                              + 'default value is 50.'
                                ;
                    type uint32 ;
                  }
                  leaf multiplier {
                    description 'BFD detect multiplier, the default value of th'
                              + 'is parameter depends on the device,  default i'
                              + 's 3.'
                                ;
                    type uint8 {
                      range 3..50 {
                        description 'BFD detect multiplier.'
                                    ;
                      }
                    }
                  }
                }
                leaf template-name {
                  if-feature template-for-session ;
                  description 'Template name.'
                              ;
                  type string {
                    length 1..31 ;
                  }
                  ncd:revise-date 2020-02-20 ;
                }
                leaf ld {
                  description 'Local discriminator for PW BFD,the range of this'
                            + ' parameter depends on the device,default range 1'
                            + '-4294967295.'
                              ;
                  type uint32 {
                    range 1..4294967295 {
                      description 'Local discriminator for PW BFD,the range of '
                                + 'this parameter depends on the device,default'
                                + ' range 1-4294967295.'
                                  ;
                    }
                  }
                  ncd:revise-date 2020-07-11 ;
                }
                leaf rd {
                  description 'Remote discriminator for PW BFD.'
                              ;
                  type uint32 {
                    range 1..4294967295 {
                      description 'Remote discriminator for PW BFD.'
                                  ;
                    }
                  }
                  ncd:revise-date 2020-07-11 ;
                }
              }
            }
            case l2-bfd {
              description 'L2 link BFD.'
                          ;
              container l2-bfd {
                description 'L2 link BFD.'
                            ;
                leaf if-name {
                  description 'Output interface for l2 link BFD.'
                              ;
                  type ncd:ifname {
                    length 1..31 {
                      description 'Output interface for l2 link BFD.'
                                  ;
                    }
                  }
                  mandatory true ;
                }
                leaf local-address {
                  description 'Local address for l2 link BFD.'
                              ;
                  type ncd:ipv4-address ;
                }
                container discriminator {
                  description 'Configure BFD local and remote discriminator.'
                              ;
                  leaf ld {
                    description 'Local discriminator for l2 link BFD,the range '
                              + 'of this parameter depends on the device,defaul'
                              + 't range 1-4294967295.'
                                ;
                    type uint32 {
                      range 1..4294967295 {
                        description 'Local discriminator for l2 link BFD,the ra'
                                  + 'nge of this parameter depends on the devic'
                                  + 'e,default range 1-4294967295.'
                                    ;
                      }
                    }
                  }
                  leaf rd {
                    description 'Remote discriminator for l2 link BFD.'
                                ;
                    type uint32 {
                      range 1..4294967295 {
                        description 'Remote discriminator for l2 link BFD.'
                                    ;
                      }
                    }
                  }
                }
                container time-negotiation {
                  description 'Configure BFD time negotiation parameter.'
                              ;
                  leaf interval {
                    description 'BFD control packets TX interval in millisecond'
                              + 's, the range and default value of this paramet'
                              + 'er depends on the device, default range is 10-'
                              + '990, default value is 50.'
                                ;
                    type uint32 ;
                  }
                  leaf min-rx {
                    description 'BFD control packets min RX in milliseconds, th'
                              + 'e range and default value of this parameter de'
                              + 'pends on the device, default range is 10-990, '
                              + 'default value is 50.'
                                ;
                    type uint32 ;
                  }
                  leaf multiplier {
                    description 'BFD detect multiplier, the default value of th'
                              + 'is parameter depends on the device,  default i'
                              + 's 3.'
                                ;
                    type uint8 {
                      range 3..50 {
                        description 'BFD detect multiplier.'
                                    ;
                      }
                    }
                  }
                }
                container notify-port-states {
                  description 'Whether to notify interface BFD detection state.'
                              ;
                  leaf notify-port-state {
                    status obsolete {
                      ncd:revise-date 2018-12-05 ;
                    }
                    description 'Whether to notify interface BFD detection stat'
                              + 'e, default value is determined by performance '
                              + 'code.'
                                ;
                    type enumeration {
                      enum disable {
                        value 0 ;
                        description 'Disabe notification of interface state.'
                                    ;
                      }
                      enum enable {
                        value 1 ;
                        description 'Enable notification of interface state.'
                                    ;
                      }
                    }
                  }
                  leaf notify-port-admin-down {
                    status obsolete {
                      ncd:revise-date 2018-12-05 ;
                    }
                    description 'Whether admin down state is included in the BF'
                              + 'D detection state of the notification interfac'
                              + 'e, default is excluded.'
                                ;
                    type enumeration {
                      enum exclude {
                        value 0 ;
                        description "Don't notify interface when BFD is admin d"
                                  + "own."
                                    ;
                      }
                      enum include {
                        value 1 ;
                        description 'Notify interface when BFD is admin down.'
                                    ;
                      }
                    }
                    default exclude ;
                  }
                  choice notify-portstate {
                    case enable {
                      leaf enable {
                        description 'Notify interface BFD detection state, defa'
                                  + 'ult value is determined by performance cod'
                                  + 'e.'
                                    ;
                        type empty ;
                        mandatory true ;
                      }
                      leaf exclude-notify-port-admin-down {
                        description 'Whether admin down state is included in th'
                                  + 'e BFD detection state of the notification '
                                  + 'interface, default is excluded.'
                                    ;
                        type enumeration {
                          enum include {
                            value 1 ;
                            description 'Notify interface when BFD is admin down.'
                                        ;
                          }
                          enum exclude {
                            value 0 ;
                            description "Don't notify interface when BFD is admin down."
                                        ;
                          }
                        }
                        default exclude ;
                      }
                    }
                    case disable {
                      leaf disable {
                        description "Don't notify interface BFD detection state"
                                  + ", default value is determined by performan"
                                  + "ce code."
                                    ;
                        type empty ;
                        mandatory true ;
                      }
                    }
                    ncd:revise-date 2018-12-05 ;
                  }
                  ncd:revise-date 2018-10-22 ;
                }
              }
            }
            case v4-sr-be-bfd {
              container v4-sr-be-bfd {
                description 'SR BE BFD.'
                            ;
                leaf ipv4 {
                  description 'IPv4 address for SR BE BFD.'
                              ;
                  type ncd:ipv4-address ;
                  mandatory true ;
                }
                leaf mask-length {
                  description 'IPv4 mask length for SR BE BFD.'
                              ;
                  type uint32 {
                    range 0..32 {
                      description 'IPv4 mask length for SR BE BFD.'
                                  ;
                    }
                  }
                  mandatory true ;
                }
                leaf vrf-name {
                  description 'VRF name for SR BE BFD.'
                              ;
                  type string {
                    length 1..32 {
                      description 'VRF name for SR BE BFD(1-32 characters).'
                                  ;
                    }
                  }
                }
                leaf ld {
                  description 'Local discriminator for SR BE BFD,the range of t'
                            + 'his parameter depends on the device,default rang'
                            + 'e 1-4294967295.'
                              ;
                  type uint32 {
                    range 1..4294967295 {
                      description 'Local discriminator for SR BE BFD,the range '
                                + 'of this parameter depends on the device,defa'
                                + 'ult range 1-4294967295.'
                                  ;
                    }
                  }
                }
                leaf rd {
                  description 'Remote discriminator for SR BE BFD.'
                              ;
                  type uint32 {
                    range 1..4294967295 {
                      description 'Remote discriminator for SR BE BFD.'
                                  ;
                    }
                  }
                }
                leaf source {
                  description 'IPv4 source address for SR BE BFD.'
                              ;
                  type ncd:ipv4-address-none-zero ;
                }
                container time-negotiation {
                  description 'Configure BFD time negotiation parameter.'
                              ;
                  leaf interval {
                    description 'BFD control packets TX interval in millisecond'
                              + 's, the range and default value of this paramet'
                              + 'er depends on the device, default range is 10-'
                              + '990, default value is 50.'
                                ;
                    type uint32 ;
                  }
                  leaf min-rx {
                    description 'BFD control packets min RX in milliseconds, th'
                              + 'e range and default value of this parameter de'
                              + 'pends on the device,default range is 10-990, d'
                              + 'efault value is 50.'
                                ;
                    type uint32 ;
                  }
                  leaf multiplier {
                    description 'BFD detect multiplier, the default value of th'
                              + 'is parameter depends on the device,  default i'
                              + 's 3.'
                                ;
                    type uint8 {
                      range 3..50 {
                        description 'BFD detect multiplier.'
                                    ;
                      }
                    }
                  }
                }
                leaf template-name {
                  if-feature template-for-session ;
                  description 'Template name.'
                              ;
                  type string {
                    length 1..31 ;
                  }
                  ncd:revise-date 2020-02-20 ;
                }
              }
              ncd:revise-date 2019-04-16 ;
            }
            case v4-gen-lsp-bfd {
              if-feature gen-lsp-bfd ;
              description 'Generic LSP BFD.'
                          ;
              container v4-gen-lsp-bfd {
                description 'Generic LSP BFD.'
                            ;
                leaf ipv4 {
                  description 'IPv4 address for Generic LSP BFD.'
                              ;
                  type ncd:ipv4-address ;
                  mandatory true ;
                }
                leaf mask-length {
                  description 'IPv4 mask length for Generic LSP BFD.'
                              ;
                  type uint32 {
                    range 0..32 {
                      description 'IPv4 mask length for Generic LSP BFD.'
                                  ;
                    }
                  }
                  mandatory true ;
                }
                leaf vrf-name {
                  description 'VRF name for Generic LSP BFD.'
                              ;
                  type string {
                    length 1..32 {
                      description 'VRF name for Generic LSP BFD(1-32 characters'
                                + ').'
                                  ;
                    }
                  }
                }
                leaf ld {
                  description 'Local discriminator for Generic LSP BFD,the rang'
                            + 'e of this parameter depends on the device,defaul'
                            + 't range 1-4294967295.'
                              ;
                  type uint32 {
                    range 1..4294967295 {
                      description 'Local discriminator for Generic LSP BFD,the '
                                + 'range of this parameter depends on the devic'
                                + 'e,default range 1-4294967295.'
                                  ;
                    }
                  }
                }
                leaf rd {
                  description 'Remote discriminator for Generic LSP BFD.'
                              ;
                  type uint32 {
                    range 1..4294967295 {
                      description 'Remote discriminator for Generic LSP BFD.'
                                  ;
                    }
                  }
                }
                leaf source {
                  description 'IPv4 source address for Generic LSP BFD.'
                              ;
                  type ncd:ipv4-address-none-zero ;
                }
                container time-negotiation {
                  description 'Configure BFD time negotiation parameter.'
                              ;
                  leaf interval {
                    description 'BFD control packets TX interval in millisecond'
                              + 's, the range and default value of this paramet'
                              + 'er depends on the device, default range is 10-'
                              + '990, default value is 50.'
                                ;
                    type uint32 ;
                  }
                  leaf min-rx {
                    description 'BFD control packets min RX in milliseconds, th'
                              + 'e range and default value of this parameter de'
                              + 'pends on the device,default range is 10-990, d'
                              + 'efault value is 50.'
                                ;
                    type uint32 ;
                  }
                  leaf multiplier {
                    description 'BFD detect multiplier, the default value of th'
                              + 'is parameter depends on the device,  default i'
                              + 's 3.'
                                ;
                    type uint8 {
                      range 3..50 {
                        description 'BFD detect multiplier.'
                                    ;
                      }
                    }
                  }
                }
                leaf template-name {
                  if-feature template-for-session ;
                  description 'Template name.'
                              ;
                  type string {
                    length 1..31 ;
                  }
                }
              }
              ncd:revise-date 2020-07-07 ;
            }
          }
          container dscp {
            description 'Configure BFD packet DSCP value.'
                        ;
            leaf dscp {
              description 'Configure BFD packet DSCP value.'
                          ;
              type uint8 {
                range 0..63 {
                  description 'Configure BFD packet DSCP value.'
                              ;
                }
              }
              default 56 ;
            }
          }
          container cv-stop {
            description 'Configure BFD cv-stop strategy.'
                        ;
            leaf cv-stop {
              description 'Configure cv-stop strategy of BFD session.'
                          ;
              type enumeration {
                enum disable {
                  value 0 ;
                  description 'Close cv-stop strategy'
                              ;
                }
                enum enable {
                  value 1 ;
                  description 'Open cv-stop strategy'
                              ;
                }
              }
              default disable ;
            }
            ncd:revise-date 2016-11-23 ;
          }
          container admin-down-paras {
            if-feature session-admin-down ;
            description 'Administratively shutdown BFD session.'
                        ;
            leaf admin-down {
              description 'Administratively shutdown BFD session.'
                          ;
              type uint8 {
                range 1 {
                  description 'Administratively shutdown BFD session.'
                              ;
                }
              }
            }
            leaf notify-client {
              description 'If notify client admin-down when session down.'
                          ;
              type switch-set ;
              default disable ;
            }
            ncd:revise-date 2019-09-29 ;
          }
          container session-description {
            description 'The description of BFD session.'
                        ;
            leaf description {
              description 'The description of BFD session.'
                          ;
              type ncd:string-with-blank {
                length 1..80 {
                  description 'Max be 80 characters.'
                              ;
                }
              }
            }
            ncd:revise-date 2020-08-26 ;
          }
        }
      }
      container seamless-sessions {
        description 'Configure BFD instance parameters.'
                    ;
        list session {
          description 'Configure BFD instance parameters.'
                      ;
          key instance-name ;
          leaf instance-name {
            description 'Instance name for BFD session.'
                        ;
            type string {
              length 1..32 {
                description 'Instance name for BFD session.'
                            ;
              }
            }
          }
          choice detect-type {
            description 'Detect type for BFD session.'
                        ;
            mandatory true ;
            case rsvp-bfd {
              description 'RSVP TUNNEL BFD.'
                          ;
              container rsvp-bfd {
                description 'RSVP TUNNEL BFD.'
                            ;
                leaf tunnel-id {
                  description 'TE TunnelID for RSVP TUNNEL BFD,the range of thi'
                            + 's parameter depends on the device.'
                              ;
                  type uint32 {
                    range 1..4294967295 {
                      description 'TE TunnelID for RSVP TUNNEL BFD,the range of'
                                + ' this parameter depends on the device.'
                                  ;
                    }
                  }
                  mandatory true ;
                }
                leaf ld {
                  description 'Local discriminator for RSVP TUNNEL BFD,the rang'
                            + 'e of this parameter depends on the device,defaul'
                            + 't range 1-4294967295.'
                              ;
                  type uint32 {
                    range 1..4294967295 {
                      description 'Local discriminator for RSVP TUNNEL BFD,the '
                                + 'range of this parameter depends on the devic'
                                + 'e,default range 1-4294967295.'
                                  ;
                    }
                  }
                }
                leaf source-address {
                  description 'Local address for RSVP TUNNEL BFD.'
                              ;
                  type ncd:ipv4-address-none-zero ;
                }
                choice single-arm-echo {
                  description 'If single-arm echo enabled.'
                              ;
                  case enable {
                    description 'Enable single-arm echo.'
                                ;
                    leaf reverse-label {
                      description 'Reverse label.'
                                  ;
                      type uint32 {
                        range 16..1048575 {
                          description 'Reverse label.'
                                      ;
                        }
                      }
                    }
                  }
                  case disable {
                    description 'Disable single-arm echo.'
                                ;
                    leaf rd {
                      description 'Remote discriminator.'
                                  ;
                      type uint32 {
                        range 1..4294967295 {
                          description 'Remote discriminator for RSVP BFD.'
                                      ;
                        }
                      }
                    }
                  }
                }
                container time-negotiation {
                  description 'Configure BFD time negotiation parameter.'
                              ;
                  leaf interval {
                    description 'BFD control packets TX interval in millisecond'
                              + 's, the range and default value of this paramet'
                              + 'er depends on the device, default range is 10-'
                              + '990, default value is 50.'
                                ;
                    type uint32 ;
                  }
                  leaf min-rx {
                    description 'BFD control packets min RX in milliseconds, th'
                              + 'e range and default value of this parameter de'
                              + 'pends on the device, default range is 10-990, '
                              + 'default value is 50.'
                                ;
                    type uint32 ;
                  }
                  leaf multiplier {
                    description 'BFD detect multiplier, the default value of th'
                              + 'is parameter depends on the device,  default i'
                              + 's 3.'
                                ;
                    type uint8 {
                      range 3..50 {
                        description 'BFD detect multiplier.'
                                    ;
                      }
                    }
                  }
                }
                leaf template-name {
                  if-feature template-for-session ;
                  description 'Template name.'
                              ;
                  type string {
                    length 1..31 ;
                  }
                  ncd:revise-date 2020-02-20 ;
                }
              }
            }
            case v4-sr-be-bfd {
              container v4-sr-be-bfd {
                description 'SR BE BFD.'
                            ;
                leaf ipv4 {
                  description 'IPv4 address for SR BE BFD.'
                              ;
                  type ncd:ipv4-address ;
                  mandatory true ;
                }
                leaf mask-length {
                  description 'IPv4 mask length for SR BE BFD.'
                              ;
                  type uint32 {
                    range 0..32 {
                      description 'IPv4 mask length for SR BE BFD.'
                                  ;
                    }
                  }
                  mandatory true ;
                }
                leaf vrf-name {
                  description 'VRF name for SR BE BFD.'
                              ;
                  type string {
                    length 1..32 {
                      description 'VRF name for SR BE BFD(1-32 characters).'
                                  ;
                    }
                  }
                }
                leaf ld {
                  description 'Local discriminator for SR BE BFD,the range of t'
                            + 'his parameter depends on the device,default rang'
                            + 'e 1-4294967295.'
                              ;
                  type uint32 {
                    range 1..4294967295 {
                      description 'Local discriminator for SR BE BFD,the range '
                                + 'of this parameter depends on the device,defa'
                                + 'ult range 1-4294967295.'
                                  ;
                    }
                  }
                }
                leaf source {
                  description 'IPv4 source address for SR BE BFD.'
                              ;
                  type ncd:ipv4-address-none-zero ;
                }
                choice single-arm-echo {
                  description 'If single-arm echo enabled.'
                              ;
                  case enable {
                    description 'Enable single-arm echo.'
                                ;
                    leaf reverse-label {
                      description 'Reverse label.'
                                  ;
                      type uint32 {
                        range 16..1048575 {
                          description 'Reverse label.'
                                      ;
                        }
                      }
                    }
                  }
                  case disable {
                    description 'Disable single-arm echo.'
                                ;
                    leaf rd {
                      description 'Remote discriminator.'
                                  ;
                      type uint32 {
                        range 1..4294967295 {
                          description 'Remote discriminator for SR BE BFD.'
                                      ;
                        }
                      }
                    }
                  }
                }
                container time-negotiation {
                  description 'Configure BFD time negotiation parameter.'
                              ;
                  leaf interval {
                    description 'BFD control packets TX interval in millisecond'
                              + 's, the range and default value of this paramet'
                              + 'er depends on the device, default range is 10-'
                              + '990, default value is 50.'
                                ;
                    type uint32 ;
                  }
                  leaf min-rx {
                    description 'BFD control packets min RX in milliseconds, th'
                              + 'e range and default value of this parameter de'
                              + 'pends on the device,default range is 10-990, d'
                              + 'efault value is 50.'
                                ;
                    type uint32 ;
                  }
                  leaf multiplier {
                    description 'BFD detect multiplier, the default value of th'
                              + 'is parameter depends on the device,  default i'
                              + 's 3.'
                                ;
                    type uint8 {
                      range 3..50 {
                        description 'BFD detect multiplier.'
                                    ;
                      }
                    }
                  }
                }
                leaf template-name {
                  if-feature template-for-session ;
                  description 'Template name.'
                              ;
                  type string {
                    length 1..31 ;
                  }
                  ncd:revise-date 2020-02-20 ;
                }
              }
            }
            case srv6-te-bfd {
              container srv6-te-bfd {
                description 'SRv6 TUNNEL BFD.'
                            ;
                leaf tunnel-id {
                  description 'TE TunnelID for RSVP TUNNEL BFD,the range of thi'
                            + 's parameter depends on the device.'
                              ;
                  type uint32 {
                    range 1..4294967295 {
                      description 'TE TunnelID for RSVP TUNNEL BFD,the range of'
                                + ' this parameter depends on the device.'
                                  ;
                    }
                  }
                  mandatory true ;
                }
                leaf ld {
                  description 'Local discriminator for RSVP TUNNEL BFD,the rang'
                            + 'e of this parameter depends on the device,defaul'
                            + 't range 1-4294967295.'
                              ;
                  type uint32 {
                    range 1..4294967295 {
                      description 'Local discriminator for RSVP TUNNEL BFD,the '
                                + 'range of this parameter depends on the devic'
                                + 'e,default range 1-4294967295.'
                                  ;
                    }
                  }
                }
                leaf source-address {
                  description 'Local IPv6 address for RSVP TUNNEL BFD.'
                              ;
                  type ncd:ipv6-address-none-zero ;
                }
                choice single-arm-echo {
                  description 'If single-arm echo enabled.'
                              ;
                  case disable {
                    description 'Disable single-arm echo.'
                                ;
                    leaf rd {
                      description 'Remote discriminator.'
                                  ;
                      type uint32 {
                        range 1..4294967295 {
                          description 'Remote discriminator for SRv6 TUNNEL BFD.'
                                      ;
                        }
                      }
                    }
                  }
                }
                container time-negotiation {
                  description 'Configure BFD time negotiation parameter.'
                              ;
                  leaf interval {
                    description 'BFD control packets TX interval in millisecond'
                              + 's, the range and default value of this paramet'
                              + 'er depends on the device, default range is 10-'
                              + '990, default value is 50.'
                                ;
                    type uint32 ;
                  }
                  leaf min-rx {
                    description 'BFD control packets min RX in milliseconds, th'
                              + 'e range and default value of this parameter de'
                              + 'pends on the device, default range is 10-990, '
                              + 'default value is 50.'
                                ;
                    type uint32 ;
                  }
                  leaf multiplier {
                    description 'BFD detect multiplier, the default value of th'
                              + 'is parameter depends on the device,  default i'
                              + 's 3.'
                                ;
                    type uint8 {
                      range 3..50 {
                        description 'BFD detect multiplier.'
                                    ;
                      }
                    }
                  }
                }
                leaf template-name {
                  if-feature template-for-session ;
                  description 'Template name.'
                              ;
                  type string {
                    length 1..31 ;
                  }
                }
              }
              ncd:revise-date 2020-04-20 ;
            }
            case v4-gen-lsp-bfd {
              if-feature gen-lsp-bfd ;
              description 'Generic LSP BFD.'
                          ;
              container v4-gen-lsp-bfd {
                description 'Generic LSP BFD.'
                            ;
                leaf ipv4 {
                  description 'IPv4 address for Generic LSP BFD.'
                              ;
                  type ncd:ipv4-address ;
                  mandatory true ;
                }
                leaf mask-length {
                  description 'IPv4 mask length for Generic LSP BFD.'
                              ;
                  type uint32 {
                    range 0..32 {
                      description 'IPv4 mask length for Generic LSP BFD.'
                                  ;
                    }
                  }
                  mandatory true ;
                }
                leaf vrf-name {
                  description 'VRF name for Generic LSP BFD.'
                              ;
                  type string {
                    length 1..32 {
                      description 'VRF name for Generic LSP BFD(1-32 characters'
                                + ').'
                                  ;
                    }
                  }
                }
                leaf ld {
                  description 'Local discriminator for Generic LSP BFD,the rang'
                            + 'e of this parameter depends on the device,defaul'
                            + 't range 1-4294967295.'
                              ;
                  type uint32 {
                    range 1..4294967295 {
                      description 'Local discriminator for Generic LSP BFD,the '
                                + 'range of this parameter depends on the devic'
                                + 'e,default range 1-4294967295.'
                                  ;
                    }
                  }
                }
                leaf source {
                  description 'IPv4 source address for Generic LSP BFD.'
                              ;
                  type ncd:ipv4-address-none-zero ;
                }
                choice single-arm-echo {
                  description 'If single-arm echo enabled.'
                              ;
                  case disable {
                    description 'Disable single-arm echo.'
                                ;
                    leaf rd {
                      description 'Remote discriminator.'
                                  ;
                      type uint32 {
                        range 1..4294967295 {
                          description 'Remote discriminator for Generic LSP BFD.'
                                      ;
                        }
                      }
                    }
                  }
                }
                container time-negotiation {
                  description 'Configure BFD time negotiation parameter.'
                              ;
                  leaf interval {
                    description 'BFD control packets TX interval in millisecond'
                              + 's, the range and default value of this paramet'
                              + 'er depends on the device, default range is 10-'
                              + '990, default value is 50.'
                                ;
                    type uint32 ;
                  }
                  leaf min-rx {
                    description 'BFD control packets min RX in milliseconds, th'
                              + 'e range and default value of this parameter de'
                              + 'pends on the device,default range is 10-990, d'
                              + 'efault value is 50.'
                                ;
                    type uint32 ;
                  }
                  leaf multiplier {
                    description 'BFD detect multiplier, the default value of th'
                              + 'is parameter depends on the device,  default i'
                              + 's 3.'
                                ;
                    type uint8 {
                      range 3..50 {
                        description 'BFD detect multiplier.'
                                    ;
                      }
                    }
                  }
                }
                leaf template-name {
                  if-feature template-for-session ;
                  description 'Template name.'
                              ;
                  type string {
                    length 1..31 ;
                  }
                }
              }
              ncd:revise-date 2020-07-07 ;
            }
            case srv6-be-bfd {
              if-feature srv6-be ;
              container srv6-be-bfd {
                description 'SRv6 BE BFD.'
                            ;
                leaf peer-address {
                  description 'Peer address.'
                              ;
                  type ncd:ipv6-address-none-zero ;
                  mandatory true ;
                }
                leaf mask-length {
                  description 'Mask length for SRv6 BE BFD.'
                              ;
                  type uint32 {
                    range 1..128 {
                      description 'Mask length for SRv6 BE BFD.'
                                  ;
                    }
                  }
                  mandatory true ;
                  ncd:revise-date 2020-09-30 ;
                }
                leaf ld {
                  description 'Local discriminator for SRv6 BE BFD,the range of'
                            + ' this parameter depends on the device,default ra'
                            + 'nge 1-4294967295.'
                              ;
                  type uint32 {
                    range 1..4294967295 {
                      description 'Local discriminator for SR BE BFD,the range '
                                + 'of this parameter depends on the device,defa'
                                + 'ult range 1-4294967295.'
                                  ;
                    }
                  }
                }
                leaf rd {
                  description 'Remote discriminator.'
                              ;
                  type uint32 {
                    range 1..4294967295 {
                      description 'Remote discriminator for SRv6 BE BFD.'
                                  ;
                    }
                  }
                }
                leaf source {
                  description 'IPv6 source address.'
                              ;
                  type ncd:ipv6-address-none-zero ;
                }
                container time-negotiation {
                  description 'Configure BFD time negotiation parameter.'
                              ;
                  leaf interval {
                    description 'BFD control packets TX interval in millisecond'
                              + 's, the range and default value of this paramet'
                              + 'er depends on the device, default range is 10-'
                              + '990, default value is 50.'
                                ;
                    type uint32 ;
                  }
                  leaf min-rx {
                    description 'BFD control packets min RX in milliseconds, th'
                              + 'e range and default value of this parameter de'
                              + 'pends on the device,default range is 10-990, d'
                              + 'efault value is 50.'
                                ;
                    type uint32 ;
                  }
                  leaf multiplier {
                    description 'BFD detect multiplier, the default value of th'
                              + 'is parameter depends on the device,  default i'
                              + 's 3.'
                                ;
                    type uint8 {
                      range 3..50 {
                        description 'BFD detect multiplier.'
                                    ;
                      }
                    }
                  }
                }
                leaf template-name {
                  if-feature template-for-session ;
                  description 'Template name.'
                              ;
                  type string {
                    length 1..31 ;
                  }
                }
              }
              ncd:revise-date 2020-08-08 ;
            }
          }
          container dscp {
            description 'Configure BFD packet DSCP value.'
                        ;
            leaf dscp {
              description 'Configure BFD packet DSCP value.'
                          ;
              type uint8 {
                range 0..63 {
                  description 'Configure BFD packet DSCP value.'
                              ;
                }
              }
              default 56 ;
            }
          }
          container cv-stop {
            description 'Configure BFD cv-stop strategy.'
                        ;
            leaf cv-stop {
              description 'Configure cv-stop strategy of BFD session.'
                          ;
              type enumeration {
                enum disable {
                  value 0 ;
                  description 'Close cv-stop strategy'
                              ;
                }
                enum enable {
                  value 1 ;
                  description 'Open cv-stop strategy'
                              ;
                }
              }
              default disable ;
            }
          }
          container admin-down-paras {
            if-feature session-admin-down ;
            description 'Administratively shutdown BFD session.'
                        ;
            leaf admin-down {
              description 'Administratively shutdown BFD session.'
                          ;
              type uint8 {
                range 1 {
                  description 'Administratively shutdown BFD session.'
                              ;
                }
              }
            }
            leaf notify-client {
              description 'If notify client admin-down when session down.'
                          ;
              type switch-set ;
              default disable ;
            }
            ncd:revise-date 2019-09-29 ;
          }
          container session-description {
            description 'The description of seamless BFD session.'
                        ;
            leaf description {
              description 'The description of seamless BFD session.'
                          ;
              type ncd:string-with-blank {
                length 1..80 {
                  description 'Max be 80 characters.'
                              ;
                }
              }
            }
            ncd:revise-date 2020-08-26 ;
          }
        }
        ncd:revise-date 2019-05-31 ;
      }
      container interface-paras {
        description 'Configure BFD interface parameter.'
                    ;
        list interface-para {
          description 'Configure BFD interface parameter.'
                      ;
          key if-name ;
          leaf if-name {
            description 'Interface name for BFD. Only used for IPv4 and IPv6 li'
                      + 'nk BFD.'
                        ;
            type ncd:ifname {
              length 1..31 {
                description 'Interface name for BFD. Only used for IPv4 and IPv'
                          + '6 link BFD.'
                            ;
              }
            }
          }
          leaf interval {
            description 'BFD control packets TX interval in milliseconds,the ra'
                      + 'nge and default value of this parameter depends on the'
                      + ' device,default range 10-990, default value is 50.'
                        ;
            type uint32 ;
          }
          leaf min-rx {
            description 'BFD control packets min RX in milliseconds,the range a'
                      + 'nd default value of this parameter depends on the devi'
                      + 'ce,default range 10-990, default value is 50.'
                        ;
            type uint32 ;
          }
          leaf multiplier {
            description 'BFD detect multiplier, the default value of this param'
                      + 'eter depends on the device,  default is 3.'
                        ;
            type uint8 {
              range 3..50 {
                description 'BFD detect multiplier.'
                            ;
              }
            }
          }
          container single-arm-echo-paras {
            description 'Single-arm echo parameters.'
                        ;
            leaf ipv4-single-arm-echo {
              description 'If single-arm echo is enabled for IPv4 single-hop BF'
                        + 'D of this interface.'
                          ;
              type enumeration {
                enum disable {
                  value 0 ;
                  description 'Single-arm echo disabled.'
                              ;
                }
                enum enable {
                  value 1 ;
                  description 'Single-arm echo enabled.'
                              ;
                }
              }
              default disable ;
            }
            leaf ipv6-single-arm-echo {
              description 'If single-arm echo is enabled for IPv6 single-hop BF'
                        + 'D of this interface.'
                          ;
              type enumeration {
                enum disable {
                  value 0 ;
                  description 'Single-arm echo disabled.'
                              ;
                }
                enum enable {
                  value 1 ;
                  description 'Single-arm echo enabled.'
                              ;
                }
              }
              default disable ;
            }
            ncd:revise-date 2019-07-12 ;
          }
          container echo-paras {
            description 'Echo parameters.'
                        ;
            leaf min-echo-rx-interval {
              description 'BFD echo packets TX interval in milliseconds,the ran'
                        + 'ge depends on the device,default range 10-990.'
                          ;
              type uint32 ;
            }
            ncd:revise-date 2019-07-12 ;
          }
          container interface-description {
            description 'The description of interface.'
                        ;
            leaf description {
              description 'The description of interface.'
                          ;
              type ncd:string-with-blank {
                length 1..80 {
                  description 'Max be 80 characters.'
                              ;
                }
              }
            }
            ncd:revise-date 2020-08-26 ;
          }
        }
      }
      container ipv4-lag-para {
        description 'Configure global parameters of IPv4 lag-bfd.'
                    ;
        leaf ipv4-lag-src {
          description 'Configure global source address of IPv4 lag-bfd.'
                      ;
          type ncd:ipv4-address-none-zero ;
        }
        ncd:revise-date 2016-11-23 ;
      }
      container ipv6-lag-para {
        description 'Configure global parameters of IPv6 lag-bfd.'
                    ;
        leaf ipv6-lag-src {
          description 'Configure global source address of IPv6 lag-bfd.'
                      ;
          type ncd:ipv6-address ;
        }
        ncd:revise-date 2016-11-23 ;
      }
      container seamless-paras {
        description 'Configure parameters for Seamless BFD.'
                    ;
        container remote-target {
          description 'Configure the mapping of remote IP address and remote di'
                    + 'scriminator.'
                      ;
          container ipv4-remote-targets {
            description 'Configure the mapping of remote IPv4 address and remot'
                      + 'e discriminator.'
                        ;
            list ipv4-remote-target {
              description 'Configure the mapping of remote IPv4 address and rem'
                        + 'ote discriminator.'
                          ;
              key ipv4-address ;
              leaf ipv4-address {
                description 'IPv4 address.'
                            ;
                type ncd:ipv4-address-none-zero ;
              }
              leaf discriminator {
                description Discriminator. ;
                type uint32 {
                  range 1..4294967295 ;
                }
              }
            }
          }
          container ipv6-remote-targets {
            description 'Configure the mapping of remote IPv6 address and remot'
                      + 'e discriminator.'
                        ;
            list ipv6-remote-target {
              description 'Configure the mapping of remote IPv6 address and rem'
                        + 'ote discriminator.'
                          ;
              key ipv6-address ;
              leaf ipv6-address {
                description 'IPv6 address.'
                            ;
                type ncd:ipv6-address-none-zero ;
              }
              leaf discriminator {
                description Discriminator. ;
                type uint32 {
                  range 1..4294967295 ;
                }
              }
            }
            ncd:revise-date 2020-04-20 ;
          }
        }
        container reflector-source {
          description 'The source IP address of reflector.'
                      ;
          leaf ipv4-address {
            description 'IPv4 address.'
                        ;
            type ncd:ipv4-address-none-zero ;
          }
        }
        container reflector-source-ipv6 {
          description 'The IPv6 source address of reflector.'
                      ;
          leaf ipv6-address {
            description 'IPv6 address.'
                        ;
            type ncd:ipv6-address-none-zero ;
          }
          ncd:revise-date 2020-04-20 ;
        }
        container reflector-discriminator {
          description 'Configure reflector discriminator.'
                      ;
          container integer-discriminators {
            description 'Interger discriminators.'
                        ;
            list integer-discriminator {
              description 'Interger discriminators.'
                          ;
              key integer ;
              leaf integer {
                description 'Interger discriminators.'
                            ;
                type uint32 {
                  range 1..4294967295 {
                    description Discriminator ;
                  }
                }
              }
            }
          }
          container ipv4-discriminators {
            description 'IPv4 discriminators.'
                        ;
            list ipv4-discriminator {
              description 'IPv4 discriminators.'
                          ;
              key ipv4-address ;
              leaf ipv4-address {
                description 'IPv4 address.'
                            ;
                type ncd:ipv4-address-none-zero ;
              }
            }
          }
        }
        ncd:revise-date 2019-05-31 ;
      }
      container template-paras {
        description 'Configure BFD template parameter.'
                    ;
        list template-para {
          description 'Configure BFD template parameter.'
                      ;
          key template-name ;
          leaf template-name {
            description 'Template name for BFD.'
                        ;
            type string {
              length 1..31 {
                description 'Template name for BFD.'
                            ;
              }
            }
          }
          leaf interval {
            description 'BFD control packets TX interval in milliseconds,the ra'
                      + 'nge and default value of this parameter depends on the'
                      + ' device,default range 10-990.'
                        ;
            type uint32 ;
          }
          leaf min-rx {
            description 'BFD control packets min RX in milliseconds,the range a'
                      + 'nd default value of this parameter depends on the devi'
                      + 'ce,default range 10-990.'
                        ;
            type uint32 ;
          }
          leaf multiplier {
            description 'BFD detect multiplier, the default value of this param'
                      + 'eter depends on the device.'
                        ;
            type uint8 {
              range 3..50 {
                description 'BFD detect multiplier.'
                            ;
              }
            }
          }
          leaf location-policy {
            if-feature location-board ;
            description 'BFD location policy.'
                        ;
            type policy-set ;
            ncd:revise-date 2020-02-20 ;
          }
          container location-board {
            if-feature location-board ;
            description 'Configure BFD location board parameter.'
                        ;
            list board {
              description 'BFD location board.'
                          ;
              key name ;
              leaf name {
                description 'Location board name.'
                            ;
                type ncd:board {
                  length 1..31 ;
                }
              }
              leaf secondary {
                description 'Secondary board flag.'
                            ;
                type uint8 {
                  range 0..1 {
                    description 'Secondary flag'
                                ;
                  }
                }
                default 0 ;
              }
            }
            ncd:revise-date 2020-02-20 ;
          }
          leaf min-echo-rx-interval {
            description 'BFD echo packets TX interval in milliseconds,the range'
                      + ' depends on the device,default range 10-990.'
                        ;
            type uint32 ;
            ncd:revise-date 2020-07-11 ;
          }
          leaf dscp {
            description 'Configure BFD packet DSCP value.'
                        ;
            type uint8 {
              range 0..63 {
                description 'Configure BFD packet DSCP value.'
                            ;
              }
            }
            ncd:revise-date 2020-09-15 ;
          }
        }
        ncd:revise-date 2019-11-21 ;
      }
      container auto-sessions {
        description 'batch creating BFD sessions by protocols'
                    ;
        container sr-be-sbfd {
          description 'batch creating SR-BE seamless BFD sessions by protocols'
                      ;
          list sessions {
            description 'configuration instances of BFD sessions.'
                        ;
            key bfd-type ;
            leaf bfd-type {
              description 'the type of BFD sessions.'
                          ;
              type enumeration {
                enum MPLS-IPv4 {
                  value 1 ;
                  description 'MPLS IPv4 SR-BE SBFD'
                              ;
                }
                enum SRv6 {
                  value 2 ;
                  description 'SRv6 BE BFD'
                              ;
                }
              }
            }
            leaf ip-prefix-name {
              description 'IP prefix name.'
                          ;
              type string {
                length 1..169 ;
              }
            }
            leaf template-name {
              description 'template name of time parameters.'
                          ;
              type string {
                length 1..31 ;
              }
            }
            choice source-address {
              case ipv6-source {
                leaf ipv6-source {
                  description 'Source address for SRv6 BE BFD.'
                              ;
                  type ncd:ipv6-address-none-zero ;
                  ncd:revise-date 2020-10-14 ;
                }
              }
              case ipv4-source {
                leaf source {
                  description 'Source address for SR BE BFD.'
                              ;
                  type ncd:ipv4-address-none-zero ;
                  ncd:revise-date 2020-05-20 ;
                }
              }
            }
          }
        }
        ncd:revise-date 2020-03-24 ;
      }
    }
  }
  container state {
    config false ;
    description 'State model info.'
                ;
    container bfd {
      description 'BFD state information.'
                  ;
      container global {
        description 'Show BFD global information.'
                    ;
        list statistic {
          description 'Show statistics of BFD.'
                      ;
          key show-detect-type ;
          leaf show-detect-type {
            description 'Detect type for BFD session.'
                        ;
            type enumeration {
              enum all {
                value 1 ;
              }
              enum SingleHop {
                value 2 ;
              }
              enum MultiHop {
                value 3 ;
              }
              enum L2link {
                value 4 ;
              }
              enum LDP-Active {
                value 5 ;
              }
              enum LDP-Passive {
                value 6 ;
              }
              enum PwType {
                value 7 ;
              }
              enum RSVP-TUNNEL-Active {
                value 8 ;
              }
              enum RSVP-Passive {
                value 9 ;
              }
              enum RSVP-LSP-Active {
                value 10 ;
              }
              enum Lag {
                value 11 ;
              }
              enum SubSingleHop {
                value 12 ;
              }
              enum SrBe {
                value 13 ;
              }
              enum Mldp {
                value 14 ;
              }
              enum Mldp-Passive {
                value 15 ;
              }
              enum Mte {
                value 16 ;
              }
              enum Mte-Passive {
                value 17 ;
              }
              enum SrPath {
                value 18 ;
              }
              enum Srv6Te {
                value 19 ;
              }
              enum Srv6Lsp {
                value 20 ;
              }
              enum Srv6PolicySl {
                value 22 ;
              }
              enum Srv6Policy {
                value 23 ;
              }
              enum SrMplsPolicy {
                value 24 ;
              }
              enum MvpnBier {
                value 25 ;
              }
              enum MvpnBier-Passive {
                value 26 ;
              }
              enum GEN-LSP-Active {
                value 27 ;
              }
              enum GEN-LSP-Passive {
                value 28 ;
              }
              enum SrMplsPolicySL {
                value 29 ;
              }
              enum Srv6Be {
                value 21 ;
              }
              enum Srv6EvpnVpws {
                value 30 ;
              }
            }
          }
          leaf up-count {
            description 'The count of BFD session with state UP.'
                        ;
            type uint32 ;
          }
          leaf down-count {
            description 'The count of BFD session with state DOWN.'
                        ;
            type uint32 ;
          }
          leaf init-admin-count {
            description 'The count of BFD session with state INIT and ADMINDOWN.'
                        ;
            type uint32 ;
          }
          leaf total-count {
            description 'The count of BFD session.'
                        ;
            type uint32 ;
          }
          leaf device-total-num {
            description 'The MAX number of BFD session on device.'
                        ;
            type uint32 ;
          }
          leaf device-left-num {
            description 'The left number of BFD session can be configured.'
                        ;
            type uint32 ;
          }
        }
      }
      container session-results {
        description 'BFD session state information.'
                    ;
        list session-result {
          description 'BFD session state information.'
                      ;
          key 'ld instance-name'
              ;
          leaf ld {
            description 'Local discriminator for BFD session.'
                        ;
            type uint32 ;
          }
          leaf instance-name {
            description 'Instance name for BFD session.'
                        ;
            type string {
              length 0..32 {
                description 'Instance name for BFD session.'
                            ;
              }
            }
          }
          leaf rd {
            description 'Remote discriminator for BFD session.'
                        ;
            type uint32 ;
          }
          leaf bfd-detect-type {
            description 'Detail detect type for BFD session.'
                        ;
            type enumeration {
              enum SingleHop {
                value 0 ;
              }
              enum MultiHop {
                value 1 ;
              }
              enum LDP-Active {
                value 2 ;
              }
              enum LDP-Passive {
                value 3 ;
              }
              enum RSVP-TUNNEL-Active {
                value 4 ;
              }
              enum RSVP-LSP-Active {
                value 5 ;
              }
              enum RSVP-Passive {
                value 6 ;
              }
              enum PwType {
                value 7 ;
              }
              enum L2link {
                value 8 ;
              }
              enum Bidirection-RSVP-LSP {
                value 9 ;
              }
              enum Static-LDP {
                value 10 ;
              }
              enum Static-RSVP-TUNNEL {
                value 11 ;
              }
              enum Lag {
                value 12 ;
              }
              enum SubSingleHop {
                value 13 ;
              }
              enum SrBe {
                value 14 ;
              }
              enum Mldp {
                value 15 ;
              }
              enum Mldp-Passive {
                value 16 ;
              }
              enum Mte {
                value 17 ;
              }
              enum Mte-Passive {
                value 18 ;
              }
              enum SrPath {
                value 19 ;
              }
              enum Srv6Te {
                value 20 ;
              }
              enum Srv6Lsp {
                value 21 ;
              }
              enum Srv6PolicySl {
                value 23 ;
              }
              enum Srv6Policy {
                value 24 ;
              }
              enum SrMplsPolicy {
                value 25 ;
              }
              enum MvpnBier {
                value 26 ;
              }
              enum MvpnBier-Passive {
                value 27 ;
              }
              enum GEN-LSP-Active {
                value 28 ;
              }
              enum GEN-LSP-Passive {
                value 29 ;
              }
              enum SrMplsPolicySL {
                value 30 ;
              }
              enum Srv6Be {
                value 22 ;
              }
              enum Srv6EvpnVpws {
                value 31 ;
              }
            }
          }
          leaf protocol-type {
            description 'Protocol type for BFD session.'
                        ;
            type ncd:string-with-blank {
              length 0..128 {
                description 'Protocol type for BFD session.'
                            ;
              }
            }
          }
          leaf state {
            description 'State for BFD session.'
                        ;
            type enumeration {
              enum ADMINDOWN {
                value 0 ;
              }
              enum DOWN {
                value 1 ;
              }
              enum INIT {
                value 2 ;
              }
              enum UP {
                value 3 ;
              }
            }
          }
          leaf local-address {
            description 'Local address for SingleHop,SubSingleHop, MultiHop ,SR'
                      + 'v6 BE BFD session. Root address for MLDP,MTE BFD sessi'
                      + 'on.'
                        ;
            type string {
              length 0..47 {
                description 'Local address for BFD session.'
                            ;
              }
            }
          }
          leaf remote-address {
            description 'Remote address for SingleHop,SubSingleHop, MultiHop,RS'
                      + 'VP-TUNNEL-Active,Static-RSVP-TUNNEL,RSVP-LSP-Active,Bi'
                      + 'direction-RSVP-LSP,L2link,Lag,SRv6 BE BFD sessions. ex'
                      + 'tend tunnle id for MLDP,MTE BFD BFD passive sessions.'
                        ;
            type string {
              length 0..47 {
                description 'Remote address for BFD session.'
                            ;
              }
            }
          }
          leaf if-name {
            description 'Output interface for BFD session.'
                        ;
            type string {
              length 0..32 {
                description 'Output interface for BFD session.'
                            ;
              }
            }
          }
          leaf vrf-name {
            description 'VRF name for BFD session.'
                        ;
            type string {
              length 0..36 {
                description 'VRF name for BFD session.'
                            ;
              }
            }
          }
          leaf fec-address {
            description 'FEC address for LDP/SR BE/generic BFD.'
                        ;
            type string ;
          }
          leaf mask-length {
            description 'Mask length.'
                        ;
            type uint8 ;
          }
          leaf tunnel-id {
            description 'TE TunnelID for RSVP BFD.'
                        ;
            type uint32 ;
          }
          leaf lsp-id {
            description 'Lspid for RSVP LSP BFD.'
                        ;
            type uint16 ;
          }
          leaf lsp-role {
            description 'Lsp role for RSVP LSP BFD,include maste and slave.'
                        ;
            type enumeration {
              enum --- {
                value 0 ;
              }
              enum master {
                value 1 ;
              }
              enum slave {
                value 2 ;
              }
            }
          }
          leaf pw-name {
            description 'PW name for PW BFD.'
                        ;
            type string {
              length 0..32 {
                description 'PW name for PW BFD.'
                            ;
              }
            }
          }
          leaf pw-ttl {
            description 'PW TTL value for PW BFD.'
                        ;
            type uint16 ;
          }
          leaf rx-count {
            description 'Count of received BFD Control packets.'
                        ;
            type uint32 ;
          }
          leaf tx-count {
            description 'Count of transmitting BFD Control packets.'
                        ;
            type uint32 ;
          }
          leaf up-time {
            description 'Time of BFD session at UP states.'
                        ;
            type ncd:string-with-blank {
              length 0..63 {
                description 'Time of BFD session at UP states.'
                            ;
              }
            }
          }
          leaf local-diag {
            description "Local system's reason for the last change in BFD sessi"
                      + "on state."
                        ;
            type uint32 ;
          }
          leaf min-tx-interval {
            description 'Minimum interval of transmitting BFD Control packets.'
                        ;
            type uint32 ;
          }
          leaf max-tx-interval {
            description 'Maximum interval of transmitting BFD Control packets.'
                        ;
            type uint32 ;
          }
          leaf avg-tx-interval {
            description 'Average interval values of transmitting BFD Control pa'
                      + 'ckets.'
                        ;
            type uint32 ;
          }
          leaf min-rx-interval {
            description 'Minimum interval of received BFD Control packets.'
                        ;
            type uint32 ;
          }
          leaf max-rx-interval {
            description 'Maximum interval of received BFD Control packets.'
                        ;
            type uint32 ;
          }
          leaf avg-rx-interval {
            description 'Average interval values of received BFD Control packet'
                      + 's.'
                        ;
            type uint32 ;
          }
          leaf local-tx {
            description "Local system's interval of transmitting BFD Control pa"
                      + "ckets."
                        ;
            type uint32 ;
          }
          leaf local-rx {
            description "Local system's interval of received BFD Control packet"
                      + "s."
                        ;
            type uint32 ;
          }
          leaf local-multiplier {
            description "Local system's detection time multiplier."
                        ;
            type uint8 ;
          }
          leaf received-tx {
            description "Remote system's interval of transmitting BFD Control p"
                      + "ackets."
                        ;
            type uint32 ;
          }
          leaf received-rx {
            description "Remote system's interval of received BFD Control packe"
                      + "ts."
                        ;
            type uint32 ;
          }
          leaf received-multiplier {
            description "Remote system's detection time multiplier."
                        ;
            type uint8 ;
          }
          leaf p-bit {
            description "Local system's poll bit."
                        ;
            type uint8 ;
          }
          leaf f-bit {
            description "Local system's final bit."
                        ;
            type uint8 ;
          }
          leaf hold-down {
            description "Local system's holding Down time."
                        ;
            type uint32 ;
          }
          leaf dest-udpport {
            description 'UDP destination port of BFD session.'
                        ;
            type uint16 ;
          }
          leaf rcv-phyif {
            description 'Physical interface name of receiving packets by contro'
                      + 'l plane.'
                        ;
            type string {
              length 0..31 {
                description 'Physical interface name of receiving packets by co'
                          + 'ntrol plane.'
                            ;
              }
            }
          }
          leaf summary-detect-type {
            description 'Summary detect type for BFD session.'
                        ;
            type enumeration {
              enum ip {
                value 0 ;
              }
              enum ldp {
                value 1 ;
              }
              enum rsvp {
                value 2 ;
              }
              enum l2 {
                value 3 ;
              }
              enum pw {
                value 4 ;
              }
              enum lag {
                value 5 ;
              }
              enum srbe {
                value 6 ;
              }
              enum mldp {
                value 7 ;
              }
              enum mte {
                value 8 ;
              }
              enum srpath {
                value 9 ;
              }
              enum Srv6Te {
                value 10 ;
              }
              enum Srv6Lsp {
                value 11 ;
              }
              enum Srv6PolicySl {
                value 13 ;
              }
              enum Srv6Policy {
                value 14 ;
              }
              enum SrMplsPolicy {
                value 15 ;
              }
              enum MvpnBier {
                value 16 ;
              }
              enum GEN-LSP {
                value 17 ;
              }
              enum SrMplsPolicySL {
                value 18 ;
              }
              enum Srv6Be {
                value 12 ;
              }
              enum Srv6EvpnVpws {
                value 19 ;
              }
            }
          }
          leaf leaf-id {
            description 'Leaf id for MTE/MLDP BFD.'
                        ;
            type uint32 ;
            ncd:revise-date 2019-05-20 ;
          }
          leaf opaque-type {
            description 'MLDP Opaque type'
                        ;
            type enumeration {
              enum Tunnel-Id {
                value 1 ;
              }
              enum Invalid {
                value 0 ;
              }
            }
            ncd:revise-date 2019-05-20 ;
          }
          leaf p2mp-id {
            description 'P2MP ID  for MTE.'
                        ;
            type uint32 ;
            ncd:revise-date 2019-05-20 ;
          }
          leaf seamless-mode {
            description 'If BFD is seamless.'
                        ;
            type enumeration {
              enum disable {
                value 0 ;
                description 'Seamless disable.'
                            ;
              }
              enum enable {
                value 1 ;
                description 'Seamless enable.'
                            ;
              }
            }
            ncd:revise-date 2019-05-31 ;
          }
          leaf seamless-role {
            description 'The role of Seamless BFD.'
                        ;
            type enumeration {
              enum Invalid {
                value 0 ;
                description 'Not seamless.'
                            ;
              }
              enum Initiator {
                value 1 ;
                description Initiator ;
              }
              enum Reflector {
                value 2 ;
                description Reflector ;
              }
            }
            ncd:revise-date 2019-05-31 ;
          }
          leaf detect-mode {
            description 'Actual detect mode.'
                        ;
            type detect-mode ;
            ncd:revise-date 2019-07-12 ;
          }
          leaf path-id {
            description 'PATH ID for SR-PATH.'
                        ;
            type uint32 ;
            ncd:revise-date 2019-11-21 ;
          }
          leaf path-index {
            description 'PATH INDEX for SR-PATH.'
                        ;
            type uint32 ;
            ncd:revise-date 2020-02-20 ;
          }
          leaf path-type {
            description 'PATH TYPE for SR-PATH.'
                        ;
            type string ;
            ncd:revise-date 2020-02-20 ;
          }
          leaf template-name {
            if-feature location-board ;
            description 'Template name.'
                        ;
            type string {
              length 1..31 {
                description 'Template name.'
                            ;
              }
            }
            ncd:revise-date 2020-02-20 ;
          }
          leaf working-board {
            if-feature location-board ;
            description 'Working Board name.'
                        ;
            type string {
              length 1..31 {
                description 'Working board Name.'
                            ;
              }
            }
            ncd:revise-date 2020-02-20 ;
          }
          leaf standby-board {
            if-feature location-board ;
            description 'Standby board name.'
                        ;
            type string {
              length 1..31 {
                description 'Protect board name.'
                            ;
              }
            }
            ncd:revise-date 2020-02-20 ;
          }
          leaf sub-domain-id {
            description 'Sub-domain ID.'
                        ;
            type uint8 ;
            ncd:revise-date 2020-07-02 ;
          }
          leaf bfr-id {
            description 'Bit-Forwarding Router ID.'
                        ;
            type uint16 ;
            ncd:revise-date 2020-07-02 ;
          }
          leaf mpls-label {
            description 'mpls label.'
                        ;
            type uint32 ;
            ncd:revise-date 2020-07-02 ;
          }
          ncd:select ld ;
          ncd:select summary-detect-type ;
          ncd:select 'local-address remote-address summary-detect-type'
                     ;
          ncd:select 'fec-address summary-detect-type'
                     ;
          ncd:select 'tunnel-id summary-detect-type'
                     ;
          ncd:select 'if-name summary-detect-type'
                     ;
          ncd:select 'pw-name summary-detect-type'
                     ;
          ncd:select 'ld instance-name'
                     ;
          ncd:select 'summary-detect-type path-id'
                     ;
          ncd:select 'summary-detect-type sub-domain-id bfr-id'
                     ;
        }
      }
    }
  }
  notification notification-bfd-sessions {
    description 'Notification of BFD sessions.'
                ;
    container bfd-sessions {
      config false ;
      description 'Notification of BFD sessions.'
                  ;
      list bfd-session {
        description 'The detail notification information of BFD session.'
                    ;
        key 'ld instance-name'
            ;
        leaf ld {
          description 'Local discriminator for BFD session.'
                      ;
          type uint32 ;
        }
        leaf instance-name {
          description 'Instance name for BFD session.'
                      ;
          type string {
            length 0..32 {
              description 'Instance name for BFD session.'
                          ;
            }
          }
        }
        leaf rd {
          description 'Remote discriminator for BFD session.'
                      ;
          type uint32 ;
        }
        leaf protocol-type {
          description 'Protocol type for BFD session.'
                      ;
          type ncd:string-with-blank {
            length 0..128 {
              description 'Protocol type for BFD session.'
                          ;
            }
          }
        }
        leaf detect-type {
          description 'Detail detect type for BFD session.'
                      ;
          type enumeration {
            enum SingleHop {
              value 0 ;
            }
            enum MultiHop {
              value 1 ;
            }
            enum LDP-Active {
              value 2 ;
            }
            enum LDP-Passive {
              value 3 ;
            }
            enum RSVP-TUNNEL-Active {
              value 4 ;
            }
            enum RSVP-LSP-Active {
              value 5 ;
            }
            enum RSVP-Passive {
              value 6 ;
            }
            enum PwType {
              value 7 ;
            }
            enum L2link {
              value 8 ;
            }
            enum Bidirection-RSVP-LSP {
              value 9 ;
            }
            enum Static-LDP {
              value 10 ;
            }
            enum Static-RSVP-TUNNEL {
              value 11 ;
            }
            enum Lag {
              value 12 ;
            }
            enum SubSingleHop {
              value 13 ;
            }
            enum SrBe {
              value 14 ;
            }
            enum Mldp {
              value 15 ;
            }
            enum Mldp-Passive {
              value 16 ;
            }
            enum Mte {
              value 17 ;
            }
            enum Mte-Passive {
              value 18 ;
            }
            enum SrPath {
              value 19 ;
            }
            enum Srv6Te {
              value 20 ;
            }
            enum Srv6Lsp {
              value 21 ;
            }
            enum Srv6PolicySl {
              value 23 ;
            }
            enum Srv6Policy {
              value 24 ;
            }
            enum SrMplsPolicy {
              value 25 ;
            }
            enum MvpnBier {
              value 26 ;
            }
            enum MvpnBier-Passive {
              value 27 ;
            }
            enum GEN-LSP-Active {
              value 28 ;
            }
            enum GEN-LSP-Passive {
              value 29 ;
            }
            enum SrMplsPolicySL {
              value 30 ;
            }
            enum Srv6Be {
              value 22 ;
            }
            enum Srv6EvpnVpws {
              value 31 ;
            }
          }
        }
        leaf state {
          description 'State for BFD session.'
                      ;
          type enumeration {
            enum ADMINDOWN {
              value 0 ;
            }
            enum DOWN {
              value 1 ;
            }
            enum INIT {
              value 2 ;
            }
            enum UP {
              value 3 ;
            }
          }
        }
        leaf local-diag {
          description "Local system's reason for the last change in BFD session"
                    + " state."
                      ;
          type uint32 ;
        }
        leaf delete-flag {
          description 'If BFD session delete or not.'
                      ;
          type boolean ;
          default false ;
        }
        leaf down-reason {
          description 'Down reason of BFD session.'
                      ;
          type enumeration {
            enum RCV_ADMINDOWN {
              value 0 ;
            }
            enum LP_OFF_LINE {
              value 1 ;
            }
            enum INTERFACE_DELETE {
              value 2 ;
            }
            enum FAIL_TO_CHOOSE_BOARD {
              value 3 ;
            }
            enum FTM_UP_DOWN {
              value 4 ;
            }
            enum DETECT_TIME_OUT {
              value 5 ;
            }
            enum UP_RCV_DOWN {
              value 6 ;
            }
            enum LINKLOCAL_DELETE {
              value 7 ;
            }
            enum V6INTERFACE_DISABLE {
              value 8 ;
            }
            enum AC_DOWN {
              value 9 ;
            }
            enum STATE_REROLL {
              value 10 ;
            }
            enum INTERFACE_NOT_SUPPORT {
              value 11 ;
            }
            enum CREATE_BUT_NOT_UP {
              value 12 ;
            }
            enum AUTH_CHANGE {
              value 13 ;
            }
            enum SHUT_DOWN {
              value 14 ;
            }
            enum SUB_SESSION_DOWN {
              value 15 ;
            }
            enum SUB_SESSION_DELETE {
              value 16 ;
            }
            enum FTM_FIRST_PKT_TIMEOUT {
              value 17 ;
            }
          }
        }
        leaf local-address {
          description 'Local address for SingleHop,SubSingleHop, MultiHop BFD s'
                    + 'ession. Root address for MLDP,MTE BFD session.'
                      ;
          type string {
            length 0..47 {
              description 'Local address for BFD session.'
                          ;
            }
          }
        }
        leaf remote-address {
          description 'Remote address for SingleHop,SubSingleHop, MultiHop,RSVP'
                    + '-TUNNEL-Active,Static-RSVP-TUNNEL,RSVP-LSP-Active,Bidire'
                    + 'ction-RSVP-LSP,L2link,Lag BFD sessions. extend tunnle id'
                    + ' for MLDP,MTE BFD BFD passive sessions.'
                      ;
          type string {
            length 0..47 {
              description 'Remote address for BFD session.'
                          ;
            }
          }
        }
        leaf if-name {
          description 'Output interface for BFD session.'
                      ;
          type string {
            length 0..32 {
              description 'Output interface for BFD session.'
                          ;
            }
          }
        }
        leaf vrf-name {
          description 'VRF name for BFD session.'
                      ;
          type string {
            length 0..36 {
              description 'VRF name for BFD session.'
                          ;
            }
          }
        }
        leaf fec-address {
          description 'FEC address for LDP BFD.'
                      ;
          type string ;
        }
        leaf mask-length {
          description 'Mask length.'
                      ;
          type uint8 ;
        }
        leaf tunnel-id {
          description 'TE TunnelID for RSVP BFD.'
                      ;
          type uint32 ;
        }
        leaf lsp-id {
          description 'Lspid for RSVP LSP BFD.'
                      ;
          type uint16 ;
        }
        leaf lsp-role {
          description 'Lsp role for RSVP LSP BFD,include maste and slave.'
                      ;
          type enumeration {
            enum --- {
              value 0 ;
            }
            enum master {
              value 1 ;
            }
            enum slave {
              value 2 ;
            }
          }
        }
        leaf pw-name {
          description 'PW name for PW BFD.'
                      ;
          type string {
            length 0..32 {
              description 'PW name for PW BFD.'
                          ;
            }
          }
        }
        leaf pw-ttl {
          description 'PW TTL value for PW BFD.'
                      ;
          type uint16 ;
        }
        leaf leaf-id {
          description 'Leaf id for MTE/MLDP BFD.'
                      ;
          type uint32 ;
          ncd:revise-date 2019-05-20 ;
        }
        leaf opaque-type {
          description 'MLDP Opaque type.'
                      ;
          type enumeration {
            enum Tunnel-Id {
              value 1 ;
            }
            enum Invalid {
              value 0 ;
            }
          }
          ncd:revise-date 2019-05-20 ;
        }
        leaf p2mp-id {
          description 'P2MP ID  for MTE.'
                      ;
          type uint32 ;
          ncd:revise-date 2019-05-20 ;
        }
        leaf path-id {
          description 'PATH ID for SR-PATH.'
                      ;
          type uint32 ;
          ncd:revise-date 2019-11-21 ;
        }
        leaf path-index {
          description 'PATH INDEX for SR-PATH.'
                      ;
          type uint32 ;
          ncd:revise-date 2020-02-20 ;
        }
        leaf path-type {
          description 'PATH TYPE for SR-PATH.'
                      ;
          type string ;
          ncd:revise-date 2020-02-20 ;
        }
        leaf sub-domain-id {
          description 'Sub-domain ID.'
                      ;
          type uint8 ;
          ncd:revise-date 2020-07-02 ;
        }
        leaf bfr-id {
          description 'Bit-Forwarding Router ID.'
                      ;
          type uint16 ;
          ncd:revise-date 2020-07-02 ;
        }
        leaf mpls-label {
          description 'mpls label.'
                      ;
          type uint32 ;
          ncd:revise-date 2020-07-02 ;
        }
      }
    }
    ncd:revise-date 2016-11-23 ;
  }
}
