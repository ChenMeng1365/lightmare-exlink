module zxr10-pm-license {
  namespace 'http://www.zte.com.cn/zxr10/netconf/schema/rosng/pm-license'
            ;
  prefix pm-license ;
  import zxr10-netconf-defs {
    prefix ncd ;
  }
  organization 'ZTE Corporation'
               ;
  contact 'ZTE Corporation'+"\n"
        + '   Nanjing Institute of ZTE Corporation'+"\n"
        + '   No.68 Zijinghua Rd. Yuhuatai District, Nanjing, China'+"\n"
        + '   Tel: +86-25-52870000'
          ;
  revision 2021-01-28 {
    description 'Initial version.'
                ;
  }
  container configuration {
    container ports {
      container active-ports {
        list active-port {
          key 'shelf slot subslot portno restype itemname'
              ;
          leaf shelf {
            type uint8 ;
          }
          leaf slot {
            type uint8 ;
          }
          leaf subslot {
            type uint8 ;
          }
          leaf portno {
            type uint32 ;
          }
          leaf restype {
            type uint16 ;
          }
          leaf itemname {
            type string {
              length 1..64 ;
            }
          }
          leaf activeflag {
            type enumeration {
              enum active {
                value 1 ;
              }
              enum inactive {
                value 0 ;
              }
            }
            default inactive ;
          }
        }
      }
    }
  }
}
