module zxr10-pm-interface {
  namespace 'http://www.zte.com.cn/zxr10/netconf/schema/rosng/pm-interface'
            ;
  prefix pm-interface ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2021-04-19 {
    description 'add flexe dcn overhead.'
                ;
  }
  revision 2021-01-28 {
    description 'Modify the range of holdtime value.'
                ;
  }
  revision 2021-01-11 {
    description 'add laser-status invalid mode.'
                ;
  }
  revision 2021-01-05 {
    description 'add flow control on threshold'
                ;
  }
  revision 2020-09-21 {
    description 'add MTN leaf'
                ;
  }
  revision 2020-09-14 {
    description 'add single-fiber and link-force'
                ;
  }
  revision 2020-06-12 {
    description 'add eth speed mode "speed-auto"'
                ;
  }
  revision 2020-04-28 {
    description 'Add create-vsgs.'
                ;
  }
  revision 2020-04-01 {
    description 'add enum speed-25G, speed-40G, speed-50G and speed-100G in lea'
              + 'f ulei speed.'
                ;
  }
  revision 2020-02-25 {
    description 'Add container eee-statisticss,clear-eee-statisticss,control-fl'
              + 'ap,control-flap-clears,eee-config and optical-inform-monitor.'
                ;
  }
  revision 2020-02-15 {
    description 'Add contain split.'
                ;
  }
  revision 2019-06-25 {
    description 'add fec-eth and fec-bypass add center-frequency and obsolete c'
              + 'enter-freq.'
                ;
  }
  revision 2019-05-10 {
    description 'add leaf loopback.'
                ;
  }
  revision 2019-03-05 {
    description 'add optical module config.'
                ;
  }
  revision 2018-12-12 {
    description 'jumbo add.'
                ;
  }
  revision 2018-11-14 {
    description 'add work-mode'
                ;
  }
  revision 2018-09-17 {
    description 'ipg add perfcode.'
                ;
  }
  revision 2018-09-08 {
    description 'add ipg container delete2reset and modify default value.'
                ;
  }
  revision 2018-09-06 {
    description 'add port-speed.'
                ;
  }
  revision 2018-09-03 {
    description 'add enum speed-25G and speed-50G in leaf speed.'
                ;
  }
  revision 2018-08-16 {
    description 'add port-status.'
                ;
  }
  revision 2018-07-25 {
    description 'add laser off-reason and modify current-status.'
                ;
  }
  revision 2018-07-01 {
    description 'add gfp-mplss.'
                ;
  }
  revision 2018-06-28 {
    description 'add laser-status and loopback-auto-cancel.'
                ;
  }
  revision 2018-05-28 {
    description 'add ifhaslos.'
                ;
  }
  revision 2018-05-24 {
    description 'add loopback time.'
                ;
  }
  revision 2018-03-09 {
    description 'add rf2sf and ipg.'
                ;
  }
  revision 2017-10-16 {
    description 'add laser-status.'
                ;
  }
  revision 2017-08-01 {
    description 'add alarm insert sd.'
                ;
  }
  revision 2017-06-02 {
    description 'add leaf trace-64-value to pos j0 and j0ex'
                ;
  }
  revision 2016-11-18 {
    description 'add loopback-external'
                ;
  }
  revision 2016-09-26 {
    description 'leaf loopback modify type for eths wans poss and atms.'
                ;
  }
  revision 2016-09-10 {
    description 'list port-mode add leaf xgei-gei, leaf lan-wan add parameter p'
              + 'os3 and pos12, leaf pos3-pos12 add parameter lan, wan and gei.'
                ;
  }
  revision 2016-08-10 {
    description 'add alarm-insert-hp and alarm-insert-ms for atms and poss'
                ;
  }
  revision 2016-04-15 {
    description 'modify the range of link-delay-up and link-delay-down from 0 t'
              + 'o 600000.'
                ;
  }
  revision 2016-03-15 {
    description 'add b2-sd-ber b2-sf-ber to sdh-threshold, only for atm'
                ;
  }
  revision 2016-02-29 {
    description 'modify contain threshold-sd-fers leaf occur-exponent and clear'
              + '-exponent range 1 to 9'
                ;
  }
  revision 2016-01-20 {
    description 'Add leaf speed-100G and modify the value of speed-40G.'
                ;
  }
  revision 2015-12-31 {
    description 'modify atm flag c2/c2ex default value'+"\n"
              + 'modify pos clock-mode default value'
                ;
  }
  revision 2015-12-17 {
    description 'leaf recovery-mode add parameter laser-on add laser-off.'
                ;
  }
  revision 2015-09-06 {
    description 'add contain sdh-thresholds'
                ;
  }
  feature optical-module-config ;
  feature flow-control-threshold ;
  container configuration {
    container pm-if {
      container eths {
        list eth {
          description 'Ethernet interface mode.'
                      ;
          key if-name ;
          leaf if-name {
            description 'Interface name.'
                        ;
            type string ;
          }
          leaf holdtime {
            description 'Configures the port hold-time.'
                        ;
            type uint16 {
              range 0..3600 {
                description 'Range: 0-3600.'
                            ;
              }
            }
            units second ;
            default 120 ;
          }
          leaf negotiation {
            description 'Configures the port negotiation mode.'
                        ;
            type enumeration {
              enum negotiation-force {
                value 1 ;
                description 'Force negotiation mode.'
                            ;
              }
              enum negotiation-auto {
                value 2 ;
                description 'Auto negotiation mode.'
                            ;
              }
            }
            default negotiation-auto ;
          }
          leaf speed {
            description 'Configures the rate of a port.'
                        ;
            type enumeration {
              enum speed-10M {
                value 1 ;
                description 'Port speed is 10M.'
                            ;
              }
              enum speed-100M {
                value 2 ;
                description 'Port speed is 100M.'
                            ;
              }
              enum speed-1G {
                value 3 ;
                description 'Port speed is 1G.'
                            ;
              }
              enum speed-10G {
                value 4 ;
                description 'Port speed is 10G.'
                            ;
              }
              enum speed-25G {
                value 10 ;
                description 'Port speed is 25G.'
                            ;
              }
              enum speed-40G {
                value 5 ;
                description 'Port speed is 40G.'
                            ;
              }
              enum speed-50G {
                value 11 ;
                description 'Port speed is 50G.'
                            ;
              }
              enum speed-100G {
                value 6 ;
                description 'Port speed is 100G.'
                            ;
              }
              enum speed-200G {
                value 12 ;
                description 'Port speed is 200G.'
                            ;
              }
              enum speed-400G {
                value 13 ;
                description 'Port speed is 400G.'
                            ;
              }
              enum speed-auto {
                value 15 ;
                description 'Port speed is configured to auto, the real speed d'
                          + 'epend on optical module.'
                            ;
              }
            }
            default speed-1G ;
          }
          leaf duplex {
            description 'Configures the Ethernet working mode.'
                        ;
            type enumeration {
              enum duplex-full {
                value 1 ;
                description 'Full duplex mode.'
                            ;
              }
              enum duplex-half {
                value 2 ;
                description 'Half duplex mode.'
                            ;
              }
            }
            default duplex-full ;
          }
          leaf loopback {
            description 'Configures the loopback method of a port.'
                        ;
            type enumeration {
              enum cancel {
                value 0 ;
                description 'Cancel loopback mode.'
                            ;
              }
              enum outer {
                value 1 ;
                description 'Line loopback mode.'
                            ;
              }
              enum inner {
                value 2 ;
                description 'Inner loopback mode.'
                            ;
              }
              enum external {
                value 3 ;
                description 'External loopback mode.'
                            ;
              }
            }
            default cancel ;
          }
          leaf mdimode {
            description 'Configures the MDI/MDI-X function.'
                        ;
            type enumeration {
              enum mdimode-mdix {
                value 1 ;
                description 'Switch port to straight-through mode.'
                            ;
              }
              enum mdimode-mdi {
                value 2 ;
                description 'Switch port to crossover mode.'
                            ;
              }
              enum mdimode-auto {
                value 3 ;
                description 'Switch port to auto-cross mode.'
                            ;
              }
            }
            default mdimode-auto ;
          }
          leaf pemode {
            description 'Configures the copper-fiber attribute of a port.'
                        ;
            type enumeration {
              enum media-copper {
                value 1 ;
                description 'The PEMode of the port is electric.'
                            ;
              }
              enum media-fiber {
                value 2 ;
                description 'The PEMode of the port is optical.'
                            ;
              }
            }
            default media-fiber ;
          }
          leaf threshold-error-packet {
            description 'Sets the alarm threshold for port errors.'
                        ;
            type uint16 {
              range 1..65535 {
                description 'The number of error packets.'
                            ;
              }
            }
            default 3 ;
          }
          leaf unidirection {
            description 'Configures an unframing channel.'
                        ;
            type enumeration {
              enum disable {
                value 1 ;
                description 'Unidirection disable.'
                            ;
              }
              enum enable {
                value 2 ;
                description 'Unidirection enable'
                            ;
              }
            }
            default disable ;
          }
          leaf rf2sf {
            description 'Configures rf2sf.'
                        ;
            type enumeration {
              enum enable {
                value 1 ;
                description 'rf2sf enable'
                            ;
              }
              enum disable {
                value 0 ;
                description 'rf2sf diable'
                            ;
              }
            }
            default enable ;
            ncd:revise-date 2018-03-09 ;
          }
          container laser-status {
            leaf status {
              description 'Open/close laser or set recover mode of ALS status.'
                          ;
              type enumeration {
                enum on {
                  value 1 ;
                  description 'Open laser.'
                              ;
                }
                enum off {
                  value 2 ;
                  description 'Close laser.'
                              ;
                }
                enum auto-recovery {
                  value 3 ;
                  description 'Set recover mode is auto-recovery.'
                              ;
                }
                enum manual-recovery {
                  value 4 ;
                  description 'Set recover mode is manual-recovery.'
                              ;
                }
                enum invalid {
                  value 0 ;
                  description 'The invalid value of laser-status mode.'
                              ;
                }
              }
              default on ;
            }
            leaf period {
              description 'Start period of automatic.'
                          ;
              type uint16 {
                range 20..600 {
                  description 'Range: 20-600.'
                              ;
                }
              }
              units second ;
              default 100 ;
            }
            leaf pulsewidth {
              description 'Start pulse wide of automatic.'
                          ;
              type uint8 {
                range 1..20 {
                  description 'Range: 1-20.'
                              ;
                }
              }
              units second ;
              default 2 ;
            }
            leaf testpulsewidth {
              description 'Start pulse wide of testing.'
                          ;
              type uint8 {
                range 50..200 {
                  description 'Range: 50-200.'
                              ;
                }
              }
              units second ;
              default 90 ;
            }
            leaf offtime {
              description 'Time of laser reopen, unit is second'
                          ;
              type uint32 {
                range 0..65535 {
                  description 'laser status off times (s)'
                              ;
                }
              }
              units second ;
              default 0 ;
            }
          }
          leaf flow-ctr-receive {
            description 'Flow control receive.'
                        ;
            type enumeration {
              enum disable {
                value 1 ;
                description 'Disable receive flow control.'
                            ;
              }
              enum enable {
                value 2 ;
                description 'Enable receive flow control.'
                            ;
              }
            }
            default disable ;
          }
          leaf flow-ctrl-send {
            description 'Flow control send.'
                        ;
            type enumeration {
              enum disable {
                value 1 ;
                description 'Disable send flow control.'
                            ;
              }
              enum enable {
                value 2 ;
                description 'Enable send flow control.'
                            ;
              }
            }
            default disable ;
          }
          leaf jumbo {
            description 'Configures jumbo.'
                        ;
            type enumeration {
              enum disable {
                value 1 ;
                description 'Jumbo disable.'
                            ;
              }
              enum enable {
                value 2 ;
                description 'Jumbo enable.'
                            ;
              }
            }
            default enable ;
            ncd:revise-date 2018-12-12 ;
          }
          leaf jumbo-size {
            description 'Configures jumbo size.'
                        ;
            type uint32 ;
            default 9216 ;
            ncd:revise-date 2018-12-12 ;
          }
          leaf master-slave-mode {
            description 'Set clock negotiation mode of interface.'
                        ;
            type enumeration {
              enum master {
                value 1 ;
                description 'Master mode.'
                            ;
              }
              enum slave {
                value 2 ;
                description 'Slave mode.'
                            ;
              }
              enum auto {
                value 3 ;
                description 'Auto mode.'
                            ;
              }
            }
            default auto ;
          }
          leaf fec-eth {
            description 'Configures fec of a port.'
                        ;
            type enumeration {
              enum enable {
                value 1 ;
                description enable. ;
              }
              enum disable {
                value 2 ;
                description disable. ;
              }
              enum auto {
                value 3 ;
                description auto. ;
              }
              enum invalid {
                value 0 ;
                description invalid ;
              }
            }
            default invalid ;
            ncd:revise-date 2019-06-25 ;
          }
          container alarm-insert {
            description 'Configure alarm insert'
                        ;
            leaf alarm-insert-sd {
              description 'Alarm insert SD.'
                          ;
              type empty ;
            }
            ncd:revise-date 2017-08-01 ;
          }
          container ipg-config {
            description 'Configure ipg'
                        ;
            leaf ipg {
              description ipg ;
              type uint16 {
                range 0..255 {
                  description 'ipg rang value and default value configured by p'
                            + 'erfcode.'
                              ;
                }
              }
              default 12 ;
            }
            ncd:revise-date 2018-03-09 ;
          }
          container loopback-time {
            description 'Configure loopback time.'
                        ;
            choice effective-time {
              case timeliness {
                leaf permanent {
                  description 'Loopback config permanent effective'
                              ;
                  type empty ;
                }
              }
              case date-time {
                leaf begin-date {
                  description 'Begin date from 1-1-2001 to 12-31-2037'
                              ;
                  type ncd:date ;
                  mandatory true ;
                }
                leaf begin-time {
                  description 'Begin time'
                              ;
                  type ncd:time ;
                  mandatory true ;
                }
                leaf end-date {
                  description 'End date from 1-1-2001 to 12-31-2037'
                              ;
                  type ncd:date ;
                  mandatory true ;
                }
                leaf end-time {
                  description 'End time'
                              ;
                  type ncd:time ;
                  mandatory true ;
                }
              }
            }
          }
          container work-mode-config {
            description 'Configure work mode'
                        ;
            leaf work-mode {
              description 'Ethernet working mode.'
                          ;
              type enumeration {
                enum eth {
                  value 1 ;
                  description 'Work mode is eth'
                              ;
                }
                enum flexe {
                  value 2 ;
                  description 'Work mode is flexe'
                              ;
                }
              }
              default eth ;
            }
            ncd:revise-date 2018-11-14 ;
          }
          container optical-module-config {
            // if-feature optical-module-config ;
            description 'Configure optical module'
                        ;
            leaf fec-mode {
              // if-feature optical-module-config ;
              description 'Configure fec mode for interface'
                          ;
              type enumeration {
                enum GFEC {
                  value 12 ;
                  description 'OTU-4 G.709 FEC'
                              ;
                }
                enum OTNnoFEC {
                  value 18 ;
                  description 'OTU-4 Transparent mode'
                              ;
                }
                enum HD-FEC1 {
                  value 48 ;
                  description 'OTU-4 7% Staircase HD-FEC'
                              ;
                }
                enum SD-FECy-DIFF-15 {
                  value 53 ;
                  description '15% SD-FEC Everest Compatible'
                              ;
                }
                enum SD-FECy-NONDIFF-15 {
                  value 85 ;
                  description '15% SD-FEC Denali Compatible'
                              ;
                }
              }
              ncd:revise-date 2019-03-05 ;
            }
            leaf optical-power-adjust {
              // if-feature optical-module-config ;
              description 'Configure optical power for interface'
                          ;
              type int32 {
                range -2000..1000 {
                  description 'Optical power(0.01dbm, must be a multiple of 10)'
                              ;
                }
              }
            }
            container wavelength {
              // if-feature optical-module-config ;
              description 'Configure wavelength for interface'
                          ;
              presence wavelength ;
              leaf translation-mode {
                // if-feature optical-module-config ;
                description 'Configure translation mode for interface'
                            ;
                type enumeration {
                  enum dwdm {
                    value 1 ;
                  }
                  enum cwdm {
                    value 3 ;
                  }
                }
                mandatory true ;
              }
              leaf center-frequency {
                // if-feature optical-module-config ;
                description 'Configure center frequency for interface.The range'
                          + ' is 192.1-196.0.'
                            ;
                type decimal64 {
                  fraction-digits 1 ;
                  range 192.1..196.0 ;
                }
                mandatory true ;
                ncd:revise-date 2019-06-25 ;
              }
              leaf center-freq {
                // if-feature optical-module-config ;
                status obsolete {
                  ncd:revise-date 2019-06-25 ;
                }
                description 'Configure center frequency for interface.The range'
                          + ' is 192.1-196.0.'
                            ;
                type string ;
                mandatory true ;
              }
              ncd:revise-date 2019-03-05 ;
            }
            ncd:revise-date 2019-03-05 ;
          }
          container split {
            leaf split-name {
              description 'Split name'
                          ;
              type enumeration {
                enum xgei {
                  value 132 ;
                  description 'Port xgei'
                              ;
                }
                enum xxvgei {
                  value 145 ;
                  description 'Port xxvgei'
                              ;
                }
              }
            }
            leaf split-num {
              description 'Split number'
                          ;
              type uint8 {
                range 1..255 {
                  description 'Split number range'
                              ;
                }
              }
            }
            ncd:revise-date 2020-02-15 ;
          }
          container eee-config {
            description 'Configure ethernet energy efficient function.'
                        ;
            leaf status {
              description 'Enable or disable eee function.'
                          ;
              type enumeration {
                enum disable {
                  value 0 ;
                  description 'Disable eee function.'
                              ;
                }
                enum enable {
                  value 1 ;
                  description 'Enable eee function.'
                              ;
                }
              }
              default disable ;
            }
            leaf txidletime {
              description 'Duration to the low power idle state.'
                          ;
              type uint8 {
                range 0..100 ;
              }
              default 0 ;
            }
            leaf txwaketime {
              description 'Duration to the active state.'
                          ;
              type uint8 {
                range 0..100 ;
              }
              default 0 ;
            }
            ncd:revise-date 2020-02-25 ;
          }
          container optical-inform-monitor {
            description 'Optical information monitor switch.'
                        ;
            leaf status {
              description 'Enable or disable optical information monitor.'
                          ;
              type enumeration {
                enum disable {
                  value 0 ;
                  description 'Disable optical information monitor.'
                              ;
                }
                enum enable {
                  value 1 ;
                  description 'Enable optical information monitor.'
                              ;
                }
              }
              default disable ;
            }
            ncd:revise-date 2020-02-25 ;
          }
          container control-flap {
            description 'Interface control flap auto or manual recovery.'
                        ;
            presence control-flap ;
            choice recovery-mode {
              description 'Configure recovery mode.'
                          ;
              mandatory true ;
              case automode {
                leaf auto {
                  description 'Configure interface auto recovery of control fla'
                            + 'p.'
                              ;
                  type empty ;
                  mandatory true ;
                }
                leaf recovery-time {
                  description 'Configure interface recovery time of control fla'
                            + 'p.'
                              ;
                  type uint8 {
                    range 1..60 ;
                  }
                  mandatory true ;
                }
              }
              case forcemode {
                leaf force {
                  description 'Configure interface manual recovery of control f'
                            + 'lap.'
                              ;
                  type empty ;
                  mandatory true ;
                }
              }
            }
            leaf interval-unit {
              description 'Configure the unit to second or millisecond.'
                          ;
              type enumeration {
                enum s {
                  value 0 ;
                  description 'The control flap unit of time is second.'
                              ;
                }
                enum ms {
                  value 1 ;
                  description 'The control flap unit of time is millisecond.'
                              ;
                }
              }
              mandatory true ;
            }
            leaf threshold-times {
              description 'The threshold times of interface.'
                          ;
              type uint16 {
                range 1..20000 ;
              }
              mandatory true ;
            }
            leaf interval-time {
              description 'The interval time of interface.'
                          ;
              type uint8 {
                range 1..60 ;
              }
              mandatory true ;
            }
            ncd:revise-date 2020-02-25 ;
          }
          container single-fiber {
            description 'Config single-fiber tx/rx disable/enable'
                        ;
            leaf tx {
              description 'Singel fiber tx disable/enable'
                          ;
              type enumeration {
                enum disable {
                  value 0 ;
                  description 'Singel fiber tx disable'
                              ;
                }
                enum enable {
                  value 1 ;
                  description 'Singel fiber tx enable'
                              ;
                }
              }
              default disable ;
            }
            leaf rx {
              description 'Singel fiber rx disable/enable'
                          ;
              type enumeration {
                enum disable {
                  value 0 ;
                  description 'Singel fiber rx disable'
                              ;
                }
                enum enable {
                  value 1 ;
                  description 'Singel fiber rx enable'
                              ;
                }
              }
              default disable ;
            }
            ncd:revise-date 2020-09-14 ;
          }
          leaf link-force {
            description 'Config single-fiber tx/rx disable/enable'
                        ;
            type uint8 {
              range 0..1 {
                description 'The range of link-force'
                            ;
              }
            }
            default 0 ;
            ncd:revise-date 2020-09-14 ;
          }
          container link-delays {
            description 'Configure link delay'
                        ;
            leaf link-delay-down {
              description 'Delay the processing of hardware link down notificat'
                        + 'ions.'
                          ;
              type uint32 {
                range 0..600000 {
                  description 'The time to delay link down notifications(ms).'
                              ;
                }
              }
              units millisecond ;
              default 0 ;
            }
            leaf link-delay-up {
              description 'Delay the processing of hardware link up notificatio'
                        + 'ns.'
                          ;
              type uint32 {
                range 0..600000 {
                  description 'The time to delay link up notifications(ms).'
                              ;
                }
              }
              units millisecond ;
              default 0 ;
            }
            ncd:revise-date 2020-09-21 ;
          }
          leaf flow-ctrl-onthreshold {
            // if-feature flow-control-threshold ;
            description 'Configures flow control on threshold, 0-15000.'
                        ;
            type uint32 {
              range 0..15000 ;
            }
            ncd:revise-date 2021-01-05 ;
          }
        }
      }
      container wans {
        list wan {
          key if-name ;
          leaf if-name {
            description 'Interface name.'
                        ;
            type string ;
          }
          leaf holdtime {
            description 'Configures the port hold-time.'
                        ;
            type uint16 {
              range 0..3600 {
                description 'Range: 0-3600.'
                            ;
              }
            }
            units second ;
            default 120 ;
          }
          leaf negotiation {
            description 'Configures the port negotiation mode.'
                        ;
            type enumeration {
              enum negotiation-force {
                value 1 ;
                description 'Force negotiation mode.'
                            ;
              }
              enum negotiation-auto {
                value 2 ;
                description 'Auto negotiation mode.'
                            ;
              }
            }
            default negotiation-force ;
          }
          leaf loopback {
            description 'Configures the loopback method of a port.'
                        ;
            type enumeration {
              enum cancel {
                value 0 ;
                description 'Cancel loopback mode.'
                            ;
              }
              enum outer {
                value 1 ;
                description 'Line loopback mode.'
                            ;
              }
              enum inner {
                value 2 ;
                description 'Inner loopback mode.'
                            ;
              }
              enum external {
                value 3 ;
                description 'External loopback mode.'
                            ;
              }
            }
            default cancel ;
          }
          leaf clock-mode {
            description 'Configures the clock mode.'
                        ;
            type enumeration {
              enum internal {
                value 1 ;
                description 'Select clock from local.'
                            ;
              }
              enum line {
                value 2 ;
                description 'Select clock from line.'
                            ;
              }
            }
            default internal ;
          }
          leaf framing {
            description 'Configures the framing format on port.'
                        ;
            type enumeration {
              enum sdh {
                value 1 ;
                description 'Select sdh framing.'
                            ;
              }
              enum sonet {
                value 2 ;
                description 'Select sonet framing.'
                            ;
              }
            }
            default sdh ;
          }
          leaf threshold-error-packet {
            description 'Sets the alarm threshold for port errors.'
                        ;
            type uint16 {
              range 1..65535 {
                description 'The number of error packets.'
                            ;
              }
            }
            default 3 ;
          }
          leaf threshold-sd-ber {
            description 'Configure the degrade threshold of signal for interfac'
                      + 'e.'
                        ;
            type uint8 {
              range 5..8 {
                description 'Sd-ber value.'
                            ;
              }
            }
            default 6 ;
          }
          leaf threshold-sf-ber {
            description 'Configure the failure threshold of signal for interface'
                        ;
            type uint8 {
              range 4..8 {
                description 'Sf-ber value.'
                            ;
              }
            }
            default 4 ;
          }
          leaf unidirection {
            description 'Configures an unframing channel.'
                        ;
            type enumeration {
              enum disable {
                value 1 ;
                description 'Unidirection disable.'
                            ;
              }
              enum enable {
                value 2 ;
                description 'Unidirection enable.'
                            ;
              }
            }
            default disable ;
          }
          container flag {
            leaf c2 {
              description 'Configures signaling path flag of a interface.'
                          ;
              type uint16 {
                range '0..5 | 18..28 | 32 | 207 | 254'
                      ;
              }
              default 22 ;
            }
            leaf c2ex {
              description 'Configures the channel signal flag of the expected p'
                        + 'eer on interface.'
                          ;
              type uint16 {
                range '0..5 | 18..28 | 32 | 207 | 254'
                      ;
              }
              default 22 ;
            }
            container j0 {
              leaf trace-mode {
                description 'Trace mode.'
                            ;
                type enumeration {
                  enum trace-1 {
                    value 1 ;
                  }
                  enum trace-16 {
                    value 2 ;
                  }
                }
              }
              leaf trace-1-value {
                description 'J0 description.'
                            ;
                type ncd:hex {
                  length 0..255 ;
                }
              }
              leaf trace-16-value {
                description 'J0 description.'
                            ;
                type ncd:string-with-blank {
                  length 1..15 {
                    description 'Range: 1-15.'
                                ;
                  }
                }
              }
            }
            container j0ex {
              leaf trace-mode {
                description 'Trace mode.'
                            ;
                type enumeration {
                  enum trace-1 {
                    value 1 ;
                  }
                  enum trace-16 {
                    value 2 ;
                  }
                }
              }
              leaf trace-1-value {
                description 'J0ex description.'
                            ;
                type ncd:hex {
                  length 0..255 ;
                }
              }
              leaf trace-16-value {
                description 'J0ex description.'
                            ;
                type ncd:string-with-blank {
                  length 1..15 {
                    description 'Range: 1-15.'
                                ;
                  }
                }
              }
            }
            container j1 {
              leaf trace-mode {
                description 'Trace mode.'
                            ;
                type enumeration {
                  enum trace-1 {
                    value 1 ;
                  }
                  enum trace-16 {
                    value 2 ;
                  }
                  enum trace-64 {
                    value 3 ;
                  }
                }
              }
              leaf trace-1-value {
                description 'J1 description.'
                            ;
                type ncd:hex {
                  length 0..255 ;
                }
              }
              leaf trace-16-64-value {
                description 'J1 description.'
                            ;
                type ncd:string-with-blank {
                  length 1..62 {
                    description 'Range: 1-62.'
                                ;
                  }
                }
              }
            }
            container j1ex {
              leaf trace-mode {
                description 'Trace mode.'
                            ;
                type enumeration {
                  enum trace-1 {
                    value 1 ;
                  }
                  enum trace-16 {
                    value 2 ;
                  }
                  enum trace-64 {
                    value 3 ;
                  }
                }
              }
              leaf trace-1-value {
                description 'J1ex description.'
                            ;
                type ncd:hex {
                  length 0..255 ;
                }
              }
              leaf trace-16-64-value {
                description 'J1ex description.'
                            ;
                type ncd:string-with-blank {
                  length 1..62 {
                    description 'Range: 1-62.'
                                ;
                  }
                }
              }
            }
          }
          container port-down-sdh-alarm {
            leaf rdi-l {
              description 'RDI-L alarm.'
                          ;
              type uint8 {
                range 0..1 {
                  description 'Range: 0-1.'
                              ;
                }
              }
              default 0 ;
            }
            leaf rdi-p {
              description 'RDI-P alarm.'
                          ;
              type uint8 {
                range 0..1 {
                  description 'Range: 0-1.'
                              ;
                }
              }
              default 0 ;
            }
            leaf sd {
              description 'SD alarm.'
                          ;
              type uint8 {
                range 0..1 {
                  description 'Range: 0-1.'
                              ;
                }
              }
              default 0 ;
            }
            leaf sf {
              description 'SF alarm.'
                          ;
              type uint8 {
                range 0..1 {
                  description 'Range: 0-1.'
                              ;
                }
              }
              default 0 ;
            }
          }
          container laser-status {
            leaf status {
              description 'Open/close laser or set recover mode of ALS status.'
                          ;
              type enumeration {
                enum on {
                  value 1 ;
                  description 'Open laser.'
                              ;
                }
                enum off {
                  value 2 ;
                  description 'Close laser.'
                              ;
                }
                enum auto-recovery {
                  value 3 ;
                  description 'Set recover mode is auto-recovery.'
                              ;
                }
                enum manual-recovery {
                  value 4 ;
                  description 'Set recover mode is manual-recovery.'
                              ;
                }
              }
              default on ;
            }
            leaf period {
              description 'Start period of automatic.'
                          ;
              type uint16 {
                range 20..600 {
                  description 'Range: 20-600.'
                              ;
                }
              }
              units second ;
              default 100 ;
            }
            leaf pulsewidth {
              description 'Start pulse wide of automatic.'
                          ;
              type uint8 {
                range 1..20 {
                  description 'Range: 1-20.'
                              ;
                }
              }
              units second ;
              default 2 ;
            }
            leaf testpulsewidth {
              description 'Start pulse wide of testing.'
                          ;
              type uint8 {
                range 50..200 {
                  description 'Range: 50-200.'
                              ;
                }
              }
              units second ;
              default 90 ;
            }
          }
        }
      }
      container atms {
        list atm {
          description 'ATM interface mode.'
                      ;
          key if-name ;
          leaf if-name {
            description 'Interface name.'
                        ;
            type string ;
          }
          leaf holdtime {
            description 'Configures the port hold-time.'
                        ;
            type uint16 {
              range 0..3600 {
                description 'Range: 0-3600.'
                            ;
              }
            }
            units second ;
            default 120 ;
          }
          leaf loopback {
            description 'Configures the loopback method of a port.'
                        ;
            type enumeration {
              enum cancel {
                value 0 ;
                description 'Cancel loopback mode.'
                            ;
              }
              enum outer {
                value 1 ;
                description 'Line loopback mode.'
                            ;
              }
              enum inner {
                value 2 ;
                description 'Inner loopback mode.'
                            ;
              }
            }
            default cancel ;
          }
          leaf scramble {
            description 'Configures the scrambling code of a port.'
                        ;
            type enumeration {
              enum scramble-disable {
                value 1 ;
                description 'Disable scramble payload.'
                            ;
              }
              enum scramble-enable {
                value 2 ;
                description 'Enable scramble payload.'
                            ;
              }
            }
            default scramble-enable ;
          }
          leaf clock-mode {
            description 'Configures the clock mode.'
                        ;
            type enumeration {
              enum internal {
                value 1 ;
                description 'Select clock from local.'
                            ;
              }
              enum line {
                value 2 ;
                description 'Select clock from line.'
                            ;
              }
            }
            default internal ;
          }
          leaf framing {
            description 'Configures the framing format on port.'
                        ;
            type enumeration {
              enum sdh {
                value 1 ;
                description 'Select sdh framing.'
                            ;
              }
              enum sonet {
                value 2 ;
                description 'Select sonet framing.'
                            ;
              }
            }
            default sdh ;
          }
          leaf threshold-error-packet {
            description 'Sets the alarm threshold for port errors.'
                        ;
            type uint16 {
              range 1..65535 {
                description 'The number of error packets.'
                            ;
              }
            }
            default 3 ;
          }
          container flag {
            leaf c2 {
              description 'Configures signaling path flag of a interface.'
                          ;
              type uint16 {
                range '0..5 | 18..28 | 32 | 207 | 254'
                      ;
              }
              default 19 ;
            }
            leaf c2ex {
              description 'Configures the channel signal flag of the expected p'
                        + 'eer on interface.'
                          ;
              type uint16 {
                range '0..5 | 18..28 | 32 | 207 | 254'
                      ;
              }
              default 19 ;
            }
            container j0 {
              leaf trace-mode {
                description 'Trace mode.'
                            ;
                type enumeration {
                  enum trace-1 {
                    value 1 ;
                  }
                  enum trace-16 {
                    value 2 ;
                  }
                }
              }
              leaf trace-1-value {
                description 'J0 description.'
                            ;
                type ncd:hex {
                  length 0..255 ;
                }
              }
              leaf trace-16-value {
                description 'J0 description.'
                            ;
                type ncd:string-with-blank {
                  length 1..15 {
                    description 'Range: 1-15.'
                                ;
                  }
                }
              }
            }
            container j0ex {
              leaf trace-mode {
                description 'Trace mode.'
                            ;
                type enumeration {
                  enum trace-1 {
                    value 1 ;
                  }
                  enum trace-16 {
                    value 2 ;
                  }
                }
              }
              leaf trace-1-value {
                description 'J0ex description.'
                            ;
                type ncd:hex {
                  length 0..255 ;
                }
              }
              leaf trace-16-value {
                description 'J0ex description.'
                            ;
                type ncd:string-with-blank {
                  length 1..15 {
                    description 'Range: 1-15.'
                                ;
                  }
                }
              }
            }
            container j1 {
              leaf trace-mode {
                description 'Trace mode.'
                            ;
                type enumeration {
                  enum trace-1 {
                    value 1 ;
                  }
                  enum trace-16 {
                    value 2 ;
                  }
                  enum trace-64 {
                    value 3 ;
                  }
                }
              }
              leaf trace-1-value {
                description 'J1 description.'
                            ;
                type ncd:hex {
                  length 0..255 ;
                }
              }
              leaf trace-16-64-value {
                description 'J1 description.'
                            ;
                type ncd:string-with-blank {
                  length 1..62 {
                    description 'Range: 1-62.'
                                ;
                  }
                }
              }
            }
            container j1ex {
              leaf trace-mode {
                description 'Trace mode.'
                            ;
                type enumeration {
                  enum trace-1 {
                    value 1 ;
                  }
                  enum trace-16 {
                    value 2 ;
                  }
                  enum trace-64 {
                    value 3 ;
                  }
                }
              }
              leaf trace-1-value {
                description 'J1ex description.'
                            ;
                type ncd:hex {
                  length 0..255 ;
                }
              }
              leaf trace-16-64-value {
                description 'J1ex description.'
                            ;
                type ncd:string-with-blank {
                  length 1..62 {
                    description 'Range: 1-62.'
                                ;
                  }
                }
              }
            }
          }
          container laser-status {
            leaf status {
              description 'Open/close laser or set recover mode of ALS status.'
                          ;
              type enumeration {
                enum on {
                  value 1 ;
                  description 'Open laser.'
                              ;
                }
                enum off {
                  value 2 ;
                  description 'Close laser.'
                              ;
                }
                enum auto-recovery {
                  value 3 ;
                  description 'Set recover mode is auto-recovery.'
                              ;
                }
                enum manual-recovery {
                  value 4 ;
                  description 'Set recover mode is manual-recovery.'
                              ;
                }
              }
              default on ;
            }
            leaf period {
              description 'Start period of automatic.'
                          ;
              type uint16 {
                range 20..600 {
                  description 'Range: 20-600.'
                              ;
                }
              }
              units second ;
              default 100 ;
            }
            leaf pulsewidth {
              description 'Start pulse wide of automatic.'
                          ;
              type uint8 {
                range 1..20 {
                  description 'Range: 1-20.'
                              ;
                }
              }
              units second ;
              default 2 ;
            }
            leaf testpulsewidth {
              description 'Start pulse wide of testing.'
                          ;
              type uint8 {
                range 50..200 {
                  description 'Range: 50-200.'
                              ;
                }
              }
              units second ;
              default 90 ;
            }
          }
          container alarm-insert {
            description 'Configure alarm insert'
                        ;
            leaf alarm-insert-hp {
              description 'High order path alarm insert'
                          ;
              type empty ;
            }
            leaf alarm-insert-ms {
              description 'Multiplex section alarm insert'
                          ;
              type empty ;
            }
          }
        }
      }
      container poss {
        list pos {
          description 'POS interface mode.'
                      ;
          key if-name ;
          leaf if-name {
            description 'Interface name.'
                        ;
            type string ;
          }
          leaf holdtime {
            description 'Configures the port hold-time.'
                        ;
            type uint16 {
              range 0..3600 {
                description 'Range: 0-3600.'
                            ;
              }
            }
            units second ;
            default 120 ;
          }
          leaf loopback {
            description 'Configures the loopback method of a port.'
                        ;
            type enumeration {
              enum cancel {
                value 0 ;
                description 'Cancel loopback mode.'
                            ;
              }
              enum outer {
                value 1 ;
                description 'Line loopback mode.'
                            ;
              }
              enum inner {
                value 2 ;
                description 'Inner loopback mode.'
                            ;
              }
              enum external {
                value 3 ;
                description 'External loopback mode.'
                            ;
              }
            }
            default cancel ;
          }
          leaf crc {
            description 'Configures CRC mode of a interface.'
                        ;
            type enumeration {
              enum crc16 {
                value 1 ;
                description 'CRC 16.'
                            ;
              }
              enum crc32 {
                value 2 ;
                description 'CRC 32.'
                            ;
              }
            }
            default crc32 ;
          }
          leaf scramble {
            description 'Configures the scrambling code of a port.'
                        ;
            type enumeration {
              enum scramble-disable {
                value 1 ;
                description 'Disable scramble payload.'
                            ;
              }
              enum scramble-enable {
                value 2 ;
                description 'Enable scramble payload.'
                            ;
              }
            }
            default scramble-enable ;
          }
          leaf clock-mode {
            description 'Configures the clock mode.'
                        ;
            type enumeration {
              enum internal {
                value 1 ;
                description 'Select clock from local.'
                            ;
              }
              enum line {
                value 2 ;
                description 'Select clock from line.'
                            ;
              }
            }
            default internal ;
          }
          leaf threshold-error-packet {
            description 'Sets the alarm threshold for port errors.'
                        ;
            type uint16 {
              range 1..65535 {
                description 'The number of error packets.'
                            ;
              }
            }
            default 3 ;
          }
          leaf threshold-sd-ber {
            description 'Configure the degrade threshold of signal for interfac'
                      + 'e.'
                        ;
            type uint8 {
              range 5..8 {
                description 'Sd-ber value.'
                            ;
              }
            }
            default 6 ;
          }
          leaf threshold-sf-ber {
            description 'Configure the failure threshold of signal for interfac'
                      + 'e.'
                        ;
            type uint8 {
              range 4..8 {
                description 'Sf-ber value.'
                            ;
              }
            }
            default 4 ;
          }
          container flag {
            leaf c2 {
              description 'Configures signaling path flag of a interface.'
                          ;
              type uint16 {
                range '0..5 | 18..28 | 32 | 207 | 254'
                      ;
              }
              default 22 ;
            }
            leaf c2ex {
              description 'Configures the channel signal flag of the expected p'
                        + 'eer on interface.'
                          ;
              type uint16 {
                range '0..5 | 18..28 | 32 | 207 | 254'
                      ;
              }
              default 22 ;
            }
            container j0 {
              leaf trace-mode {
                description 'Trace mode.'
                            ;
                type enumeration {
                  enum trace-1 {
                    value 1 ;
                  }
                  enum trace-16 {
                    value 2 ;
                  }
                  enum trace-64 {
                    value 3 ;
                  }
                }
              }
              leaf trace-1-value {
                description 'J0 description.'
                            ;
                type ncd:hex {
                  length 0..255 ;
                }
              }
              leaf trace-16-value {
                description 'J0 description.'
                            ;
                type ncd:string-with-blank {
                  length 1..15 {
                    description 'Range: 1-15.'
                                ;
                  }
                }
              }
              leaf trace-64-value {
                description 'J0 description.'
                            ;
                type ncd:string-with-blank {
                  length 1..62 {
                    description 'Range: 1-62.'
                                ;
                  }
                }
                ncd:revise-date 2017-06-02 ;
              }
            }
            container j0ex {
              leaf trace-mode {
                description 'Trace mode.'
                            ;
                type enumeration {
                  enum trace-1 {
                    value 1 ;
                  }
                  enum trace-16 {
                    value 2 ;
                  }
                  enum trace-64 {
                    value 3 ;
                  }
                }
              }
              leaf trace-1-value {
                description 'J0ex description.'
                            ;
                type ncd:hex {
                  length 0..255 ;
                }
              }
              leaf trace-16-value {
                description 'J0ex description.'
                            ;
                type ncd:string-with-blank {
                  length 1..15 {
                    description 'Range: 1-15.'
                                ;
                  }
                }
              }
              leaf trace-64-value {
                description 'J0ex description.'
                            ;
                type ncd:string-with-blank {
                  length 1..63 {
                    description 'Range: 1-63.'
                                ;
                  }
                }
                ncd:revise-date 2017-06-02 ;
              }
            }
            container j1 {
              leaf trace-mode {
                description 'Trace mode.'
                            ;
                type enumeration {
                  enum trace-1 {
                    value 1 ;
                  }
                  enum trace-16 {
                    value 2 ;
                  }
                  enum trace-64 {
                    value 3 ;
                  }
                }
              }
              leaf trace-1-value {
                description 'J1 description.'
                            ;
                type ncd:hex {
                  length 0..255 ;
                }
              }
              leaf trace-16-64-value {
                description 'J1 description.'
                            ;
                type ncd:string-with-blank {
                  length 1..62 {
                    description 'Range: 1-62.'
                                ;
                  }
                }
              }
            }
            container j1ex {
              leaf trace-mode {
                description 'Trace mode.'
                            ;
                type enumeration {
                  enum trace-1 {
                    value 1 ;
                  }
                  enum trace-16 {
                    value 2 ;
                  }
                  enum trace-64 {
                    value 3 ;
                  }
                }
              }
              leaf trace-1-value {
                description 'J1ex description.'
                            ;
                type ncd:hex {
                  length 0..255 ;
                }
              }
              leaf trace-16-64-value {
                description 'J1ex description.'
                            ;
                type ncd:string-with-blank {
                  length 1..62 {
                    description 'Range: 1-62.'
                                ;
                  }
                }
              }
            }
          }
          container laser-status {
            leaf status {
              description 'Open/close laser or set recover mode of ALS status.'
                          ;
              type enumeration {
                enum on {
                  value 1 ;
                  description 'Open laser.'
                              ;
                }
                enum off {
                  value 2 ;
                  description 'Close laser.'
                              ;
                }
                enum auto-recovery {
                  value 3 ;
                  description 'Set recover mode is auto-recovery.'
                              ;
                }
                enum manual-recovery {
                  value 4 ;
                  description 'Set recover mode is manual-recovery.'
                              ;
                }
              }
              default on ;
            }
            leaf period {
              description 'Start period of automatic.'
                          ;
              type uint16 {
                range 20..600 {
                  description 'Range: 20-600.'
                              ;
                }
              }
              units second ;
              default 100 ;
            }
            leaf pulsewidth {
              description 'Start pulse wide of automatic.'
                          ;
              type uint8 {
                range 1..20 {
                  description 'Range: 1-20.'
                              ;
                }
              }
              units second ;
              default 2 ;
            }
            leaf testpulsewidth {
              description 'Start pulse wide of testing.'
                          ;
              type uint8 {
                range 50..200 {
                  description 'Range: 50-200.'
                              ;
                }
              }
              units second ;
              default 90 ;
            }
          }
          container alarm-insert {
            description 'Configure alarm insert'
                        ;
            leaf alarm-insert-hp {
              description 'High order path alarm insert'
                          ;
              type empty ;
            }
            leaf alarm-insert-ms {
              description 'Multiplex section alarm insert'
                          ;
              type empty ;
            }
          }
        }
      }
      container uleis {
        list ulei {
          description 'ULEI interface mode.'
                      ;
          key if-name ;
          leaf if-name {
            description 'Interface name.'
                        ;
            type string ;
          }
          leaf holdtime {
            description 'Configures the port hold-time.'
                        ;
            type uint16 {
              range 0..3600 {
                description 'Range: 0-3600.'
                            ;
              }
            }
            units second ;
            default 120 ;
          }
          leaf speed {
            description 'Configures the rate of a port.'
                        ;
            type enumeration {
              enum speed-10M {
                value 1 ;
                description 'Port speed is 10M.'
                            ;
              }
              enum speed-100M {
                value 2 ;
                description 'Port speed is 100M.'
                            ;
              }
              enum speed-1G {
                value 3 ;
                description 'Port speed is 1G.'
                            ;
              }
              enum speed-10G {
                value 4 ;
                description 'Port speed is 10G.'
                            ;
              }
              enum speed-25G {
                value 10 ;
                description 'Port speed is 25G.'
                            ;
              }
              enum speed-40G {
                value 5 ;
                description 'Port speed is 40G.'
                            ;
              }
              enum speed-50G {
                value 11 ;
                description 'Port speed is 50G.'
                            ;
              }
              enum speed-100G {
                value 6 ;
                description 'Port speed is 100G.'
                            ;
              }
            }
            default speed-1G ;
          }
        }
      }
      container dampings {
        list damp-status {
          key if-name ;
          leaf if-name {
            description 'Interface name.'
                        ;
            type string ;
          }
          leaf status {
            description 'Port damping status.'
                        ;
            type enumeration {
              enum disable {
                value 1 ;
                description 'Port damping disable.'
                            ;
              }
              enum enable {
                value 2 ;
                description 'Port damping enable.'
                            ;
              }
            }
            default enable ;
          }
        }
        list damping {
          key if-name ;
          leaf if-name {
            type string ;
          }
          leaf max-suppress-time {
            description 'Max suppress time(max-suppress-time > half-life).'
                        ;
            type uint16 {
              range 2..600 {
                description 'Range: 2-600.'
                            ;
              }
            }
            units second ;
            default 20 ;
          }
          leaf suppress-threshold {
            description 'Suppress threshold(suppress > reuse).'
                        ;
            type uint16 {
              range 2..10000 {
                description 'Range: 2-10000.'
                            ;
              }
            }
            default 2000 ;
          }
          leaf reuse-threshold {
            description 'Reuse threshold(suppress > reuse).'
                        ;
            type uint16 {
              range 1..2000 {
                description 'Range: 1-2000.'
                            ;
              }
            }
            default 1000 ;
          }
          leaf halflife {
            description 'Half life(max-suppress-time > half-life).'
                        ;
            type uint8 {
              range 1..100 {
                description 'Range: 1-100.'
                            ;
              }
            }
            units second ;
            default 5 ;
          }
        }
      }
      container link-delays {
        list link-delay {
          key if-name ;
          leaf if-name {
            description 'Interface name.'
                        ;
            type string ;
          }
          leaf link-delay-down {
            description 'Delay the processing of hardware link down notificatio'
                      + 'ns.'
                        ;
            type uint32 {
              range 0..600000 {
                description 'The time to delay link down notifications(ms).'
                            ;
              }
            }
            units millisecond ;
            default 0 ;
          }
          leaf link-delay-up {
            description 'Delay the processing of hardware link up notifications.'
                        ;
            type uint32 {
              range 0..600000 {
                description 'The time to delay link up notifications(ms).'
                            ;
              }
            }
            units millisecond ;
            default 0 ;
          }
        }
      }
      container port-modes {
        list port-mode {
          key if-name ;
          leaf if-name {
            description 'Interface name.'
                        ;
            type string ;
          }
          leaf lan-wan {
            description 'Switch port mode to LAN or WAN.'
                        ;
            type enumeration {
              enum lan {
                value 132 ;
                description 'Switch port to LAN mode.'
                            ;
              }
              enum wan {
                value 133 ;
                description 'Switch port to WAN mode.'
                            ;
              }
              enum gei {
                value 131 ;
              }
              enum pos3 {
                value 260 ;
                description 'Switch port to POS3 mode.'
                            ;
              }
              enum pos12 {
                value 261 ;
                description 'Switch port to POS12 mode.'
                            ;
              }
              enum pos48 {
                value 262 ;
                description 'Switch port to POS48 mode.'
                            ;
              }
            }
          }
          leaf pos3-pos12 {
            description 'Switches pos interface modes.'
                        ;
            type enumeration {
              enum pos3 {
                value 260 ;
                description 'Switch port to POS3 mode.'
                            ;
              }
              enum pos12 {
                value 261 ;
                description 'Switch port to POS12 mode.'
                            ;
              }
              enum lan {
                value 132 ;
                description 'Switch port to LAN mode.'
                            ;
              }
              enum wan {
                value 133 ;
                description 'Switch port to WAN mode.'
                            ;
              }
              enum gei {
                value 131 ;
              }
              enum pos48 {
                value 262 ;
                description 'Switch port to POS48 mode.'
                            ;
              }
            }
          }
          leaf xgei-gei {
            description 'Switch port mode to xgei or gei.'
                        ;
            type enumeration {
              enum xgei {
                value 132 ;
                description 'Switch to xgei'
                            ;
              }
              enum gei {
                value 131 ;
                description 'Switch to gei'
                            ;
              }
              enum wan {
                value 133 ;
                description 'Switch to wan'
                            ;
              }
              enum pos3 {
                value 260 ;
                description 'Switch to POS3'
                            ;
              }
              enum pos12 {
                value 261 ;
                description 'Switch to POS12'
                            ;
              }
              enum pos48 {
                value 262 ;
                description 'Switch to POS48'
                            ;
              }
            }
            ncd:revise-date 2016-09-10 ;
          }
        }
      }
      container create-uleis {
        list create-ulei {
          key ulei-ifname ;
          leaf ulei-ifname {
            description 'Ulei interface name.'
                        ;
            type string ;
          }
        }
      }
      container threshold-sd-fers {
        list sd-status {
          key if-name ;
          leaf if-name {
            description 'Interface name.'
                        ;
            type string ;
          }
          leaf status {
            description 'Enable or disable sd detection.'
                        ;
            type enumeration {
              enum disable {
                value 0 ;
                description 'Disable sd detection.'
                            ;
              }
              enum enable {
                value 1 ;
                description 'Enable sd detection.'
                            ;
              }
            }
            default disable ;
          }
        }
        list threshold-sd-fer {
          key if-name ;
          leaf if-name {
            description 'Interface name.'
                        ;
            type string ;
          }
          leaf occur-coefficient {
            description 'Threshold coefficient of occur alarm.'
                        ;
            type uint8 {
              range 1..9 {
                description 'Range: 1-9.'
                            ;
              }
            }
            default 1 ;
          }
          leaf occur-exponent {
            description 'Threshold exponent of occur alarm.'
                        ;
            type uint8 {
              range 1..9 {
                description 'Range: 1-9.'
                            ;
              }
            }
            default 6 ;
          }
          leaf clear-coefficient {
            description 'Threshold coefficient of clear alarm.'
                        ;
            type uint8 {
              range 1..9 {
                description 'Range: 1-9.'
                            ;
              }
            }
            default 1 ;
          }
          leaf clear-exponent {
            description 'Threshold exponent of clear alarm.'
                        ;
            type uint8 {
              range 1..9 {
                description 'Range: 1-9.'
                            ;
              }
            }
            default 6 ;
          }
          leaf period {
            description 'alarm period.'
                        ;
            type uint16 {
              range 20..3000 {
                description 'Range: 20-3000.'
                            ;
              }
            }
            units second ;
            default 20 ;
          }
        }
      }
      container sdh-thresholds {
        list sdh-threshold {
          key if-name ;
          leaf if-name {
            description 'Interface name'
                        ;
            type string ;
          }
          leaf b2-sf-ber {
            description 'Configure multiplex section signal failure threshold'
                        ;
            type uint8 {
              range 4..8 {
                description 'Range: 4-8'
                            ;
              }
            }
          }
          leaf b2-sd-ber {
            description 'Configure multiplex section signal degradation thresho'
                      + 'ld'
                        ;
            type uint8 {
              range 5..8 {
                description 'Range: 5-8'
                            ;
              }
            }
          }
          leaf b3-sf-ber {
            description 'Configure high order channel signal failure threshold'
                        ;
            type uint8 {
              range 4..8 {
                description 'Range: 4-8'
                            ;
              }
            }
          }
          leaf b3-sd-ber {
            description 'Configure high order channel signal degradation thresh'
                      + 'old'
                        ;
            type uint8 {
              range 5..8 {
                description 'Range: 5-8'
                            ;
              }
            }
          }
          leaf b1-sf-ber {
            description 'Configure regeneration segment signal failure threshold'
                        ;
            type uint8 {
              range 4..8 {
                description 'Range: 4-8'
                            ;
              }
            }
          }
          leaf b1-sd-ber {
            description 'Configure regeneration segment signal degradation thre'
                      + 'shold'
                        ;
            type uint8 {
              range 5..8 {
                description 'Range: 5-8'
                            ;
              }
            }
          }
        }
      }
      container special-opticals {
        list special-optical {
          description 'Special optical interface mode, such as OSC, OCH, SOMS.'
                      ;
          key if-name ;
          leaf if-name {
            description 'Interface name.'
                        ;
            type string {
              length 1..31 ;
            }
          }
          container laser-status {
            description 'Configure laser status.'
                        ;
            leaf status {
              description 'Open/close laser or set recover mode of ALS status.'
                          ;
              type enumeration {
                enum on {
                  value 1 ;
                  description 'Open laser.'
                              ;
                }
                enum off {
                  value 2 ;
                  description 'Close laser.'
                              ;
                }
                enum auto-recovery {
                  value 3 ;
                  description 'Set recover mode is auto-recovery.'
                              ;
                }
                enum manual-recovery {
                  value 4 ;
                  description 'Set recover mode is manual-recovery.'
                              ;
                }
              }
              default on ;
            }
            leaf period {
              description 'Start period of automatic.'
                          ;
              type uint16 {
                range 20..600 {
                  description 'Range: 20-600.'
                              ;
                }
              }
              units second ;
              default 100 ;
            }
            leaf pulsewidth {
              description 'Start pulse wide of automatic.'
                          ;
              type uint8 {
                range 1..20 {
                  description 'Range: 1-20.'
                              ;
                }
              }
              units second ;
              default 2 ;
            }
            leaf testpulsewidth {
              description 'Start pulse wide of testing.'
                          ;
              type uint8 {
                range 50..200 {
                  description 'Range: 50-200.'
                              ;
                }
              }
              units second ;
              default 90 ;
            }
            leaf offtime {
              description 'Time of laser reopen, unit is second'
                          ;
              type uint32 {
                range 0..65535 {
                  description 'laser status off times (s)'
                              ;
                }
              }
              units second ;
              default 0 ;
            }
          }
        }
      }
      container gfp-mplss {
        list gfp-mpls {
          key if-name ;
          leaf if-name {
            description 'Interface name.'
                        ;
            type string {
              length 1..31 ;
            }
          }
          leaf odu-if-name {
            description "The binding port's interface name."
                        ;
            type string {
              length 1..31 ;
            }
          }
          leaf sd-enabled {
            description 'sd enabled.'
                        ;
            type enumeration {
              enum disable {
                value 0 ;
              }
              enum enable {
                value 1 ;
              }
            }
            default disable ;
          }
          leaf rf2sf {
            description 'The Switch of rf to sf.'
                        ;
            type enumeration {
              enum off {
                value 0 ;
              }
              enum on {
                value 1 ;
              }
            }
            default on ;
          }
        }
        ncd:revise-date 2018-07-01 ;
      }
      container create-vsgs {
        list create-vsg {
          key vsg-ifname ;
          leaf vsg-ifname {
            description 'VSG interface name. The name starts with "vsg", follow'
                      + 'ed with a number. The default range of the number is 1'
                      + '025..1056 without customized.'
                        ;
            type string {
              length 1..31 ;
            }
          }
        }
        ncd:revise-date 2020-04-28 ;
      }
    }
    container flexe-dcn-oh {
      leaf global-dcn-oh {
        description 'All port dcn overhead.'
                    ;
        type enumeration {
          enum shim-to-shim {
            value 1 ;
            description 'Flexe dcn section overhead.'
                        ;
          }
          enum section {
            value 0 ;
            description 'Flexe dcn shim-to-shim overhead.'
                        ;
          }
        }
        default section ;
      }
      list port-dcn-oh {
        key if-name ;
        leaf if-name {
          description 'Interface name.'
                      ;
          type ncd:ifname ;
        }
        leaf dcn-oh {
          description 'Port dcn overhead.'
                      ;
          type enumeration {
            enum shim-to-shim {
              value 1 ;
              description 'Flexe dcn section overhead.'
                          ;
            }
            enum section {
              value 0 ;
              description 'Flexe dcn shim-to-shim overhead.'
                          ;
            }
          }
          default section ;
        }
      }
      ncd:revise-date 2021-04-19 ;
    }
  }
  container operation {
    config false ;
    container pm-if {
      container start-alss {
        list start-als {
          key if-name ;
          leaf if-name {
            description 'Interface name.'
                        ;
            type string ;
          }
          leaf als {
            description 'Set recovery mode.'
                        ;
            type enumeration {
              enum manual {
                value 0 ;
                description 'Manual impulse.'
                            ;
              }
              enum testing {
                value 1 ;
                description 'Testing impulse.'
                            ;
              }
            }
          }
        }
      }
      container expire-holdtimes {
        list expire-holdtime {
          key if-name ;
          leaf if-name {
            description 'Interface name.'
                        ;
            type string ;
          }
        }
      }
      container clear-eee-statisticss {
        description 'Clear eee statistics.'
                    ;
        list clear-eee-statistics-interface {
          description 'Clear eee statistics by ifname.'
                      ;
          key if-name ;
          leaf if-name {
            description 'Interface name.'
                        ;
            type string ;
          }
        }
        list clear-eee-statistics-pfu {
          description 'Clear eee statistics by pfu.'
                      ;
          key 'shelf boardtype panel'
              ;
          leaf shelf {
            description 'Shelf number.'
                        ;
            type uint8 {
              range 0..254 ;
            }
          }
          leaf boardtype {
            description 'Board type.'
                        ;
            type enumeration {
              enum MPU {
                value 1 ;
              }
              enum PFU {
                value 3 ;
              }
              enum SFU {
                value 4 ;
              }
            }
          }
          leaf panel {
            description 'Panel number of line-card.'
                        ;
            type string ;
          }
        }
        ncd:revise-date 2020-02-25 ;
      }
      container control-flap-clears {
        description 'Clear control flap of interface.'
                    ;
        list control-flap-clear {
          description 'Clear control flap of interface.'
                      ;
          key if-name ;
          leaf if-name {
            description 'Interface name.'
                        ;
            type string ;
          }
        }
        ncd:revise-date 2020-02-25 ;
      }
    }
  }
  container state {
    config false ;
    container pm-if {
      container als-statuss {
        list als-status {
          key if-name ;
          leaf if-name {
            type string ;
          }
          leaf als-flag {
            type enumeration {
              enum on {
                value 0 ;
              }
              enum off {
                value 1 ;
              }
            }
          }
          leaf recovery-mode {
            type enumeration {
              enum automatic-recovery {
                value 0 ;
              }
              enum manual-recovery {
                value 1 ;
              }
              enum laser-on {
                value 2 ;
              }
              enum laser-off {
                value 3 ;
              }
            }
          }
          leaf current-status {
            description 'The current status of the laser'
                        ;
            type enumeration {
              enum ALS {
                value 0 ;
              }
              enum normal {
                value 1 ;
              }
            }
          }
          leaf laser-status {
            type enumeration {
              enum unkonwn {
                value 0 ;
              }
              enum off {
                value 1 ;
              }
              enum on {
                value 2 ;
              }
            }
            ncd:revise-date 2017-10-16 ;
          }
          leaf off-reason {
            description 'The reason of the laser power off'
                        ;
            type enumeration {
              enum power-on-laser {
                value 0 ;
              }
              enum power-off-laser {
                value 1 ;
              }
              enum power-off-als {
                value 2 ;
              }
              enum power-off-delayup {
                value 3 ;
              }
              enum power-off-shutdown {
                value 4 ;
              }
              enum power-off-los {
                value 5 ;
              }
            }
          }
        }
      }
      container damp-statuss {
        list damp-status {
          key if-name ;
          leaf if-name {
            type string ;
          }
          leaf flap-number {
            type uint32 ;
          }
          leaf damp-number {
            type uint32 ;
          }
          leaf penalty {
            type uint32 ;
          }
          leaf max-penalty {
            type uint32 ;
          }
          leaf suppress {
            type enumeration {
              enum FALSE {
                value 0 ;
              }
              enum TRUE {
                value 1 ;
              }
            }
          }
        }
      }
      container port-statuss {
        list port-status {
          key if-name ;
          leaf if-name {
            description 'Interface name.'
                        ;
            type string ;
          }
          leaf portphystatus {
            description 'Port physical status.'
                        ;
            type enumeration {
              enum up {
                value 0 ;
                description up. ;
              }
              enum down {
                value 1 ;
                description down. ;
              }
              enum offline {
                value 32 ;
                description offline. ;
              }
            }
          }
        }
        ncd:revise-date 2018-08-16 ;
      }
      container eth-statuss {
        list eth-status {
          key if-name ;
          leaf if-name {
            description 'Interface name.'
                        ;
            type string ;
          }
          leaf ifhaslos {
            type enumeration {
              enum no {
                value 0 ;
                description no. ;
              }
              enum yes {
                value 1 ;
                description yes. ;
              }
            }
          }
          leaf loopback {
            description 'Query the loopback mode of a port.'
                        ;
            type enumeration {
              enum cancel {
                value 0 ;
                description 'Cancel loopback mode.'
                            ;
              }
              enum outer {
                value 1 ;
                description 'Line loopback mode.'
                            ;
              }
              enum inner {
                value 2 ;
                description 'Inner loopback mode.'
                            ;
              }
              enum external {
                value 3 ;
                description 'External loopback mode.'
                            ;
              }
            }
          }
          ncd:revise-date 2019-05-10 ;
        }
      }
      container eee-statisticss {
        description 'Show eee statistics.'
                    ;
        list eee-statistics-interface {
          description 'Show eee statistics of interface.'
                      ;
          key if-name ;
          leaf if-name {
            description 'Interface name.'
                        ;
            type string ;
          }
          leaf txevents {
            type uint32 ;
          }
          leaf txduration {
            type uint32 ;
          }
          leaf rxevents {
            type uint32 ;
          }
          leaf rxduration {
            type uint32 ;
          }
        }
        list eee-statistics-pfu {
          description 'Show eee statistics of board.'
                      ;
          key 'shelf boardtype panel'
              ;
          leaf shelf {
            description 'Shelf number.'
                        ;
            type uint8 ;
          }
          leaf boardtype {
            description 'Board type.'
                        ;
            type enumeration {
              enum MPU {
                value 1 ;
              }
              enum PFU {
                value 3 ;
              }
              enum SFU {
                value 4 ;
              }
              enum UNKNOWN {
                value 255 ;
              }
            }
          }
          leaf panel {
            description 'Panel number.'
                        ;
            type string ;
          }
          leaf if-name {
            description 'Interface name.'
                        ;
            type string ;
          }
          leaf txevents {
            type uint32 ;
          }
          leaf txduration {
            type uint32 ;
          }
          leaf rxevents {
            type uint32 ;
          }
          leaf rxduration {
            type uint32 ;
          }
        }
        ncd:revise-date 2020-02-25 ;
      }
      container mtn-statuss {
        list mtn-status {
          key if-name ;
          leaf if-name {
            description 'Interface name.'
                        ;
            type string ;
          }
          leaf portphystatus {
            description 'Port physical status.'
                        ;
            type enumeration {
              enum up {
                value 0 ;
                description up. ;
              }
              enum down {
                value 1 ;
                description down. ;
              }
              enum offline {
                value 32 ;
                description offline. ;
              }
            }
          }
          leaf group-id {
            type uint32 ;
          }
          leaf fec-mode {
            description 'fec of a port.'
                        ;
            type enumeration {
              enum enable {
                value 1 ;
                description enable. ;
              }
              enum disable {
                value 2 ;
                description disable. ;
              }
              enum auto {
                value 3 ;
                description auto. ;
              }
              enum invalid {
                value 0 ;
                description invalid ;
              }
            }
          }
        }
        ncd:revise-date 2020-09-21 ;
      }
    }
  }
  rpc fec-bypass {
    description 'RPC Operation'
                ;
    input {
      leaf if-name {
        config false ;
        description 'Interface name.'
                    ;
        type string ;
        mandatory true ;
      }
      leaf bypass-status {
        config false ;
        description 'Set fec bypass.'
                    ;
        type enumeration {
          enum enable {
            value 1 ;
            description enable. ;
          }
          enum disable {
            value 2 ;
            description disable. ;
          }
        }
        mandatory true ;
      }
    }
  }
  notification event {
    container loopback-auto-cancel {
      config false ;
      description 'Loopback auto cancel event.'
                  ;
      leaf ifname {
        description 'Interface name.'
                    ;
        type string ;
      }
    }
  }
}
