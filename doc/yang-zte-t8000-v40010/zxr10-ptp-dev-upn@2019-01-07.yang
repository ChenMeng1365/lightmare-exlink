module zxr10-ptp-dev-upn {
  namespace 'http://www.zte.com.cn/zxr10/netconf/schema/rosng/ptp-dev-upn'
            ;
  prefix ptp-dev-upn ;
  import zxr10-ptp {
    prefix ptp ;
    revision-date 2019-01-07 ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2019-01-07 ;
  deviation '/ptp:configuration/ptp:ptp/ptp:ptp-1588/ptp:port/ptp:port-lists/pt'
          + 'p:free-ports/ptp:free-port/ptp:domain-delay-mechanism'
            {
    deviate not-supported ;
  }
  deviation '/ptp:configuration/ptp:ptp/ptp:ptp-1588/ptp:port/ptp:port-lists/pt'
          + 'p:free-ports/ptp:free-port/ptp:multi-domain'
            {
    deviate not-supported ;
  }
  deviation '/ptp:configuration/ptp:ptp/ptp:ptp-1588/ptp:port-phys/ptp:phy-port'
          + '/ptp:pdelay-interval'
            {
    deviate not-supported ;
  }
  deviation '/ptp:configuration/ptp:ptp/ptp:ptp-1588/ptp:port/ptp:port-lists/pt'
          + 'p:free-ports/ptp:free-port/ptp:sync-interval'
            {
    deviate replace {
      type int32 {
        range -4..1 ;
      }
    }
  }
  deviation '/ptp:configuration/ptp:ptp/ptp:ptp-1588/ptp:port/ptp:port-lists/pt'
          + 'p:free-ports/ptp:free-port/ptp:delay-interval'
            {
    deviate replace {
      type int32 {
        range -4..4 ;
      }
    }
  }
  deviation '/ptp:configuration/ptp:ptp/ptp:ptp-1588/ptp:port/ptp:combined-oc-l'
          + 'ists/ptp:free-combined-oc-lists/ptp:free-combined-oc/ptp:sync-inte'
          + 'rval'
            {
    deviate replace {
      type int32 {
        range -4..1 ;
      }
    }
  }
  deviation '/ptp:configuration/ptp:ptp/ptp:ptp-1588/ptp:port/ptp:combined-oc-l'
          + 'ists/ptp:free-combined-oc-lists/ptp:free-combined-oc/ptp:delay-int'
          + 'erval'
            {
    deviate replace {
      type int32 {
        range -4..4 ;
      }
    }
  }
  deviation '/ptp:configuration/ptp:ptp/ptp:ptp-1588/ptp:port-phys/ptp:phy-port'
          + '/ptp:status'
            {
    deviate replace {
      default disable ;
      type enumeration {
        enum disable {
          value 0 ;
        }
        enum enable {
          value 1 ;
        }
      }
    }
  }
  deviation '/ptp:configuration/ptp:ptp/ptp:ptp-1588/ptp:clock-association/ptp:'
          + 'pll-associate-switch'
            {
    deviate not-supported ;
  }
    deviation '/ptp:configuration/ptp:ptp/ptp:ptp-1588/ptp:port-phys/ptp:phy-port'
          + '/ptp:accuracy-mode'
            {
    deviate not-supported ;
  }
}
