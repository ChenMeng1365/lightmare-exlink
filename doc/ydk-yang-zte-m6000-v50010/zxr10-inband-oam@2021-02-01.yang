module zxr10-inband-oam {
  namespace 'http://www.zte.com.cn/zxr10/netconf/schema/rosng/inband-oam'
            ;
  prefix inband-oam ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2021-02-01 {
    description '1.Add leaf of configuration/inband-oam/flows/flow/per-packet-d'
              + 'm-status.'+"\n"
              + '2.Add leaf of configuration/inband-oam/relations/relation/per-'
              + 'packet-dm-status.'+"\n"
              + '3.Add feature of per-packet-dm.'
                ;
  }
  revision 2021-01-20 {
    description '1. Add vpls case of configuration/relations/relation/vpn-type.'
                ;
  }
  revision 2021-01-08 {
    description '1. Add evpn-vpws case of configuration/relations/relation/vpn-'
              + 'type.'
                ;
  }
  revision 2020-06-05 {
    description '1. Add feature eth-flow.'+"\n"
              + '2. Add feature tunnel-flow.'+"\n"
              + '3. Add feature vpws-name.'+"\n"
              + '4. Add container of configuration/inband-oam/flows/flow/flow-t'
              + 'ype/ip/eth.'+"\n"
              + '5. Add container of configuration/relations/relation/vpn-type,'
              + 'which include the case of vrf and the case of vpws.'+"\n"
              + '6. Add leaf of configuration/relations/relation/vpws-name.'
                ;
  }
  revision 2020-05-22 {
    description '1. Add leaf node configuration/inband-oam/flows/flow/flow-type'
              + '/ip/member-port.'
                ;
  }
  revision 2019-10-30 {
    description '1 Modify configuration/relations/relation/vrf-name,change its '
              + 'mandatory satus from fase to true.'
                ;
  }
  revision 2019-09-09 {
    description '1 Add configuration/inband-oam/flows/flow/hop-by-hop-status.'+"\n"
              + '2 Add configuration/relations/relation/period.'+"\n"
              + '3 Add configuration/relations/relation/interfaces.'
                ;
  }
  revision 2019-01-31 {
    description '1. Add feature relation.'+"\n"
              + '2. Add configuration/global.'+"\n"
              + '3. Add configuration/relations.'+"\n"
              + '4. Modify the range of configuration/inband-oam/flows/flow/flo'
              + 'w-id.'+"\n"
              + '5. Modify the range of configuration/inband-oam/decapsulation/'
              + 'decapsulation-no-ifname/flow-id.'+"\n"
              + '6. Modify the range of configuration/inband-oam/decapsulation/'
              + 'decapsulation-with-ifname/flow-id.'+"\n"
              + '7. Add configuration/inband-oam/flows/flow/dm-dscp.'+"\n"
              + '8. Add configuration/inband-oam/flows/flow/dm-exp.'+"\n"
              + '9. Add configuration/inband-oam/flows/flow/flow-type/ip/protoc'
              + 'ol.'+"\n"
              + '10. Add configuration/inband-oam/flows/flow/flow-type/ip/sourc'
              + 'e-port.'+"\n"
              + '11. Add configuration/inband-oam/flows/flow/flow-type/ip/dest-'
              + 'port.'+"\n"
              + '12. Add configuration/inband-oam/flows/flow/flow-type/ip/dscp.'
              + ''+"\n"
              + '13. Add an enumeration value 1s for typedef of alternate-marki'
              + 'ng-period and modify the default value to 30s. '+"\n"
              + '13. Modify the default value of configuration/inband-oam/flows'
              + '/flow/period.'+"\n"
              + '14. Remove the mandatory feature of source-addr-ipv4 and dest-'
              + 'addr-ipv4 in configuration/inband-oam/flows/flow/flow-type/ip/'
              + 'ipv4-or-ipv6/ipv4.'+"\n"
              + '15. Remove the mandatory feature of source-addr-ipv6 and dest-'
              + 'addr-ipv6 in configuration/inband-oam/flows/flow/flow-type/ip/'
              + 'ipv4-or-ipv6/ipv6.'
                ;
  }
  revision 2018-10-30 {
    description 'Initial version.'
                ;
  }
  feature relation {
    description 'Configure the relation between Flowid and VRF.'
                ;
  }
  feature eth-flow {
    description 'Support the flow of eth.'
                ;
  }
  feature tunnel-flow {
    description 'Support the flow of tunnel.'
                ;
  }
  feature dm {
    description 'Support the operation of DM.'
                ;
  }
  feature vpws-name {
    description 'Support the configuration of vpws-name.'
                ;
  }
  feature evpn-vpnws {
    description 'Support the configuration of evpn-vpws.'
                ;
  }
  feature l2vpn-vpls {
    description 'Support the configuration of vpls.'
                ;
  }
  feature per-packet-dm {
    description 'Support the configuration of per-packet-dm.'
                ;
  }
  typedef alternate-marking-period {
    type enumeration {
      enum 5s {
        value 1 ;
        description 'Alternate marking period is 5s.'
                    ;
      }
      enum 10s {
        value 2 ;
        description 'Alternate marking period is 10s.'
                    ;
      }
      enum 30s {
        value 3 ;
        description 'Alternate marking period is 30s.'
                    ;
      }
      enum 60s {
        value 4 ;
        description 'Alternate marking period is 60s.'
                    ;
      }
      enum 5min {
        value 5 ;
        description 'Alternate marking period is 5min.'
                    ;
      }
      enum 15min {
        value 6 ;
        description 'Alternate marking period is 15min.'
                    ;
      }
      enum 1s {
        value 7 ;
        description 'Alternate marking period is 1s.'
                    ;
      }
    }
    default 30s ;
    description 'Alternate marking period,including 1s,5s,10s,30s,60s,5min and '
              + '15min(default:30s).'
                ;
  }
  container configuration {
    description 'Configuration of inband OAM model Info.'
                ;
    container inband-oam {
      description 'Inband OAM flow alternate marking configuration.'
                  ;
      container global {
        description 'Global configuration.'
                    ;
        leaf label {
          description 'The label ranges from 4 to 6 and 8 to 12(default:12).'
                      ;
          type uint32 {
            range '4..6 | 8..12'
                  {
              description 'The range of the label.'
                          ;
            }
          }
          default 12 ;
        }
        ncd:revise-date 2019-01-31 ;
      }
      container flows {
        description 'Configure inband OAM flow coloring.'
                    ;
        list flow {
          description 'Configure inband OAM flow coloring.'
                      ;
          key flow-id ;
          leaf flow-id {
            description 'The flow id to identify a specific flow,ranges from 1 '
                      + 'to 1048575.'
                        ;
            type uint32 {
              range 1..1048575 {
                description 'The range of flow id.'
                            ;
              }
            }
          }
          leaf alternate-status {
            description 'The status of flow alternate marking,including enable '
                      + 'and disable(default:enable).'
                        ;
            type enumeration {
              enum disable {
                value 0 ;
                description 'The status of flow alternate marking is disable.'
                            ;
              }
              enum enable {
                value 1 ;
                description 'The status of flow alternate marking is enable.'
                            ;
              }
            }
            default enable ;
          }
          leaf period {
            description 'The period of flow coloring,including 1s,5s,10s,30s,60'
                      + 's,5min and 15min(default:30s).'
                        ;
            type alternate-marking-period ;
            default 30s ;
          }
          leaf dm-dscp {
            // if-feature dm ;
            description 'The DSCP value in delay measurement of IP flow,ranges '
                      + 'from 0 to 63.'
                        ;
            type uint8 {
              range 0..63 {
                description 'The range of DSCP.'
                            ;
              }
            }
            ncd:revise-date 2019-01-31 ;
          }
          leaf dm-exp {
            // if-feature dm ;
            description 'The EXP value in delay measurement of TE tunnel,ranges'
                      + ' from 0 to 7.'
                        ;
            type uint8 {
              range 0..7 {
                description 'The range of EXP.'
                            ;
              }
            }
            ncd:revise-date 2019-01-31 ;
          }
          leaf hop-by-hop-status {
            description 'The status of hop-by-hop coloring,including enable and'
                      + ' disable(default:enable).'
                        ;
            type enumeration {
              enum disable {
                value 0 ;
                description 'Disable hop-by-hop coloring.'
                            ;
              }
              enum enable {
                value 1 ;
                description 'Enable hop-by-hop coloring.'
                            ;
              }
            }
            default disable ;
            ncd:revise-date 2019-09-09 ;
          }
          leaf per-packet-dm-status {
            // if-feature per-packet-dm ;
            description 'The status of per-packet delay measurement,including e'
                      + 'nable and disable(default:enable).'
                        ;
            type enumeration {
              enum disable {
                value 0 ;
                description 'Disable per-packet DM.'
                            ;
              }
              enum enable {
                value 1 ;
                description 'Enable per-packet DM.'
                            ;
              }
            }
            default disable ;
            ncd:revise-date 2021-02-01 ;
          }
          container flow-type {
            description 'Choose one flow type from ip and TE tunnel.'
                        ;
            choice flow-type {
              description 'Choose one flow type from ip and TE tunnel.'
                          ;
              mandatory true ;
              case ip {
                description 'The coloring flow type is ip.'
                            ;
                container ip {
                  description 'The coloring flow type is ip.'
                              ;
                  leaf ifname {
                    description 'The UNI interface name of ip flow.'
                                ;
                    type ncd:ifname {
                      length 1..31 {
                        description 'The range of interface name length.'
                                    ;
                      }
                    }
                    mandatory true ;
                  }
                  leaf member-port {
                    description 'The member port of the UNI interface.'
                                ;
                    type ncd:ifname {
                      length 1..31 {
                        description 'The range of interface name length.'
                                    ;
                      }
                    }
                    ncd:revise-date 2020-06-05 ;
                  }
                  container ipv4-or-ipv6 {
                    description 'Choose one from ipv4 and ipv6.'
                                ;
                    choice ipv4-or-ipv6 {
                      description 'Choose one from ipv4 and ipv6.'
                                  ;
                      case ipv4 {
                        description 'Type is ipv4.'
                                    ;
                        container ipv4 {
                          description 'Type is ipv4.'
                                      ;
                          leaf source-addr-ipv4 {
                            description 'The source ipv4 address.'
                                        ;
                            type ncd:ipv4-address-none-zero ;
                          }
                          leaf dest-addr-ipv4 {
                            description 'The destination ipv4 address.'
                                        ;
                            type ncd:ipv4-address-none-zero ;
                          }
                        }
                      }
                      case ipv6 {
                        description 'Type is ipv6.'
                                    ;
                        container ipv6 {
                          description 'Type is ipv6.'
                                      ;
                          leaf source-addr-ipv6 {
                            description 'The source ipv6 address.'
                                        ;
                            type ncd:ipv6-address ;
                          }
                          leaf dest-addr-ipv6 {
                            description 'The destination ipv6 address.'
                                        ;
                            type ncd:ipv6-address ;
                          }
                        }
                      }
                    }
                  }
                  leaf protocol {
                    description 'The protocol number,ranges from 1 to 255.'
                                ;
                    type uint8 {
                      range 1..255 {
                        description 'The range of protocol.'
                                    ;
                      }
                    }
                    ncd:revise-date 2019-01-31 ;
                  }
                  leaf source-port {
                    description 'The source port,ranges from 1 to 65535.'
                                ;
                    type uint16 {
                      range 1..65535 {
                        description 'The range of port number.'
                                    ;
                      }
                    }
                    ncd:revise-date 2019-01-31 ;
                  }
                  leaf dest-port {
                    description 'The destination port,ranges from 1 to 65535.'
                                ;
                    type uint16 {
                      range 1..65535 {
                        description 'The range of port number.'
                                    ;
                      }
                    }
                    ncd:revise-date 2019-01-31 ;
                  }
                  leaf dscp {
                    description 'The value of DSCP,ranges from 0 to 63.'
                                ;
                    type uint8 {
                      range 0..63 {
                        description 'The range of DSCP.'
                                    ;
                      }
                    }
                    ncd:revise-date 2019-01-31 ;
                  }
                  container eth {
                    // if-feature eth-flow ;
                    description 'The coloring flow type is eth.'
                                ;
                    leaf source-mac {
                      description 'The source MAC address.'
                                  ;
                      type ncd:mac-address-none-zero ;
                    }
                    leaf dest-mac {
                      description 'The destination MAC address.'
                                  ;
                      type ncd:mac-address-none-zero ;
                    }
                    leaf vlan-id {
                      description 'The value of vlan ID,ranges from 1 to 4094.'
                                  ;
                      type uint16 {
                        range 1..4094 {
                          description 'The range of VLAN ID.'
                                      ;
                        }
                      }
                    }
                    leaf internal-vlan-id {
                      description 'The value of internal vlan ID,ranges from 1 '
                                + 'to 4094.'
                                  ;
                      type uint16 {
                        range 1..4094 {
                          description 'The range of internal VLAN ID.'
                                      ;
                        }
                      }
                    }
                    leaf priority-8021p {
                      description 'The value of priority-8021p,ranges from 0 to'
                                + ' 7.'
                                  ;
                      type uint8 {
                        range 0..7 {
                          description 'The range of priority-8021p.'
                                      ;
                        }
                      }
                    }
                    ncd:revise-date 2020-06-05 ;
                  }
                }
              }
              case tunnel {
                description 'The coloring flow type is TE tunnel.'
                            ;
                container tunnel {
                  // if-feature tunnel-flow ;
                  description 'The coloring flow type is TE tunnel.'
                              ;
                  leaf tunnel-id {
                    description 'Tunnel ID,the upper limit of this parameter de'
                              + 'pend on the device.'
                                ;
                    type uint32 {
                      range 1..131072 {
                        description 'The range of tunnel id.'
                                    ;
                      }
                    }
                    mandatory true ;
                  }
                }
              }
            }
          }
        }
      }
      container decapsulation {
        description 'Inband OAM flow decapsulation configuration.'
                    ;
        list decapsulation-no-ifname {
          description 'Configure flow decapsulation function.'
                      ;
          key flow-id ;
          leaf flow-id {
            description 'The flow id to identify a specific flow,ranges from 1 '
                      + 'to 1048575.'
                        ;
            type uint32 {
              range 1..1048575 {
                description 'The range of flow id,ranges from 1 to 1048575.'
                            ;
              }
            }
          }
        }
        list decapsulation-with-ifname {
          description 'Configure flow decapsulation function.'
                      ;
          key 'flow-id ifname'
              ;
          leaf flow-id {
            description 'The flow id to identify a specific flow,ranges from 1 '
                      + 'to 1048575.'
                        ;
            type uint32 {
              range 1..1048575 {
                description 'The range of flow id,ranges from 1 to 1048575.'
                            ;
              }
            }
          }
          leaf ifname {
            description 'The physical interface name passed through by the flow.'
                        ;
            type ncd:ifname {
              length 1..31 {
                description 'The range of interface name length.'
                            ;
              }
            }
          }
        }
      }
      container relations {
        // if-feature relation ;
        description 'Configure the relation between Flowid and VRF.'
                    ;
        list relation {
          description 'Configure the relation between Flowid and VRF.'
                      ;
          key flow-id ;
          leaf flow-id {
            description 'The flow id to identify a specific flow,ranges from 1 '
                      + 'to 1048575.'
                        ;
            type uint32 {
              range 1..1048575 {
                description 'The range of flow-id.'
                            ;
              }
            }
          }
          choice vpn-type {
            description 'Choose one from vrf and vpws.'
                        ;
            case vrf {
              description 'Type is VRF.'
                          ;
              leaf vrf-name {
                description 'The name of VRF,this string length ranges from 1 t'
                          + 'o 32.'
                            ;
                type string {
                  length 1..32 {
                    description 'This string length ranges from 1 to 32.'
                                ;
                  }
                }
                mandatory true ;
              }
            }
            case vpws {
              description 'Type is vpws.'
                          ;
              leaf vpws-name {
                // if-feature vpws-name ;
                description 'The name of VPWS,this string length ranges from 1 '
                          + 'to 32.'
                            ;
                type string {
                  length 1..32 {
                    description 'This string length ranges from 1 to 32.'
                                ;
                  }
                }
                mandatory true ;
              }
            }
            case evpn-vpws {
              // if-feature evpn-vpnws ;
              description 'Type is EVPN VPWS.'
                          ;
              leaf evpn-vpws-name {
                description 'EVPN VPWS name,this string length ranges from 1 to'
                          + ' 32.'
                            ;
                type string {
                  length 1..32 {
                    description 'This string length ranges from 1 to 32.'
                                ;
                  }
                }
                mandatory true ;
              }
              leaf ifname {
                description 'Access point bound to the EVPN.'
                            ;
                type ncd:ifname {
                  length 1..31 {
                    description 'The range of interface name length.'
                                ;
                  }
                }
                mandatory true ;
              }
              ncd:revise-date 2021-01-08 ;
            }
            case vpls {
              // if-feature l2vpn-vpls ;
              description 'Type is VPLS.'
                          ;
              leaf vpls-name {
                description 'The name of VPLS,this string length ranges from 1 '
                          + 'to 32.'
                            ;
                type string {
                  length 1..32 {
                    description 'This string length ranges from 1 to 32.'
                                ;
                  }
                }
              }
              ncd:revise-date 2021-01-20 ;
            }
            ncd:revise-date 2020-06-05 ;
          }
          leaf period {
            description 'The flip period of relation,range form 1000 to 900000('
                      + 'default 30000).'
                        ;
            type uint32 {
              range 1000..900000 {
                description 'The value of this parameter ranges from 1000ms to '
                          + '900000ms(default:30000ms).'
                            ;
              }
            }
            units ms ;
            default 30000 ;
            ncd:revise-date 2019-09-09 ;
          }
          leaf per-packet-dm-status {
            // if-feature per-packet-dm ;
            description 'The status of per-packet delay measurement,including e'
                      + 'nable and disable(default:enable).'
                        ;
            type enumeration {
              enum disable {
                value 0 ;
                description 'Disable per-packet DM.'
                            ;
              }
              enum enable {
                value 1 ;
                description 'Enable per-packet DM.'
                            ;
              }
            }
            default disable ;
            ncd:revise-date 2021-02-01 ;
          }
          container interfaces {
            description 'Configure interfaces of relation.'
                        ;
            list interface {
              description 'Configure interface of relation.'
                          ;
              key ifname ;
              leaf ifname {
                description 'The UNI interface name of relation.'
                            ;
                type ncd:ifname {
                  length 1..31 {
                    description 'The range of interface name length.'
                                ;
                  }
                }
              }
            }
            ncd:revise-date 2019-09-09 ;
          }
        }
        ncd:revise-date 2019-01-31 ;
      }
    }
  }
}
