module zxr10-mr-dev-upn {
  namespace 'http://www.zte.com.cn/zxr10/netconf/schema/rosng/multicast-router' ;
  prefix router-multicast ;
  import zxr10-multicast {
    prefix mr ;
  }
  organization 'ZTE Corporation' ;
  contact "ZTE Corporation  
\n"
        + "   Nanjing Institute of ZTE Corporation 
\n"
        + "   No.68 Zijinghua Rd. Yuhuatai District, Nanjing, China 
\n"
        + '   Tel: +86-25-52870000'
          ;
  description 'The netconf module of describing multicast router.' ;
  revision 2015-04-02 {
    description 'Delete the revision date of the import.' ;
  }
  revision 2014-02-13 {
    description 'Initial version' ;
  }
  deviation /mr:configuration/mr:ip-multicast/mr:multicast/mr:smdms {
    description 'This command is not supported for router.' ;
    deviate not-supported ;
  }
}
