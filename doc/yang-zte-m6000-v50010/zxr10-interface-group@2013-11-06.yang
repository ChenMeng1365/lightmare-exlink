module zxr10-interface-group {
  namespace 'http://www.zte.com.cn/zxr10/netconf/schema/rosng/interface-group' ;
  prefix interface-group ;
  import zxr10-netconf-defs {
    prefix ncd ;
  }
  organization 'ZTE Corporation' ;
  contact "ZTE Corporation  
\n"
        + "   Nanjing Institute of ZTE Corporation 
\n"
        + "   No.68 Zijinghua Rd. Yuhuatai District, Nanjing, China 
\n"
        + '   Tel: +86-25-52870000'
          ;
  description 'The netconf module to describe the Interface Relation.Like bind '
            + 'ether interfaces in the same group.'
              ;
  revision 2013-11-06 {
    description 'The initial version' ;
  }
  container configuration {
    description 'Describe the configuration of interface group' ;
    container interface-group {
      description 'Describe the parameters of interface groups to be configured' ;
      container groups {
        description 'Describe the parameters of interface groups to be configur'
                  + 'ed'
                    ;
        list group {
          description 'The list of groups for configuring parameters' ;
          key group-name ;
          leaf group-name {
            description 'The name of interface group' ;
            type string {
              length 1..31 ;
            }
          }
          list bind-interface {
            description 'The list of interfaces for configuring parameters' ;
            key interface-name ;
            leaf interface-name {
              description 'interface name' ;
              type ncd:ifname ;
            }
          }
        }
      }
    }
  }
}
