module zxr10-l2vpn-dev-t8000 {
  namespace 'http://www.zte.com.cn/zxr10/netconf/schema/rosng/l2vpn-dev-t8000'
            ;
  prefix dev-t8000 ;
  import zxr10-l2vpn {
    prefix l2vpn ;
    revision-date 2018-07-25 ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2018-12-25 {
    description 'add deviation protect-type;'
                ;
  }
  deviation '/l2vpn:configuration/l2vpn:l2vpn/l2vpn:protect-rules/l2vpn:protect'
          + '-group/l2vpn:protect-strategy/l2vpn:group-type/l2vpn:common-group/'
          + 'l2vpn:common-group-params/l2vpn:protect-type'
            {
    deviate replace {
      type enumeration {
        enum one-by-one {
          value 1 ;
          description 'The protect type of the PW protect strategy is one by on'
                    + 'e.'
                      ;
        }
      }
    }
  }
}
