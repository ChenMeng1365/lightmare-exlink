module zxr10-interface-oc {

  yang-version "1";

  // namespace
  namespace "http://www.zte.com.cn/zxr10/netconf/schema/rosng/zxr10-interface-oc";

  prefix "zte-if";

  // import some basic types
  import openconfig-interfaces { prefix oc-if; }
  import openconfig-yang-types { prefix oc-yang; }

  // meta
  organization "ZTE Corporation";
	
  contact "ZTE Corporation  \n"
        + "   Nanjing Institute of ZTE Corporation \n"
        + "   No.68 Zijinghua Rd. Yuhuatai District, Nanjing, China \n"
        + '   Tel: +86-25-52870000'
          ;

  description
    "The netconf module to describe the Interface Management";

  revision "2020-08-11" {
    description 'Remove leaf /oc-if:interfaces/oc-if:interface/oc-if:state/oc-if:counters/zte-if:in-pkts'+"\n"
              + 'Remove leaf /oc-if:interfaces/oc-if:interface/oc-if:state/oc-if:counters/zte-if:out-pkts'
                ;
  }

  revision "2020-06-15" {
    description 'Add new leaf /oc-if:interfaces/oc-if:interface/oc-if:state/oc-if:counters/zte-if:in-v4-octets'+"\n"
              + 'Add new leaf /oc-if:interfaces/oc-if:interface/oc-if:state/oc-if:counters/zte-if:out-v4-octets'+"\n"
              + 'Add new leaf /oc-if:interfaces/oc-if:interface/oc-if:state/oc-if:counters/zte-if:in-v4-pkts'+"\n"
              + 'Add new leaf /oc-if:interfaces/oc-if:interface/oc-if:state/oc-if:counters/zte-if:out-v4-pkts'+"\n"
              + 'Add new leaf /oc-if:interfaces/oc-if:interface/oc-if:state/oc-if:counters/zte-if:in-v6-octets'+"\n"
              + 'Add new leaf /oc-if:interfaces/oc-if:interface/oc-if:state/oc-if:counters/zte-if:out-v6-octets'+"\n"
              + 'Add new leaf /oc-if:interfaces/oc-if:interface/oc-if:state/oc-if:counters/zte-if:in-v6-pkts'+"\n"
              + 'Add new leaf /oc-if:interfaces/oc-if:interface/oc-if:state/oc-if:counters/zte-if:out-v6-pkts'+"\n"
              + 'Add new leaf /oc-if:interfaces/oc-if:interface/oc-if:state/oc-if:counters/zte-if:in-v4-traffic-rate'+"\n"
              + 'Add new leaf /oc-if:interfaces/oc-if:interface/oc-if:state/oc-if:counters/zte-if:in-v4-packet-rate'+"\n"
              + 'Add new leaf /oc-if:interfaces/oc-if:interface/oc-if:state/oc-if:counters/zte-if:out-v4-traffic-rate'+"\n"
              + 'Add new leaf /oc-if:interfaces/oc-if:interface/oc-if:state/oc-if:counters/zte-if:out-v4-packet-rate'+"\n"
              + 'Add new leaf /oc-if:interfaces/oc-if:interface/oc-if:state/oc-if:counters/zte-if:in-v6-traffic-rate'+"\n"
              + 'Add new leaf /oc-if:interfaces/oc-if:interface/oc-if:state/oc-if:counters/zte-if:in-v6-packet-rate'+"\n"
              + 'Add new leaf /oc-if:interfaces/oc-if:interface/oc-if:state/oc-if:counters/zte-if:out-v6-traffic-rate'+"\n"
              + 'Add new leaf /oc-if:interfaces/oc-if:interface/oc-if:state/oc-if:counters/zte-if:out-v6-packet-rate'+"\n"
              + 'Add new leaf /oc-if:interfaces/oc-if:interface/oc-if:state/oc-if:counters/zte-if:input-v4-utilization'+"\n"
              + 'Add new leaf /oc-if:interfaces/oc-if:interface/oc-if:state/oc-if:counters/zte-if:output-v4-utilization'+"\n"
              + 'Add new leaf /oc-if:interfaces/oc-if:interface/oc-if:state/oc-if:counters/zte-if:input-v6-utilization'+"\n"
              + 'Add new leaf /oc-if:interfaces/oc-if:interface/oc-if:state/oc-if:counters/zte-if:output-v6-utilization'
                ;
  }

  revision "2019-05-28" {
    description 'Add new leaf /oc-if:interfaces/oc-if:interface/oc-if:state/zte-if:phy-status'+"\n"
              + 'Add new leaf /oc-if:interfaces/oc-if:interface/oc-if:state/zte-if:ipv4-oper-status'+"\n"
              + 'Add new leaf /oc-if:interfaces/oc-if:interface/oc-if:subinterfaces/oc-if:subinterface/oc-if:state/zte-if:ipv4-oper-status'
                ;
  }

  revision "2019-04-12" {
    description 'Modify leaf /oc-if:interfaces/oc-if:interface/oc-if:state/oc-if:counters/zte-if:input-utilization'+"\n"
              + 'Modify leaf /oc-if:interfaces/oc-if:interface/oc-if:state/oc-if:counters/zte-if:output-utilization'+"\n"
              + 'Add new leaf /oc-if:interfaces/oc-if:interface/oc-if:state/oc-if:counters/zte-if:in-traffic-rate'+"\n"
              + 'Add new leaf /oc-if:interfaces/oc-if:interface/oc-if:state/oc-if:counters/zte-if:in-packet-rate'+"\n"
              + 'Add new leaf /oc-if:interfaces/oc-if:interface/oc-if:state/oc-if:counters/zte-if:out-traffic-rate'+"\n"
              + 'Add new leaf /oc-if:interfaces/oc-if:interface/oc-if:state/oc-if:counters/zte-if:out-packet-rate'
                ;
  }

  revision "2018-08-17" {
    description
      "Initial revision.";
  }

  // grouping statements

  grouping f-interface-state {
    description
      "the operational state of interface.";

     leaf phy-status {
      type enumeration {
        enum UP {
          value 1;
          description
            "Ready to pass packets.";
        }
        enum DOWN {
          value 2;
          description
            "The interface does not pass any packets.";
        }
      }
      description
        "The current physical state of the interface.";
    }

    leaf ipv4-oper-status {
      type enumeration {
        enum UP {
          value 1;
          description
            "Ready to pass packets.";
        }
        enum DOWN {
          value 2;
          description
            "The interface does not pass any packets.";
        }
      }
      description
        "The current ipv4 operational state of the interface.";
    } 
  
  }
  
  grouping s-interface-state {
    description
      "the operational state of subinterface.";  
  
    leaf ipv4-oper-status {
      type enumeration {
        enum UP {
          value 1;
          description
            "Ready to pass packets.";
        }
        enum DOWN {
          value 2;
          description
            "The interface does not pass any packets.";
        }
      }
      description
        "The current ipv4 operational state of the interface.";
    }  
  }

  grouping interface-statistics-state {
    description
      "the operational state of interface statistics.";

    leaf input-utilization {
      type decimal64 {
        fraction-digits 6;
        range "0..1.000000";
      }
      description 
      "The input utilization of bandwidith. The maximum decimal precision is 6 and 
       the specific reporting accuracy shall be subject to project customization.";
    }

    leaf output-utilization {
      type decimal64 {
        fraction-digits 6;
        range "0..1.000000";
      }
      description 
      "The output utilization of bandwidith. The maximum decimal precision is 6 and 
       the specific reporting accuracy shall be subject to project customization.";
    }

    leaf in-traffic-rate {
      type decimal64{
        fraction-digits 4;
      }
      description "The input traffic rate(unit:Mbps).";
    }

    leaf in-packet-rate {
      type decimal64{
        fraction-digits 4;
      }
      description "The input packet rate(unit:Kfps).";
    }

    leaf out-traffic-rate {
      type decimal64{
        fraction-digits 4;
      }
      description "The output traffic rate(unit:Mbps).";
    }

    leaf out-packet-rate {
      type decimal64{
        fraction-digits 4;
      }
      description "The output packet rate(unit:Kfps).";
    }

    leaf in-v4-octets {
      type oc-yang:counter64;
      description "The total number of v4 octets received on the interface.";
      }

    leaf out-v4-octets {
      type oc-yang:counter64;
      description "The total number of v4 octets sent on the interface.";
      }

    leaf in-v4-pkts {
      type oc-yang:counter64;
      description "Total v4 packets received.";
    }

    leaf out-v4-pkts {
      type oc-yang:counter64;
      description "Total v4 packets sent.";
    }
    leaf in-v6-octets {
      type oc-yang:counter64;
      description "The total number of v6 octets received on the interface.";
      }

    leaf out-v6-octets {
      type oc-yang:counter64;
      description "The total number of v6 octets sent on the interface.";
      }

    leaf in-v6-pkts {
      type oc-yang:counter64;
      description "Total v6 packets received.";
    }

    leaf out-v6-pkts {
      type oc-yang:counter64;
      description "Total v6 packets sent.";
    }

    leaf in-v4-traffic-rate {
      type decimal64{
        fraction-digits 4;
      }
      description "The input v4 traffic rate(unit:Mbps).";
    }

    leaf in-v4-packet-rate {
      type decimal64{
        fraction-digits 4;
      }
      description "The input v4 packet rate(unit:Kfps).";
    }

    leaf out-v4-traffic-rate {
      type decimal64{
        fraction-digits 4;
      }
      description "The output v4 traffic rate(unit:Mbps).";
    }

    leaf out-v4-packet-rate {
      type decimal64{
        fraction-digits 4;
      }
      description "The output v4 packet rate(unit:Kfps).";
    }

    leaf in-v6-traffic-rate {
      type decimal64{
        fraction-digits 4;
      }
      description "The input v6 traffic rate(unit:Mbps).";
    }

    leaf in-v6-packet-rate {
      type decimal64{
        fraction-digits 4;
      }
      description "The input v6 packet rate(unit:Kfps).";
    }

    leaf out-v6-traffic-rate {
      type decimal64{
        fraction-digits 4;
      }
      description "The output v6 traffic rate(unit:Mbps).";
    }

    leaf out-v6-packet-rate {
      type decimal64{
        fraction-digits 4;
      }
      description "The output v6 packet rate(unit:Kfps).";
    }

    leaf input-v4-utilization {
      type decimal64 {
        fraction-digits 6;
        range "0..1.000000";
      }
      description 
      "The input v4 utilization of bandwidith. The maximum decimal precision is 6 and 
       the specific reporting accuracy shall be subject to project customization.";
    }

    leaf output-v4-utilization {
      type decimal64 {
        fraction-digits 6;
        range "0..1.000000";
      }
      description 
      "The output v4 utilization of bandwidith. The maximum decimal precision is 6 and 
       the specific reporting accuracy shall be subject to project customization.";
    }

    leaf input-v6-utilization {
      type decimal64 {
        fraction-digits 6;
        range "0..1.000000";
      }
      description 
      "The input v6 utilization of bandwidith. The maximum decimal precision is 6 and 
       the specific reporting accuracy shall be subject to project customization.";
    }

    leaf output-v6-utilization {
      type decimal64 {
        fraction-digits 6;
        range "0..1.000000";
      }
      description 
      "The output v6 utilization of bandwidith. The maximum decimal precision is 6 and 
       the specific reporting accuracy shall be subject to project customization.";
    }

  }

  // augment statements

  augment "/oc-if:interfaces/oc-if:interface/oc-if:state" {
    description
      "Additional data for interfaces";

    uses f-interface-state;
  }
  
  augment "/oc-if:interfaces/oc-if:interface/oc-if:state/oc-if:counters" {
    description
      "Additional statistics data for interfaces";

    uses interface-statistics-state;
  }

  augment "/oc-if:interfaces/oc-if:interface/oc-if:subinterfaces/oc-if:subinterface/oc-if:state" {
    description
      "Additional data for subinterfaces";

    uses s-interface-state;
  }
  
  augment "/oc-if:interfaces/oc-if:interface/oc-if:subinterfaces/oc-if:subinterface/oc-if:state/oc-if:counters" {
    description
      "Additional statistics data for interfaces";

    uses interface-statistics-state;
  }

  // rpc statements

  // notification statements
}
