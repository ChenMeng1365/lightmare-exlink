module zxr10-ipsec-dev-t8000 {
  namespace 'http://www.zte.com.cn/zxr10/netconf/schema/rosng/ipsec-dev-t8000'
            ;
  prefix ipsec-dev-t8000 ;
  import zxr10-ipsec {
    prefix ipsec ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2017-10-16 ;
  deviation '/ipsec:configuration/ipsec:ipsec/ipsec:ipsec-tunnels/ipsec:ipsec-t'
          + 'unnel/ipsec:crypto-pki-profile'
            {
    deviate not-supported ;
  }
  deviation '/ipsec:configuration/ipsec:ipsec/ipsec:transform-sets/ipsec:transf'
          + 'orm-set/ipsec:transforms/ipsec:trans-ah'
            {
    deviate replace {
      type enumeration {
        enum ah-md5-hmac {
          value 2 ;
          description 'AH-HMAC-MD5 transform'
                      ;
        }
        enum ah-sha-hmac {
          value 3 ;
          description 'AH-HMAC-SHA transform'
                      ;
        }
        enum ah-sha256-hmac {
          value 5 ;
          description 'AH-HMAC-SHA256 transform'
                      ;
        }
        enum ah-sha384-hmac {
          value 6 ;
          description 'AH-HMAC-SHA384 transform'
                      ;
        }
        enum ah-sha512-hmac {
          value 7 ;
          description AH-HMAC-SHA512transform ;
        }
      }
    }
  }
  deviation '/ipsec:configuration/ipsec:ipsec/ipsec:transform-sets/ipsec:transf'
          + 'orm-set/ipsec:transforms/ipsec:trans-esp-hmac'
            {
    deviate replace {
      type enumeration {
        enum esp-md5-hmac {
          value 1 ;
          description 'ESP transform using HMAC-MD5 auth'
                      ;
        }
        enum esp-sha-hmac {
          value 2 ;
          description 'ESP transform using HMAC-SHA auth'
                      ;
        }
        enum esp-sha256-hmac {
          value 5 ;
          description 'ESP transform using HMAC-SHA256 auth'
                      ;
        }
        enum esp-sha384-hmac {
          value 6 ;
          description 'ESP transform using HMAC-SHA384 auth'
                      ;
        }
        enum esp-sha512-hmac {
          value 7 ;
          description 'ESP transform using HMAC-SHA512 auth'
                      ;
        }
      }
    }
  }
  deviation '/ipsec:configuration/ipsec:ipsec/ipsec:transform-sets/ipsec:transf'
          + 'orm-set/ipsec:transforms/ipsec:trans-esp-cipher'
            {
    deviate replace {
      type enumeration {
        enum esp-des {
          value 2 ;
          description 'ESP transform using DES cipher (56 bits)'
                      ;
        }
        enum esp-3des {
          value 3 ;
          description 'ESP transform using 3DES(EDE) cipher (168 bits)'
                      ;
        }
        enum esp-null {
          value 11 ;
          description 'ESP transform w/o cipher'
                      ;
        }
        enum esp-aes-128 {
          value 12 ;
          description 'ESP transform using AES cipher(128 bits)'
                      ;
        }
        enum esp-aes-192 {
          value 1012 ;
          description 'ESP transform using AES cipher(192 bits)'
                      ;
        }
        enum esp-aes-256 {
          value 2012 ;
          description 'ESP transform using AES cipher(256 bits)'
                      ;
        }
      }
    }
  }
}
