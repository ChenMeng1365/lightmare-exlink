module zxr10-ospfv3 {
  namespace 'http://www.zte.com.cn/zxr10/netconf/schema/rosng/ospfv3'
            ;
  prefix ospfv3 ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module of describing OSPFv3.'
              ;
  revision 2021-01-08 {
    description 'Add some containers and leafs:'+"\n"
              + '/ospfv3:configuration/ospfv3:ospfv3/ospfv3:processes/ospfv3:pr'
              + 'ocess/ospfv3:segment-routing/ospfv3:srv6/ospfv3:locators/ospfv'
              + '3:locator/ospfv3:end-sid-auto'+"\n"
              + '/ospfv3:configuration/ospfv3:ospfv3/ospfv3:processes/ospfv3:pr'
              + 'ocess/ospfv3:segment-routing/ospfv3:srv6/ospfv3:locators/ospfv'
              + '3:locator/ospfv3:end-sid-auto/ospfv3:psp'+"\n"
              + '/ospfv3:configuration/ospfv3:ospfv3/ospfv3:processes/ospfv3:pr'
              + 'ocess/ospfv3:segment-routing/ospfv3:srv6/ospfv3:locators/ospfv'
              + '3:locator/ospfv3:end-sid-auto/ospfv3:usp'+"\n"
              + '/ospfv3:configuration/ospfv3:ospfv3/ospfv3:processes/ospfv3:pr'
              + 'ocess/ospfv3:segment-routing/ospfv3:srv6/ospfv3:locators/ospfv'
              + '3:locator/ospfv3:end-x-sid-auto'+"\n"
              + '/ospfv3:configuration/ospfv3:ospfv3/ospfv3:processes/ospfv3:pr'
              + 'ocess/ospfv3:segment-routing/ospfv3:srv6/ospfv3:locators/ospfv'
              + '3:locator/ospfv3:end-x-sid-auto/ospfv3:psp'+"\n"
              + '/ospfv3:configuration/ospfv3:ospfv3/ospfv3:processes/ospfv3:pr'
              + 'ocess/ospfv3:segment-routing/ospfv3:srv6/ospfv3:locators/ospfv'
              + '3:locator/ospfv3:end-x-sid-auto/ospfv3:usp'
                ;
  }
  revision 2020-10-20 {
    description 'modify leaf:&#xD;'+"\n"
              + '/ospfv3:configuration/ospfv3:ospfv3/ospfv3:processes/ospfv3:pr'
              + 'ocess/ospfv3:frr-policy/ospfv3:route-policy/ospfv3:intfs/ospfv'
              + '3:route-policy-name&#xD;'+"\n"
              + '/ospfv3:configuration/ospfv3:ospfv3/ospfv3:processes/ospfv3:pr'
              + 'ocess/ospfv3:distance-policy/ospfv3:policy-name'
                ;
  }
  revision 2020-09-23 {
    description 'Add some containers,lists and leafs:'+"\n"
              + '/ospfv3:configuration/ospfv3:ospfv3/ospfv3:processes/ospfv3:pr'
              + 'ocess/ospfv3:segment-routing/ospfv3:srv6/ospfv3:locators'+"\n"
              + '/ospfv3:configuration/ospfv3:ospfv3/ospfv3:processes/ospfv3:pr'
              + 'ocess/ospfv3:segment-routing/ospfv3:srv6/ospfv3:locators/ospfv'
              + '3:locator'+"\n"
              + '/ospfv3:configuration/ospfv3:ospfv3/ospfv3:processes/ospfv3:pr'
              + 'ocess/ospfv3:segment-routing/ospfv3:srv6/ospfv3:locators/ospfv'
              + '3:locator/ospfv3:locator-name'+"\n"
              + '/ospfv3:configuration/ospfv3:ospfv3/ospfv3:processes/ospfv3:pr'
              + 'ocess/ospfv3:segment-routing/ospfv3:srv6/ospfv3:locators/ospfv'
              + '3:locator/ospfv3:end-sids'+"\n"
              + '/ospfv3:configuration/ospfv3:ospfv3/ospfv3:processes/ospfv3:pr'
              + 'ocess/ospfv3:segment-routing/ospfv3:srv6/ospfv3:locators/ospfv'
              + '3:locator/ospfv3:end-sids/ospfv3:end-sid'+"\n"
              + '/ospfv3:configuration/ospfv3:ospfv3/ospfv3:processes/ospfv3:pr'
              + 'ocess/ospfv3:segment-routing/ospfv3:srv6/ospfv3:locators/ospfv'
              + '3:locator/ospfv3:end-sids/ospfv3:end-sid/ospfv3:func-code'+"\n"
              + '/ospfv3:configuration/ospfv3:ospfv3/ospfv3:processes/ospfv3:pr'
              + 'ocess/ospfv3:segment-routing/ospfv3:srv6/ospfv3:locators/ospfv'
              + '3:locator/ospfv3:end-sids/ospfv3:end-sid/ospfv3:psp'+"\n"
              + '/ospfv3:configuration/ospfv3:ospfv3/ospfv3:processes/ospfv3:pr'
              + 'ocess/ospfv3:segment-routing/ospfv3:srv6/ospfv3:locators/ospfv'
              + '3:locator/ospfv3:end-sids/ospfv3:end-sid/ospfv3:usp'+"\n"
              + '/ospfv3:configuration/ospfv3:ospfv3/ospfv3:processes/ospfv3:pr'
              + 'ocess/ospfv3:segment-routing/ospfv3:srv6/ospfv3:locators/ospfv'
              + '3:locator/ospfv3:end-x-sids'+"\n"
              + '/ospfv3:configuration/ospfv3:ospfv3/ospfv3:processes/ospfv3:pr'
              + 'ocess/ospfv3:segment-routing/ospfv3:srv6/ospfv3:locators/ospfv'
              + '3:locator/ospfv3:end-x-sids/ospfv3:end-x-sid'+"\n"
              + '/ospfv3:configuration/ospfv3:ospfv3/ospfv3:processes/ospfv3:pr'
              + 'ocess/ospfv3:segment-routing/ospfv3:srv6/ospfv3:locators/ospfv'
              + '3:locator/ospfv3:end-x-sids/ospfv3:end-x-sid/ospfv3:func-code'+"\n"
              + '/ospfv3:configuration/ospfv3:ospfv3/ospfv3:processes/ospfv3:pr'
              + 'ocess/ospfv3:segment-routing/ospfv3:srv6/ospfv3:locators/ospfv'
              + '3:locator/ospfv3:end-x-sids/ospfv3:end-x-sid/ospfv3:interface-'
              + 'name'+"\n"
              + '/ospfv3:configuration/ospfv3:ospfv3/ospfv3:processes/ospfv3:pr'
              + 'ocess/ospfv3:segment-routing/ospfv3:srv6/ospfv3:locators/ospfv'
              + '3:locator/ospfv3:end-x-sids/ospfv3:end-x-sid/ospfv3:neighbor-i'
              + 'd'+"\n"
              + '/ospfv3:configuration/ospfv3:ospfv3/ospfv3:processes/ospfv3:pr'
              + 'ocess/ospfv3:segment-routing/ospfv3:srv6/ospfv3:locators/ospfv'
              + '3:locator/ospfv3:end-x-sids/ospfv3:end-x-sid/ospfv3:psp'+"\n"
              + '/ospfv3:configuration/ospfv3:ospfv3/ospfv3:processes/ospfv3:pr'
              + 'ocess/ospfv3:segment-routing/ospfv3:srv6/ospfv3:locators/ospfv'
              + '3:locator/ospfv3:end-x-sids/ospfv3:end-x-sid/ospfv3:usp'
                ;
  }
  revision 2020-09-12 {
    description 'Add a container and leafs:'+"\n"
              + '/ospfv3:configuration/ospfv3:ospfv3/ospfv3:processes/ospfv3:pr'
              + 'ocess/ospfv3:areas/ospfv3:area/ospfv3:interfaces/ospfv3:interf'
              + 'ace/ospfv3:link-sd'+"\n"
              + '/ospfv3:configuration/ospfv3:ospfv3/ospfv3:processes/ospfv3:pr'
              + 'ocess/ospfv3:areas/ospfv3:area/ospfv3:interfaces/ospfv3:interf'
              + 'ace/ospfv3:link-sd/ospfv3:cost'+"\n"
              + '/ospfv3:configuration/ospfv3:ospfv3/ospfv3:processes/ospfv3:pr'
              + 'ocess/ospfv3:areas/ospfv3:area/ospfv3:interfaces/ospfv3:interf'
              + 'ace/ospfv3:link-sd/ospfv3:cost/ospfv3:cost'+"\n"
              + '/ospfv3:configuration/ospfv3:ospfv3/ospfv3:processes/ospfv3:pr'
              + 'ocess/ospfv3:areas/ospfv3:area/ospfv3:interfaces/ospfv3:interf'
              + 'ace/ospfv3:link-sd/ospfv3:cost/ospfv3:cost/ospfv3:maximum'+"\n"
              + '/ospfv3:configuration/ospfv3:ospfv3/ospfv3:processes/ospfv3:pr'
              + 'ocess/ospfv3:areas/ospfv3:area/ospfv3:interfaces/ospfv3:interf'
              + 'ace/ospfv3:link-sd/ospfv3:cost/ospfv3:cost/ospfv3:maximum/ospf'
              + 'v3:maximum'+"\n"
              + '/ospfv3:configuration/ospfv3:ospfv3/ospfv3:processes/ospfv3:pr'
              + 'ocess/ospfv3:areas/ospfv3:area/ospfv3:interfaces/ospfv3:interf'
              + 'ace/ospfv3:link-sd/ospfv3:cost/ospfv3:cost/ospfv3:increase-val'
              + 'ue'+"\n"
              + '/ospfv3:configuration/ospfv3:ospfv3/ospfv3:processes/ospfv3:pr'
              + 'ocess/ospfv3:areas/ospfv3:area/ospfv3:interfaces/ospfv3:interf'
              + 'ace/ospfv3:link-sd/ospfv3:cost/ospfv3:cost/ospfv3:increase-val'
              + 'ue/ospfv3:increase-value'
                ;
  }
  revision 2020-08-20 {
    description 'Add a container and leafs:'+"\n"
              + '/ospfv3:configuration/ospfv3:ospfv3/ospfv3:processes/ospfv3:pr'
              + 'ocess/ospfv3:areas/ospfv3:area/ospfv3:multi-area-interfaces'+"\n"
              + '/ospfv3:configuration/ospfv3:ospfv3/ospfv3:processes/ospfv3:pr'
              + 'ocess/ospfv3:areas/ospfv3:area/ospfv3:multi-area-interfaces/os'
              + 'pfv3:multi-area-interface/interface-name'+"\n"
              + '/ospfv3:configuration/ospfv3:ospfv3/ospfv3:processes/ospfv3:pr'
              + 'ocess/ospfv3:areas/ospfv3:area/ospfv3:multi-area-interfaces/os'
              + 'pfv3:multi-area-interface/hello-interval'+"\n"
              + '/ospfv3:configuration/ospfv3:ospfv3/ospfv3:processes/ospfv3:pr'
              + 'ocess/ospfv3:areas/ospfv3:area/ospfv3:multi-area-interfaces/os'
              + 'pfv3:multi-area-interface/dead-interval'+"\n"
              + '/ospfv3:configuration/ospfv3:ospfv3/ospfv3:processes/ospfv3:pr'
              + 'ocess/ospfv3:areas/ospfv3:area/ospfv3:multi-area-interfaces/os'
              + 'pfv3:multi-area-interface/cost'+"\n"
              + '/ospfv3:configuration/ospfv3:ospfv3/ospfv3:processes/ospfv3:pr'
              + 'ocess/ospfv3:areas/ospfv3:area/ospfv3:multi-area-interfaces/os'
              + 'pfv3:multi-area-interface/mtu-ignore'+"\n"
              + '/ospfv3:configuration/ospfv3:ospfv3/ospfv3:processes/ospfv3:pr'
              + 'ocess/ospfv3:areas/ospfv3:area/ospfv3:multi-area-interfaces/os'
              + 'pfv3:multi-area-interface/retransmit-delay'+"\n"
              + '/ospfv3:configuration/ospfv3:ospfv3/ospfv3:processes/ospfv3:pr'
              + 'ocess/ospfv3:areas/ospfv3:area/ospfv3:multi-area-interfaces/os'
              + 'pfv3:multi-area-interface/transmit-delay'+"\n"
              + '/ospfv3:configuration/ospfv3:ospfv3/ospfv3:processes/ospfv3:pr'
              + 'ocess/ospfv3:areas/ospfv3:area/ospfv3:multi-area-interfaces/os'
              + 'pfv3:multi-area-interface/authentication'+"\n"
              + '/ospfv3:configuration/ospfv3:ospfv3/ospfv3:processes/ospfv3:pr'
              + 'ocess/ospfv3:areas/ospfv3:area/ospfv3:multi-area-interfaces/os'
              + 'pfv3:multi-area-interface/authentication/keychain'
                ;
  }
  revision 2020-07-23 {
    description 'add leaf:/ospfv3:configuration/ospfv3:ospfv3/ospfv3:processes/'
              + 'ospfv3:process/ospfv3:suppress-flapping/ospfv3:adjacency/ospfv'
              + '3:capability'+"\n"
              + 'add container:/ospfv3:configuration/ospfv3:ospfv3/ospfv3:proce'
              + 'sses/ospfv3:process/ospfv3:areas/ospfv3:area/ospfv3:interfaces'
              + '/ospfv3:interface/ospfv3:suppress-flapping'
                ;
  }
  revision 2020-07-15 {
    description 'Add three containers and a leaf:'+"\n"
              + '/ospfv3:configuration/ospfv3:ospfv3/ospfv3:processes/ospfv3:pr'
              + 'ocess/ospfv3:max-metric'+"\n"
              + '/ospfv3:configuration/ospfv3:ospfv3/ospfv3:processes/ospfv3:pr'
              + 'ocess/ospfv3:max-metric/ospfv3:router-lsa'+"\n"
              + '/ospfv3:configuration/ospfv3:ospfv3/ospfv3:processes/ospfv3:pr'
              + 'ocess/ospfv3:max-metric/ospfv3:router-lsa/ospfv3:on-startup'+"\n"
              + '/ospfv3:configuration/ospfv3:ospfv3/ospfv3:processes/ospfv3:pr'
              + 'ocess/ospfv3:max-metric/ospfv3:router-lsa/ospfv3:on-startup/ti'
              + 'meout'
                ;
  }
  revision 2020-07-14 {
    description 'chg ciphertext len from 108 to 128'+"\n"
              + '/ospfv3:configuration/ospfv3:ospfv3/ospfv3:processes/ospfv3:pr'
              + 'ocess/ospfv3:areas/ospfv3:area/ospfv3:ipsec/ospfv3:ipsec/ospfv'
              + '3:authentication/ospfv3:authentication'+"\n"
              + '/ospfv3:configuration/ospfv3:ospfv3/ospfv3:processes/ospfv3:pr'
              + 'ocess/ospfv3:areas/ospfv3:area/ospfv3:ipsec/ospfv3:ipsec/ospfv'
              + '3:encryption/ospfv3:encryption'+"\n"
              + ''+"\n"
              + ''+"\n"
              + '/ospfv3:configuration/ospfv3:ospfv3/ospfv3:processes/ospfv3:pr'
              + 'ocess/ospfv3:areas/ospfv3:area/ospfv3:interface/ospfv3:interfa'
              + 'ce/ospfv3:ipsec/ospfv3:ipsec/ospfv3:encryption/ospfv3:encrypti'
              + 'on'+"\n"
              + '/ospfv3:configuration/ospfv3:ospfv3/ospfv3:processes/ospfv3:pr'
              + 'ocess/ospfv3:areas/ospfv3:area/ospfv3:interface/ospfv3:interfa'
              + 'ce/ospfv3:ipsec/ospfv3:ipsec/ospfv3:authentication/ospfv3:auth'
              + 'entication'+"\n"
              + ''+"\n"
              + ''+"\n"
              + ''+"\n"
              + '/ospfv3:configuration/ospfv3:ospfv3/ospfv3:processes/ospfv3:pr'
              + 'ocess/ospfv3:areas/ospfv3:area/ospfv3:virtual-link/ospfv3:virt'
              + 'ual-link/ospfv3:ipsec/ospfv3:ipsec/ospfv3:encryption/ospfv3:en'
              + 'cryption'+"\n"
              + '/ospfv3:configuration/ospfv3:ospfv3/ospfv3:processes/ospfv3:pr'
              + 'ocess/ospfv3:areas/ospfv3:area/ospfv3:virtual-link/ospfv3:virt'
              + 'ual-link/ospfv3:ipsec/ospfv3:ipsec/ospfv3:authentication/ospfv'
              + '3:authentication'
                ;
  }
  revision 2020-07-03 {
    description 'chg ciphertext or plaintext'+"\n"
              + '/ospfv3:configuration/ospfv3:ospfv3/ospfv3:processes/ospfv3:pr'
              + 'ocess/ospfv3:areas/ospfv3:area/ospfv3:ipsec/ospfv3:ipsec/ospfv'
              + '3:authentication/ospfv3:authentication'+"\n"
              + '/ospfv3:configuration/ospfv3:ospfv3/ospfv3:processes/ospfv3:pr'
              + 'ocess/ospfv3:areas/ospfv3:area/ospfv3:ipsec/ospfv3:ipsec/ospfv'
              + '3:encryption/ospfv3:encryption'+"\n"
              + ''+"\n"
              + ''+"\n"
              + '/ospfv3:configuration/ospfv3:ospfv3/ospfv3:processes/ospfv3:pr'
              + 'ocess/ospfv3:areas/ospfv3:area/ospfv3:interface/ospfv3:interfa'
              + 'ce/ospfv3:ipsec/ospfv3:ipsec/ospfv3:encryption/ospfv3:encrypti'
              + 'on'+"\n"
              + '/ospfv3:configuration/ospfv3:ospfv3/ospfv3:processes/ospfv3:pr'
              + 'ocess/ospfv3:areas/ospfv3:area/ospfv3:interface/ospfv3:interfa'
              + 'ce/ospfv3:ipsec/ospfv3:ipsec/ospfv3:authentication/ospfv3:auth'
              + 'entication'+"\n"
              + ''+"\n"
              + ''+"\n"
              + ''+"\n"
              + '/ospfv3:configuration/ospfv3:ospfv3/ospfv3:processes/ospfv3:pr'
              + 'ocess/ospfv3:areas/ospfv3:area/ospfv3:virtual-link/ospfv3:virt'
              + 'ual-link/ospfv3:ipsec/ospfv3:ipsec/ospfv3:encryption/ospfv3:en'
              + 'cryption'+"\n"
              + '/ospfv3:configuration/ospfv3:ospfv3/ospfv3:processes/ospfv3:pr'
              + 'ocess/ospfv3:areas/ospfv3:area/ospfv3:virtual-link/ospfv3:virt'
              + 'ual-link/ospfv3:ipsec/ospfv3:ipsec/ospfv3:authentication/ospfv'
              + '3:authentication'
                ;
  }
  revision 2020-06-21 {
    description 'Modify range:'+"\n"
              + '/ospfv3:configuration/ospfv3:ospfv3/ospfv3:processes/ospfv3:pr'
              + 'ocess/ospfv3:distribute-list/ospfv3:distribute-list-in/ospfv3:'
              + 'policy-name/ospfv3:route-map/ospfv3:route-map-name'+"\n"
              + '/ospfv3:configuration/ospfv3:ospfv3/ospfv3:processes/ospfv3:pr'
              + 'ocess/ospfv3:redistribute/ospfv3:redistribute-ospf/ospfv3:redi'
              + 'stribute-ospf/ospfv3:route-map-name'+"\n"
              + '/ospfv3:configuration/ospfv3:ospfv3/ospfv3:processes/ospfv3:pr'
              + 'ocess/ospfv3:redistribute/ospfv3:redistribute-isis/ospfv3:redi'
              + 'stribute-isis/ospfv3:route-map-name'+"\n"
              + '/ospfv3:configuration/ospfv3:ospfv3/ospfv3:processes/ospfv3:pr'
              + 'ocess/ospfv3:redistribute/ospfv3:redistribute-other/ospfv3:red'
              + 'istribute-other/ospfv3:route-map-name'+"\n"
              + '/ospfv3:configuration/ospfv3:ospfv3/ospfv3:processes/ospfv3:pr'
              + 'ocess/ospfv3:redistribute/ospfv3:redistribute-ps/ospfv3:redist'
              + 'ribute-ps/ospfv3:route-map-name'+"\n"
              + '/ospfv3:configuration/ospfv3:ospfv3/ospfv3:processes/ospfv3:pr'
              + 'ocess/ospfv3:notify-default-route/ospfv3:route-map'+"\n"
              + '/ospfv3:configuration/ospfv3:ospfv3/ospfv3:processes/ospfv3:pr'
              + 'ocess/ospfv3:prefix-priority/ospfv3:prefix-lists/ospfv3:prefix'
              + '-list/ospfv3:prefix-name'
                ;
  }
  revision 2020-06-02 {
    description 'Add three new leafs:'+"\n"
              + '/ospfv3:configuration/ospfv3:ospfv3/ospfv3:processes/ospfv3:pr'
              + 'ocess/ospfv3:bfd-template'+"\n"
              + '/ospfv3:configuration/ospfv3:ospfv3/ospfv3:processes/ospfv3:pr'
              + 'ocess/ospfv3:areas/ospfv3:area/ospfv3:bfd-template'+"\n"
              + '/ospfv3:configuration/ospfv3:ospfv3/ospfv3:processes/ospfv3:pr'
              + 'ocess/ospfv3:areas/ospfv3:area/ospfv3:interfaces/ospfv3:interf'
              + 'ace/ospfv3:bfd-template'
                ;
  }
  revision 2020-05-21 {
    description 'Add new container:'+"\n"
              + '/ospfv3:configuration/ospfv3:ospfv3/ospfv3:processes/ospfv3:pr'
              + 'ocess/ospfv3:areas/ospfv3:area/ospfv3:nssa'+"\n"
              + 'Add new container:'+"\n"
              + '/ospfv3:configuration/ospfv3:ospfv3/ospfv3:processes/ospfv3:pr'
              + 'ocess/ospfv3:areas/ospfv3:area/ospfv3:nssa/ospfv3:default-info'
              + 'rmation-originate'+"\n"
              + 'Add new leaf:'+"\n"
              + '/ospfv3:configuration/ospfv3:ospfv3/ospfv3:processes/ospfv3:pr'
              + 'ocess/ospfv3:areas/ospfv3:area/ospfv3:nssa/ospfv3:default-info'
              + 'rmation-originate/ospfv3:metric'+"\n"
              + 'Add new leaf:'+"\n"
              + '/ospfv3:configuration/ospfv3:ospfv3/ospfv3:processes/ospfv3:pr'
              + 'ocess/ospfv3:areas/ospfv3:area/ospfv3:nssa/ospfv3:default-info'
              + 'rmation-originate/ospfv3:metric-type'+"\n"
              + 'Add new leaf:'+"\n"
              + '/ospfv3:configuration/ospfv3:ospfv3/ospfv3:processes/ospfv3:pr'
              + 'ocess/ospfv3:areas/ospfv3:area/ospfv3:nssa/ospfv3:translator-r'
              + 'ole'+"\n"
              + 'Add new leaf:'+"\n"
              + '/ospfv3:configuration/ospfv3:ospfv3/ospfv3:processes/ospfv3:pr'
              + 'ocess/ospfv3:areas/ospfv3:area/ospfv3:nssa/ospfv3:trans-stab-i'
              + 'nterval'+"\n"
              + 'Add new leaf:'+"\n"
              + '/ospfv3:configuration/ospfv3:ospfv3/ospfv3:processes/ospfv3:pr'
              + 'ocess/ospfv3:areas/ospfv3:area/ospfv3:nssa/ospfv3:no-summary'+"\n"
              + 'Add new leaf:'+"\n"
              + '/ospfv3:configuration/ospfv3:ospfv3/ospfv3:processes/ospfv3:pr'
              + 'ocess/ospfv3:areas/ospfv3:area/ospfv3:nssa/ospfv3:no-redistrib'
              + 'ution'+"\n"
              + 'Add new leaf:'+"\n"
              + '/ospfv3:configuration/ospfv3:ospfv3/ospfv3:processes/ospfv3:pr'
              + 'ocess/ospfv3:areas/ospfv3:area/ospfv3:nssa/ospfv3:suppress-fa'+"\n"
              + 'Add new list:'+"\n"
              + '/ospfv3:configuration/ospfv3:ospfv3/ospfv3:processes/ospfv3:pr'
              + 'ocess/ospfv3:areas/ospfv3:area/ospfv3:ranges/ospfv3:nssa-range'
              + ''+"\n"
              + 'Add new leaf:'+"\n"
              + '/ospfv3:configuration/ospfv3:ospfv3/ospfv3:processes/ospfv3:pr'
              + 'ocess/ospfv3:areas/ospfv3:area/ospfv3:ranges/ospfv3:nssa-range'
              + '/ospfv3:prefix'+"\n"
              + 'Add new leaf:'+"\n"
              + '/ospfv3:configuration/ospfv3:ospfv3/ospfv3:processes/ospfv3:pr'
              + 'ocess/ospfv3:areas/ospfv3:area/ospfv3:ranges/ospfv3:nssa-range'
              + '/ospfv3:prefix-len'+"\n"
              + 'Add new leaf:'+"\n"
              + '/ospfv3:configuration/ospfv3:ospfv3/ospfv3:processes/ospfv3:pr'
              + 'ocess/ospfv3:areas/ospfv3:area/ospfv3:ranges/ospfv3:nssa-range'
              + '/ospfv3:not-advertise'+"\n"
              + 'Add new leaf:'+"\n"
              + '/ospfv3:configuration/ospfv3:ospfv3/ospfv3:processes/ospfv3:pr'
              + 'ocess/ospfv3:areas/ospfv3:area/ospfv3:ranges/ospfv3:nssa-range'
              + '/ospfv3:metric'+"\n"
              + 'Add new leaf:'+"\n"
              + '/ospfv3:configuration/ospfv3:ospfv3/ospfv3:processes/ospfv3:pr'
              + 'ocess/ospfv3:areas/ospfv3:area/ospfv3:ranges/ospfv3:nssa-range'
              + '/ospfv3:tag'
                ;
  }
  revision 2020-04-10 {
    description 'Add new container:'+"\n"
              + '/ospfv3:configuration/ospfv3:ospfv3/ospfv3:processes/ospfv3:pr'
              + 'ocess/ospfv3:areas/ospfv3:area/ospfv3:interfaces/ospfv3:interf'
              + 'ace/ospfv3:ti-lfa'+"\n"
              + 'Add new list:'+"\n"
              + '/ospfv3:configuration/ospfv3:ospfv3/ospfv3:processes/ospfv3:pr'
              + 'ocess/ospfv3:areas/ospfv3:area/ospfv3:interfaces/ospfv3:interf'
              + 'ace/ospfv3:ti-lfa/ospfv3:srlg'+"\n"
              + 'Add new leaf:'+"\n"
              + '/ospfv3:configuration/ospfv3:ospfv3/ospfv3:processes/ospfv3:pr'
              + 'ocess/ospfv3:areas/ospfv3:area/ospfv3:interfaces/ospfv3:interf'
              + 'ace/ospfv3:ti-lfa/ospfv3:srlg/ospfv3:srlg-id'
                ;
  }
  revision 2020-03-28 {
    description 'Add new leaf:'+"\n"
              + '/ospfv3:configuration/ospfv3:ospfv3/ospfv3:processes/ospfv3:pr'
              + 'ocess/ospfv3:segment-routing/ospfv3:mpls/ospfv3:adj-sid/ospfv3'
              + ':type'
                ;
  }
  revision 2020-02-19 {
    description 'add leaf:'+"\n"
              + '/ospfv3:configuration/ospfv3:ospfv3/ospfv3:processes/ospfv3:pr'
              + 'ocess/ospfv3:te-link-delay'
                ;
  }
  revision 2019-12-16 {
    description 'IPSEC add encrpted key leafnode'
                ;
  }
  revision 2019-11-24 {
    description "Feature 'segment-routing' add new project-label-info.
\nFeatur"
              + "e'distance-policy' add new project-label-info."
                ;
  }
  revision 2019-11-23 {
    description 'Add new container:'+"\n"
              + '/ospfv3:configuration/ospfv3:ospfv3/ospfv3:processes/ospfv3:pr'
              + 'ocess/ospfv3:areas/ospfv3:area/ospfv3:interfaces/ospfv3:interf'
              + 'ace/ospfv3:cost-bfd-down'+"\n"
              + 'Add new leaf:'+"\n"
              + '/ospfv3:configuration/ospfv3:ospfv3/ospfv3:processes/ospfv3:pr'
              + 'ocess/ospfv3:areas/ospfv3:area/ospfv3:interfaces/ospfv3:interf'
              + 'ace/ospfv3:cost-bfd-down/ospfv3:cost-bfd-down/ospfv3:increase-'
              + 'value/ospfv3:increase-value'+"\n"
              + 'Add new leaf:'+"\n"
              + '/ospfv3:configuration/ospfv3:ospfv3/ospfv3:processes/ospfv3:pr'
              + 'ocess/ospfv3:areas/ospfv3:area/ospfv3:interfaces/ospfv3:interf'
              + 'ace/ospfv3:cost-bfd-down/ospfv3:cost-bfd-down/ospfv3:maximum/o'
              + 'spfv3:maximum'
                ;
  }
  revision 2019-11-13 {
    description 'Add new container:'+"\n"
              + '/ospfv3:configuration/ospfv3:ospfv3/ospfv3:processes/ospfv3:pr'
              + 'ocess/ospfv3:segment-routing/ospfv3:mpls/ospfv3:entropy/ospfv3'
              + ':capability'
                ;
  }
  revision 2019-10-17 {
    description 'Add new container:'+"\n"
              + '/ospfv3:configuration/ospfv3:ospfv3/ospfv3:processes/ospfv3:pr'
              + 'ocess/ospfv3:microloop-prevention'
                ;
  }
  revision 2019-10-08 {
    description 'Add new container:'+"\n"
              + '/ospfv3:configuration/ospfv3:ospfv3/ospfv3:processes/ospfv3:pr'
              + 'ocess/ospfv3:frr'
                ;
  }
  revision 2019-08-20 {
    description 'Add new container:'+"\n"
              + '/ospfv3:configuration/ospfv3:ospfv3/ospfv3:processes/ospfv3:pr'
              + 'ocess/ospfv3:segment-routing/ospfv3:srv6'+"\n"
              + 'Add new container:'+"\n"
              + '/ospfv3:configuration/ospfv3:ospfv3/ospfv3:processes/ospfv3:pr'
              + 'ocess/ospfv3:areas/ospfv3:area/ospfv3:interfaces/ospfv3:interf'
              + 'ace/ospfv3:segment-routing/ospfv3:srv6'
                ;
  }
  revision 2019-08-03 {
    description 'Add new container:'+"\n"
              + '/ospfv3:configuration/ospfv3:ospfv3/ospfv3:processes/ospfv3:pr'
              + 'ocess/ospfv3:areas/ospfv3:area/ospfv3:interfaces/ospfv3:interf'
              + 'ace/ospfv3:cost-lag-down'+"\n"
              + 'Add new leaf:'+"\n"
              + '/ospfv3:configuration/ospfv3:ospfv3/ospfv3:processes/ospfv3:pr'
              + 'ocess/ospfv3:areas/ospfv3:area/ospfv3:interfaces/ospfv3:interf'
              + 'ace/ospfv3:cost-lag-down/ospfv3:cost-lag-down/ospfv3:increase-'
              + 'value/ospfv3:increase-value'+"\n"
              + 'Add new leaf:'+"\n"
              + '/ospfv3:configuration/ospfv3:ospfv3/ospfv3:processes/ospfv3:pr'
              + 'ocess/ospfv3:areas/ospfv3:area/ospfv3:interfaces/ospfv3:interf'
              + 'ace/ospfv3:cost-lag-down/ospfv3:cost-lag-down/ospfv3:maximum/o'
              + 'spfv3:maximum'
                ;
  }
  revision 2019-07-11 {
    description 'Add new container:'+"\n"
              + '/ospfv3:configuration/ospfv3:ospfv3/ospfv3:processes/ospfv3:pr'
              + 'ocess/ospfv3:bgp-ls'+"\n"
              + 'Add new leaf:'+"\n"
              + '/ospfv3:configuration/ospfv3:ospfv3/ospfv3:processes/ospfv3:pr'
              + 'ocess/ospfv3:bgp-ls/ospfv3:instance-id'
                ;
  }
  revision 2019-06-20 {
    description '1.Add a new leaf:'+"\n"
              + '/ospfv3:configuration/ospfv3:ospfv3/ospfv3:processes/ospfv3:pr'
              + 'ocess/ospfv3:redistribute/ospfv3:redistribute/ospfv3:redistrib'
              + 'ute/ospfv3:host-only'
                ;
  }
  revision 2019-03-28 {
    description 'Add new container:'+"\n"
              + '/ospfv3:configuration/ospfv3:ospfv3/ospfv3:processes/ospfv3:pr'
              + 'ocess/ospfv3:segment-routing'
                ;
  }
  revision 2019-03-08 {
    description '1.Add a new enum type:'+"\n"
              + '/ospfv3:configuration/ospfv3:ospfv3/ospfv3:processes/ospfv3:pr'
              + 'ocess/ospfv3:redistribute/ospfv3:redistribute-other/ospfv3:red'
              + 'istribute-other/ospfv3:protocol'
                ;
  }
  revision 2018-11-28 {
    description 'Add new container:'+"\n"
              + '/ospfv3:configuration/ospfv3:ospfv3/ospfv3:processes/ospfv3:pr'
              + 'ocess/ospfv3:distance-policy'+"\n"
              + 'Add new leaf:'+"\n"
              + '/ospfv3:configuration/ospfv3:ospfv3/ospfv3:processes/ospfv3:pr'
              + 'ocess/ospfv3:distance-policy/ospfv3:policy-type'+"\n"
              + 'Add new leaf:'+"\n"
              + '/ospfv3:configuration/ospfv3:ospfv3/ospfv3:processes/ospfv3:pr'
              + 'ocess/ospfv3:distance-policy/ospfv3:policy-name'
                ;
  }
  revision 2018-07-27 {
    description 'Add new enumeration value:'+"\n"
              + '/ospfv3:state/ospfv3:ospfv3/ospfv3:processes/ospfv3:process/os'
              + 'pfv3:areas/ospfv3:area/ospfv3:ipsec/ospfv3:authentication-algo'
              + 'rithm'+"\n"
              + '/ospfv3:state/ospfv3:ospfv3/ospfv3:processes/ospfv3:process/os'
              + 'pfv3:areas/ospfv3:area/ospfv3:ipsec/ospfv3:encryption-algorith'
              + 'm'
                ;
  }
  revision 2018-04-12 {
    description 'Add new enumeration value:'+"\n"
              + '/ospfv3:configuration/ospfv3:ospfv3/ospfv3:processes/ospfv3:pr'
              + 'ocess/ospfv3:redistribute/ospfv3:redistribute-other/ospfv3:red'
              + 'istribute-other/ospfv3:protocol'
                ;
  }
  revision 2017-10-27 {
    description 'Add default value:'+"\n"
              + '/ospfv3:configuration/ospfv3:ospfv3/ospfv3:processes/ospfv3:pr'
              + 'ocess/ospfv3:reference-bandwidth'
                ;
  }
  revision 2017-07-05 {
    description 'Add new container:'+"\n"
              + '/ospfv3:configuration/ospfv3:ospfv3/ospfv3:processes/ospfv3:pr'
              + 'ocess/ospfv3:frr-policy'
                ;
  }
  revision 2017-06-04 {
    description '1.Add new container:'+"\n"
              + '/ospfv3:configuration/ospfv3:ospfv3/ospfv3:processes/ospfv3:pr'
              + 'ocess/ospfv3:areas/ospfv3:area/ospfv3:keychain'+"\n"
              + '/ospfv3:configuration/ospfv3:ospfv3/ospfv3:processes/ospfv3:pr'
              + 'ocess/ospfv3:areas/ospfv3:area/ospfv3:interfaces/ospfv3:interf'
              + 'ace/ospfv3:keychain'+"\n"
              + '2.Add new cases:'+"\n"
              + '/ospfv3:configuration/ospfv3:ospfv3/ospfv3:processes/ospfv3:pr'
              + 'ocess/ospfv3:areas/ospfv3:area/ospfv3:ipsec/ospfv3:ipsec/ospfv'
              + '3:authentication/ospfv3:authentication/ospfv3:authentication-k'
              + 'ey/ospfv3:authentication-key/ospfv3:keychain'+"\n"
              + '/ospfv3:configuration/ospfv3:ospfv3/ospfv3:processes/ospfv3:pr'
              + 'ocess/ospfv3:areas/ospfv3:area/ospfv3:ipsec/ospfv3:ipsec/ospfv'
              + '3:encryption/ospfv3:encryption/ospfv3:authentication-key/ospfv'
              + '3:authentication-key/ospfv3:keychain'+"\n"
              + '/ospfv3:configuration/ospfv3:ospfv3/ospfv3:processes/ospfv3:pr'
              + 'ocess/ospfv3:areas/ospfv3:area/ospfv3:ipsec/ospfv3:ipsec/ospfv'
              + '3:encryption/ospfv3:encryption/ospfv3:encryption-key/ospfv3:en'
              + 'cryption-key/ospfv3:keychain'+"\n"
              + '/ospfv3:configuration/ospfv3:ospfv3/ospfv3:processes/ospfv3:pr'
              + 'ocess/ospfv3:areas/ospfv3:area/ospfv3:virtual-links/ospfv3:vir'
              + 'tual-link/ospfv3:ipsec/ospfv3:ipsec/ospfv3:authentication/ospf'
              + 'v3:authentication/ospfv3:authentication-key/ospfv3:authenticat'
              + 'ion-key/ospfv3:keychain'+"\n"
              + '/ospfv3:configuration/ospfv3:ospfv3/ospfv3:processes/ospfv3:pr'
              + 'ocess/ospfv3:areas/ospfv3:area/ospfv3:virtual-links/ospfv3:vir'
              + 'tual-link/ospfv3:ipsec/ospfv3:ipsec/ospfv3:encryption/ospfv3:e'
              + 'ncryption/ospfv3:encryption-key/ospfv3:encryption-key/ospfv3:k'
              + 'eychain'+"\n"
              + '/ospfv3:configuration/ospfv3:ospfv3/ospfv3:processes/ospfv3:pr'
              + 'ocess/ospfv3:areas/ospfv3:area/ospfv3:virtual-links/ospfv3:vir'
              + 'tual-link/ospfv3:ipsec/ospfv3:ipsec/ospfv3:encryption/ospfv3:e'
              + 'ncryption/ospfv3:authentication-key/ospfv3:authentication-key/'
              + 'ospfv3:keychain'+"\n"
              + '/ospfv3:configuration/ospfv3:ospfv3/ospfv3:processes/ospfv3:pr'
              + 'ocess/ospfv3:areas/ospfv3:area/ospfv3:interfaces/ospfv3:interf'
              + 'ace/ospfv3:ipsec/ospfv3:ipsec/ospfv3:authentication/ospfv3:aut'
              + 'hentication/ospfv3:authentication/ospfv3:authentication-ipsec/'
              + 'ospfv3:authentication-key/ospfv3:authentication-key/ospfv3:key'
              + 'chain'+"\n"
              + '/ospfv3:configuration/ospfv3:ospfv3/ospfv3:processes/ospfv3:pr'
              + 'ocess/ospfv3:areas/ospfv3:area/ospfv3:interfaces/ospfv3:interf'
              + 'ace/ospfv3:ipsec/ospfv3:ipsec/ospfv3:encryption/ospfv3:encrypt'
              + 'ion/ospfv3:encryption/ospfv3:encryption-ipsec/ospfv3:authentic'
              + 'ation-key/ospfv3:authentication-key/ospfv3:keychain'+"\n"
              + '/ospfv3:configuration/ospfv3:ospfv3/ospfv3:processes/ospfv3:pr'
              + 'ocess/ospfv3:areas/ospfv3:area/ospfv3:interfaces/ospfv3:interf'
              + 'ace/ospfv3:ipsec/ospfv3:ipsec/ospfv3:encryption/ospfv3:encrypt'
              + 'ion/ospfv3:encryption/ospfv3:encryption-ipsec/ospfv3:encryptio'
              + 'n-key/ospfv3:encryption-key/ospfv3:keychain'+"\n"
              + '3.Add new enum values:'+"\n"
              + '/ospfv3:state/ospfv3:ospfv3/ospfv3:interfaces/ospfv3:normal-in'
              + 'terfaces/ospfv3:normal-interface/ospfv3:ipsec/ospfv3:authentic'
              + 'ation-algorithm'+"\n"
              + '/ospfv3:state/ospfv3:ospfv3/ospfv3:interfaces/ospfv3:normal-in'
              + 'terfaces/ospfv3:normal-interface/ospfv3:ipsec/ospfv3:encryptio'
              + 'n-algorithm'
                ;
  }
  revision 2017-05-18 {
    description 'Add new leaf:'+"\n"
              + '/ospfv3:configuration/ospfv3:ospfv3/ospfv3:processes/ospfv3:pr'
              + 'ocess/ospfv3:reference-bandwidth'
                ;
  }
  revision 2017-03-31 {
    description 'Add new container:'+"\n"
              + '/ospfv3:configuration/ospfv3:ospfv3/ospfv3:processes/ospfv3:pr'
              + 'ocess/ospfv3:areas/ospfv3:area/ospfv3:interfaces/ospfv3:interf'
              + 'ace/ospfv3:link-damping'+"\n"
              + 'Add new leaf:'+"\n"
              + '/ospfv3:state/ospfv3:ospfv3/ospfv3:interfaces/ospfv3:normal-in'
              + 'terfaces/ospfv3:normal-interface/ospfv3:damp-state'+"\n"
              + '/ospfv3:state/ospfv3:ospfv3/ospfv3:interfaces/ospfv3:normal-in'
              + 'terfaces/ospfv3:normal-interface/ospfv3:damp-remain'
                ;
  }
  revision 2017-01-17 {
    description 'Add new enumeration value:'+"\n"
              + '1./ospfv3:configuration/ospfv3:ospfv3/ospfv3:processes/ospfv3:'
              + 'process/ospfv3:redistribute/ospfv3:redistribute-other/ospfv3:r'
              + 'edistribute-other/ospfv3:protocol'
                ;
  }
  revision 2016-12-08 {
    description 'Add new leaf:'+"\n"
              + '/ospfv3:configuration/ospfv3:ospfv3/ospfv3:processes/ospfv3:pr'
              + 'ocess/ospfv3:redistribute/ospfv3:redistribute-ospf/ospfv3:redi'
              + 'stribute-ospf/ospfv3:with-origin-metric'+"\n"
              + '/ospfv3:configuration/ospfv3:ospfv3/ospfv3:processes/ospfv3:pr'
              + 'ocess/ospfv3:redistribute/ospfv3:redistribute-isis/ospfv3:redi'
              + 'stribute-isis/ospfv3:with-origin-metric'+"\n"
              + '/ospfv3:configuration/ospfv3:ospfv3/ospfv3:processes/ospfv3:pr'
              + 'ocess/ospfv3:redistribute/ospfv3:redistribute-other/ospfv3:red'
              + 'istribute-other/ospfv3:with-origin-metric'
                ;
  }
  revision 2016-07-04 {
    description 'Add new container:'+"\n"
              + '/ospfv3:configuration/ospfv3:ospfv3/ospfv3:processes/ospfv3:pr'
              + 'ocess/ospfv3:domain-ids'+"\n"
              + 'Add new leaf:'+"\n"
              + '/ospfv3:configuration/ospfv3:ospfv3/ospfv3:processes/ospfv3:pr'
              + 'ocess/ospfv3:areas/ospfv3:area/ospfv3:stub/ospfv3:default-orig'
              + 'in'
                ;
  }
  revision 2016-06-23 {
    description '1.Add leaf node:'+"\n"
              + '/ospfv3:configuration/ospfv3:ospfv3/ospfv3:processes/ospfv3:pr'
              + 'ocess/ospfv3:cap-vrf-lite'
                ;
  }
  revision 2016-06-15 {
    description 'Add new enum item:'+"\n"
              + '/configuration/ospfv3/processes/process/redistribute/redistrib'
              + 'ute-other/redistribute-other/protocol'
                ;
  }
  revision 2016-01-21 {
    description '1.Modify the description:'+"\n"
              + '/ospfv3:state/ospfv3:ospfv3/ospfv3:interfaces/ospfv3:normal-in'
              + 'terfaces/ospfv3:normal-interface/ospfv3:interface-state'+"\n"
              + '/ospfv3:state/ospfv3:ospfv3/ospfv3:interfaces/ospfv3:normal-in'
              + 'terfaces/ospfv3:normal-interface/ospfv3:ldp-link-state'
                ;
  }
  revision 2015-12-08 {
    description '1.Add leaf node:'+"\n"
              + '/ospfv3:configuration/ospfv3:ospfv3/ospfv3:processes/ospfv3:pr'
              + 'ocess/ospfv3:ldp-igp-sync'+"\n"
              + '/ospfv3:configuration/ospfv3:ospfv3/ospfv3:processes/ospfv3:pr'
              + 'ocess/ospfv3:areas/ospfv3:area/ospfv3:ldp-igp-sync'+"\n"
              + '/ospfv3:configuration/ospfv3:ospfv3/ospfv3:processes/ospfv3:pr'
              + 'ocess/ospfv3:areas/ospfv3:area/ospfv3:interfaces/ospfv3:interf'
              + 'ace/ospfv3:ldp-igp-sync'+"\n"
              + '/ospfv3:state/ospfv3:ospfv3/ospfv3:interfaces/ospfv3:normal-in'
              + 'terfaces/ospfv3:normal-interface/ospfv3:ldp-sync'+"\n"
              + '/ospfv3:state/ospfv3:ospfv3/ospfv3:interfaces/ospfv3:normal-in'
              + 'terfaces/ospfv3:normal-interface/ospfv3:ldp-sync-state'+"\n"
              + '/ospfv3:state/ospfv3:ospfv3/ospfv3:interfaces/ospfv3:normal-in'
              + 'terfaces/ospfv3:normal-interface/ospfv3:ldp-link-state'+"\n"
              + '/ospfv3:state/ospfv3:ospfv3/ospfv3:interfaces/ospfv3:normal-in'
              + 'terfaces/ospfv3:normal-interface/ospfv3:no-cut-edge'
                ;
  }
  revision 2015-08-04 {
    description '1.Modify derivedType:'+"\n"
              + '/ospfv3:configuration/ospfv3:ospfv3/ospfv3:processes/ospfv3:pr'
              + 'ocess/ospfv3:summary-prefixs/ospfv3:summary-prefix/ospfv3:summ'
              + 'ary-prefix'+"\n"
              + '/ospfv3:configuration/ospfv3:ospfv3/ospfv3:processes/ospfv3:pr'
              + 'ocess/ospfv3:areas/ospfv3:area/ospfv3:ranges/ospfv3:range/ospf'
              + 'v3:prefix'+"\n"
              + '2.Refresh the config label'
                ;
  }
  revision 2015-07-06 {
    description 'Delete enumeration values:'+"\n"
              + '/ospfv3:state/ospfv3:ospfv3/ospfv3:neighbors/ospfv3:normal-nei'
              + 'ghbors/ospfv3:normal-neighbor/ospfv3:neighbor-state'
                ;
  }
  revision 2015-06-10 {
    description '1.Modify range:'+"\n"
              + '/ospfv3:state/ospfv3:ospfv3/ospfv3:interfaces/ospfv3:virtual-i'
              + 'nterfaces/ospfv3:virtual-interface/ospfv3:interface-id'+"\n"
              + '2.Modify the description:'+"\n"
              + '/ospfv3:state/ospfv3:ospfv3/ospfv3:neighbors/ospfv3:normal-nei'
              + 'ghbors/ospfv3:normal-neighbor/ospfv3:options/ospfv3:v6-bit'
                ;
  }
  revision 2015-06-03 {
    description '1.Modify the units of these leaf nodes:'+"\n"
              + '/ospfv3:configuration/ospfv3:ospfv3/ospfv3:processes/ospfv3:pr'
              + 'ocess/ospfv3:areas/ospfv3:area/ospfv3:interfaces/ospfv3:interf'
              + 'ace/ospfv3:ipsec/ospfv3:ipsec/ospfv3:authentication/ospfv3:aut'
              + 'hentication/ospfv3:authentication/ospfv3:authentication-ipsec/'
              + 'ospfv3:roll-interval'+"\n"
              + '/ospfv3:configuration/ospfv3:ospfv3/ospfv3:processes/ospfv3:pr'
              + 'ocess/ospfv3:areas/ospfv3:area/ospfv3:interfaces/ospfv3:interf'
              + 'ace/ospfv3:ipsec/ospfv3:ipsec/ospfv3:encryption/ospfv3:encrypt'
              + 'ion/ospfv3:encryption/ospfv3:encryption-ipsec/ospfv3:roll-inte'
              + 'rval'+"\n"
              + '/ospfv3:configuration/ospfv3:ospfv3/ospfv3:processes/ospfv3:pr'
              + 'ocess/ospfv3:areas/ospfv3:area/ospfv3:ipsec/ospfv3:ipsec/ospfv'
              + '3:authentication/ospfv3:authentication/ospfv3:roll-interval'+"\n"
              + '/ospfv3:configuration/ospfv3:ospfv3/ospfv3:processes/ospfv3:pr'
              + 'ocess/ospfv3:areas/ospfv3:area/ospfv3:ipsec/ospfv3:ipsec/ospfv'
              + '3:encryption/ospfv3:encryption/ospfv3:roll-interval'+"\n"
              + '/ospfv3:configuration/ospfv3:ospfv3/ospfv3:processes/ospfv3:pr'
              + 'ocess/ospfv3:areas/ospfv3:area/ospfv3:virtual-links/ospfv3:vir'
              + 'tual-link/ospfv3:ipsec/ospfv3:ipsec/ospfv3:authentication/ospf'
              + 'v3:authentication/ospfv3:roll-interval'+"\n"
              + '/ospfv3:configuration/ospfv3:ospfv3/ospfv3:processes/ospfv3:pr'
              + 'ocess/ospfv3:areas/ospfv3:area/ospfv3:virtual-links/ospfv3:vir'
              + 'tual-link/ospfv3:ipsec/ospfv3:ipsec/ospfv3:encryption/ospfv3:e'
              + 'ncryption/ospfv3:roll-interval'+"\n"
              + '2.Delete an enumeration value:'+"\n"
              + '/ospfv3:state/ospfv3:ospfv3/ospfv3:neighbors/ospfv3:virtual-ne'
              + 'ighbors/ospfv3:virtual-neighbor/ospfv3:neighbor-state'+"\n"
              + '3.Modify the description:'+"\n"
              + '/ospfv3:state/ospfv3:ospfv3/ospfv3:neighbors/ospfv3:virtual-ne'
              + 'ighbors/ospfv3:virtual-neighbor/ospfv3:options/ospfv3:v6-bit'
                ;
  }
  revision 2015-05-04 {
    description 'Add new container:'+"\n"
              + '/configuration/ospfv3/processes/process/redistribute/redistrib'
              + 'ute-ps'
                ;
  }
  revision 2015-03-26 {
    description 'Add state and operation of OSPFv3.'
                ;
  }
  revision 2015-01-14 {
    description 'Add new container:'+"\n"
              + '/configuration/ospfv3/processes/process/notify-default-route'
                ;
  }
  revision 2014-12-22 {
    description 'Add new enum item:'+"\n"
              + '/configuration/ospfv3/processes/process/redistribute/redistrib'
              + 'ute-other/redistribute-other/protocol'+"\n"
              + 'Change container of leaves to container of list:'+"\n"
              + '/configuration/ospfv3/processes/process/timers-throttle-spf'+"\n"
              + 'Rename:'+"\n"
              + '/configuration/ospfv3/processes/process/summary-prefixs/summar'
              + 'y-prefix/summary_prefix'+"\n"
              + '/configuration/ospfv3/processes/process/timers-throttle-spf'
                ;
  }
  revision 2014-09-29 {
    description 'Rename some container and leaf node:'+"\n"
              + '/configuration/ospfv3/processes/process/max-path'+"\n"
              + '/configuration/ospfv3/processes/process/areas/area/bfd-cfg'+"\n"
              + '/configuration/ospfv3/processes/process/areas/area/interfaces/'
              + 'interface/bfd-cfg'+"\n"
              + '/configuration/ospfv3/processes/process/areas/area/interfaces/'
              + 'interface/network-type/network-type/p-to-mp-nbma'+"\n"
              + '/configuration/ospfv3/processes/process/areas/area/interfaces/'
              + 'interface/network-type/network-type/p-to-mp-nb/p-to-mp-nbma'+"\n"
              + '/configuration/ospfv3/processes/process/areas/area/interfaces/'
              + 'interface/interface-ipsec'+"\n"
              + '/configuration/ospfv3/processes/process/areas/area/interfaces/'
              + 'interface/ipsec/interface-ipsec'+"\n"
              + '/configuration/ospfv3/processes/process/areas/area/virtual-lin'
              + 'ks/virtual-link/vlink-ipsec'+"\n"
              + '/configuration/ospfv3/processes/process/areas/area/virtual-lin'
              + 'ks/virtual-link/ipsec/vlink-ipsec'+"\n"
              + '/configuration/ospfv3/processes/process/areas/area/area-ipsec'+"\n"
              + '/configuration/ospfv3/processes/process/areas/area/ipsec/area-'
              + 'ipsec'
                ;
  }
  revision 2014-01-13 {
    description 'Initial version.'
                ;
  }
  feature distance-policy {
    description 'The feature is for distance-policy.'
                ;
  }
  feature segment-routing {
    description 'SR support labels'
                ;
  }
  container configuration {
    description Configuration. ;
    container ospfv3 {
      description 'OSPFv3 configuration.'
                  ;
      container processes {
        description 'OSPFv3 process configuration.'
                    ;
        list process {
          description 'OSPFv3 process configuration.'
                      ;
          key proc-id ;
          leaf proc-id {
            description 'OSPFv3 process ID.'
                        ;
            type uint32 {
              range 1..65535 ;
            }
          }
          leaf vrf-name {
            description 'VPN routing/forwarding instance (VRF) name.'
                        ;
            type string {
              length 1..32 ;
            }
          }
          leaf bfd-enable {
            description 'BFD configuration of OSPFv3 process.'
                        ;
            type empty ;
          }
          leaf bfd-template {
            description 'Configure BFD template for OSPFv3.'
                        ;
            type string {
              length 1..31 ;
            }
            ncd:revise-date 2020-06-21 ;
          }
          leaf default-metric {
            description 'Default metric of Type 5 LSA.'
                        ;
            type uint32 {
              range 1..16777214 ;
            }
            default 20 ;
          }
          leaf maximum-paths {
            description 'Maximum of paths to one destination.'
                        ;
            type uint32 {
              range 1..64 ;
            }
            default 1 ;
          }
          leaf fast-reroute {
            description Fast-reroute. ;
            type empty ;
          }
          leaf nsf {
            description 'Non-stop forwarding.'
                        ;
            type empty ;
          }
          leaf grace-period {
            description 'The max period of a graceful restart.'
                        ;
            type uint32 {
              range 1..1800 ;
            }
            units second ;
            default 120 ;
          }
          leaf ispf {
            description 'Incremental SPF computation.'
                        ;
            type empty ;
          }
          leaf ldp-igp-sync {
            description 'Configure MPLS LDP IGP sync.'
                        ;
            type empty ;
            ncd:revise-date 2015-12-08 ;
          }
          leaf cap-vrf-lite {
            description 'Configure capbility vrf lite'
                        ;
            type empty ;
            ncd:revise-date 2016-06-23 ;
          }
          leaf reference-bandwidth {
            description 'The reference bandwidth in terms of Mbps.'
                        ;
            type uint32 {
              range 1..4000000 ;
            }
            units Mbps ;
            default 100 ;
            ncd:revise-date 2017-05-18 ;
          }
          leaf te-link-delay {
            description 'Set OSPF TE link delay'
                        ;
            type enumeration {
              enum enable {
                value 1 ;
                description 'Enable TE link delay'
                            ;
              }
              enum disable {
                value 2 ;
                description 'Disable TE link delay'
                            ;
              }
            }
            default disable ;
            ncd:revise-date 2020-02-19 ;
          }
          container frr-policy {
            description 'Configure OSPF backup route policy.'
                        ;
            presence frr-policy ;
            choice policy-type {
              description 'Configure OSPF backup route policy type.'
                          ;
              mandatory true ;
              case route-policy {
                description 'Configure OSPF backup route-policy.'
                            ;
                leaf route-policy-name {
                  description 'Configure route-policy name.'
                              ;
                  type string {
                    length 1..200 {
                      description 'Name of the route-policy,characters from 1 t'
                                + 'o 200.'
                                  ;
                    }
                  }
                  mandatory true ;
                }
              }
            }
            ncd:revise-date 2017-07-05 ;
          }
          container router-id {
            description Router-id. ;
            presence router-id-presence ;
            leaf router-id {
              description Router-id. ;
              type ncd:ipv4-address ;
              mandatory true ;
            }
          }
          container distance {
            description 'Distance of OSPF route.'
                        ;
            leaf external {
              description 'Distance for external routes.'
                          ;
              type uint8 {
                range 1..255 ;
              }
              default 110 ;
            }
            leaf inter-area {
              description 'Distance for inter-area routes.'
                          ;
              type uint8 {
                range 1..255 ;
              }
              default 110 ;
            }
            leaf intra-area {
              description 'Distance for intra-area routes.'
                          ;
              type uint8 {
                range 1..255 ;
              }
              default 110 ;
            }
          }
          container distribute-list {
            description 'Filter networks in routing updates.'
                        ;
            container distribute-list-in {
              description 'Filter incoming routing updates.'
                          ;
              presence dl-in-presence ;
              container policy-name {
                description 'Policy name.'
                            ;
                choice policy-name {
                  description 'Policy name.'
                              ;
                  mandatory true ;
                  case access-list {
                    description 'Access list.'
                                ;
                    leaf acl-name {
                      description 'Access list name.'
                                  ;
                      type string {
                        length 1..31 ;
                      }
                      mandatory true ;
                    }
                  }
                  case route-map {
                    description Route-map. ;
                    leaf route-map-name {
                      description 'Route-map name.'
                                  ;
                      type string {
                        length 1..200 ;
                      }
                      mandatory true ;
                    }
                  }
                }
              }
            }
          }
          container prefix-priority {
            description 'Priority for prefix convergence.'
                        ;
            presence prefix-priority-presence ;
            container prefix-lists {
              description 'Prefix-list for prefix convergence.'
                          ;
              presence prefix-list-presence ;
              list prefix-list {
                description 'Prefix-list for prefix convergence.'
                            ;
                key priority ;
                leaf priority {
                  description 'Priority for prefix.'
                              ;
                  type enumeration {
                    enum critical {
                      value 1 ;
                      description 'Critical priority.'
                                  ;
                    }
                    enum high {
                      value 2 ;
                      description 'High priority.'
                                  ;
                    }
                    enum medium {
                      value 3 ;
                      description 'Medium priority.'
                                  ;
                    }
                  }
                }
                leaf prefix-name {
                  description 'Prefix-list name.'
                              ;
                  type string {
                    length 1..169 ;
                  }
                  mandatory true ;
                }
              }
            }
            container tags {
              description 'Tag value for prefix convergence.'
                          ;
              presence tags-presence ;
              list tag {
                description 'Tag value for prefix convergence.'
                            ;
                key 'priority tag-value'
                    ;
                leaf priority {
                  description 'Priority for prefix.'
                              ;
                  type enumeration {
                    enum critical {
                      value 1 ;
                      description 'Critical priority.'
                                  ;
                    }
                    enum high {
                      value 2 ;
                      description 'High priority.'
                                  ;
                    }
                    enum medium {
                      value 3 ;
                      description 'Medium priority.'
                                  ;
                    }
                  }
                }
                leaf tag-value {
                  description 'Tag value of prefix.'
                              ;
                  type uint32 {
                    range 0..4294967295 ;
                  }
                }
              }
            }
          }
          container redistribute {
            description Redistribute. ;
            container redistribute-ospf {
              description 'Redistribute information from OSPF.'
                          ;
              presence redistribute-ospf-presence ;
              list redistribute-ospf {
                description 'Redistribute information from OSPF.'
                            ;
                key ospf-proc-id ;
                leaf ospf-proc-id {
                  description 'OSPF process ID for redistribute.'
                              ;
                  type uint32 {
                    range 1..65535 ;
                  }
                }
                leaf metric {
                  description 'Metric for redistributed routes.'
                              ;
                  type uint32 {
                    range 1..16777214 ;
                  }
                }
                leaf metric-type {
                  description 'Metric type for redistributed routes.'
                              ;
                  type enumeration {
                    enum ext-2 {
                      value 0 ;
                      description 'External metric-type 2.'
                                  ;
                    }
                    enum ext-1 {
                      value 1 ;
                      description 'External metric-type 1.'
                                  ;
                    }
                  }
                  default ext-2 ;
                }
                leaf route-map-name {
                  description 'Route map reference.'
                              ;
                  type string {
                    length 1..200 ;
                  }
                }
                leaf tag {
                  description 'Tag for redistributed routes.'
                              ;
                  type uint32 {
                    range 0..4294967295 ;
                  }
                  default 0 ;
                }
                leaf with-origin-metric {
                  description 'Use origin metric of the route.'
                              ;
                  type empty ;
                  ncd:revise-date 2016-12-08 ;
                }
                leaf host-only {
                  type empty ;
                  ncd:revise-date 2019-06-20 ;
                }
              }
            }
            container redistribute-isis {
              description 'Redistribute information from ISIS.'
                          ;
              presence redistribute-isis-presence ;
              list redistribute-isis {
                description 'Redistribute information from ISIS.'
                            ;
                key isis-proc-id ;
                leaf isis-proc-id {
                  description 'ISIS process ID for redistribute.'
                              ;
                  type uint32 {
                    range 0..65535 ;
                  }
                }
                leaf metric {
                  description 'Metric for redistributed routes.'
                              ;
                  type uint32 {
                    range 1..16777214 ;
                  }
                }
                leaf metric-type {
                  description 'Metric type for redistributed routes.'
                              ;
                  type enumeration {
                    enum ext-2 {
                      value 0 ;
                      description 'External metric-type 2.'
                                  ;
                    }
                    enum ext-1 {
                      value 1 ;
                      description 'External metric-type 1.'
                                  ;
                    }
                  }
                  default ext-2 ;
                }
                leaf route-map-name {
                  description 'Route map reference.'
                              ;
                  type string {
                    length 1..200 ;
                  }
                }
                leaf tag {
                  description 'Tag for redistributed routes.'
                              ;
                  type uint32 {
                    range 0..4294967295 ;
                  }
                  default 0 ;
                }
                leaf with-origin-metric {
                  description 'Use origin metric of the route.'
                              ;
                  type empty ;
                  ncd:revise-date 2016-12-08 ;
                }
                leaf host-only {
                  type empty ;
                  ncd:revise-date 2019-06-20 ;
                }
              }
            }
            container redistribute-other {
              description 'Redistribute information from other protocal.'
                          ;
              presence redistribute-other-presence ;
              list redistribute-other {
                description 'Redistribute information from other protocal.'
                            ;
                key protocol ;
                leaf protocol {
                  description 'Route protocol.'
                              ;
                  type enumeration {
                    enum static {
                      value 1 ;
                      description 'Static routes.'
                                  ;
                    }
                    enum connected {
                      value 2 ;
                      description 'Connected routes.'
                                  ;
                    }
                    enum rip {
                      value 3 ;
                      description 'Routing information protocol (RIPNG).'
                                  ;
                    }
                    enum bgp {
                      value 6 ;
                      description 'Border gateway protocol for ipv6 (BGP).'
                                  ;
                    }
                    enum subscriber-host {
                      value 7 ;
                      description "Bras subscriber's host routes."
                                  ;
                    }
                    enum aftr {
                      value 8 ;
                      description 'AFTR routes.'
                                  ;
                    }
                    enum sf-nat64 {
                      value 9 ;
                      description 'Stateful NAT64 routes.'
                                  ;
                    }
                    enum sl-nat64 {
                      value 10 ;
                      description 'Stateless NAT64 routes.'
                                  ;
                    }
                    enum dhcp-pd {
                      value 11 ;
                      description 'DHCP-PD routes.'
                                  ;
                    }
                    enum subscriber-aggregation {
                      value 14 ;
                      description "Bras subscriber's aggregation routes."
                                  ;
                    }
                    enum user-special {
                      value 15 ;
                      description 'User special routes.'
                                  ;
                    }
                    enum bras-pool {
                      value 16 ;
                      description 'Bras-pool routes.'
                                  ;
                    }
                    enum zenic-local {
                      value 17 ;
                      description 'Zenic-local routes.'
                                  ;
                    }
                    enum dyn-leasedline {
                      value 18 ;
                      description 'Dynamic-leased-line routes assigned by AAA'
                                  ;
                    }
                  }
                }
                leaf metric {
                  description 'Metric for redistributed routes.'
                              ;
                  type uint32 {
                    range 1..16777214 ;
                  }
                }
                leaf metric-type {
                  description 'Metric type for redistributed routes.'
                              ;
                  type enumeration {
                    enum ext-2 {
                      value 0 ;
                      description 'External metric-type 2.'
                                  ;
                    }
                    enum ext-1 {
                      value 1 ;
                      description 'External metric-type 1.'
                                  ;
                    }
                  }
                  default ext-2 ;
                }
                leaf route-map-name {
                  description 'Route map reference.'
                              ;
                  type string {
                    length 1..200 ;
                  }
                }
                leaf tag {
                  description 'Tag for redistributed routes.'
                              ;
                  type uint32 {
                    range 0..4294967295 ;
                  }
                  default 0 ;
                }
                leaf with-origin-metric {
                  description 'Use origin metric of the route.'
                              ;
                  type empty ;
                  ncd:revise-date 2016-12-08 ;
                }
                leaf host-only {
                  type empty ;
                  ncd:revise-date 2019-06-20 ;
                }
              }
            }
            container redistribute-ps {
              description 'Redistribute PS route.'
                          ;
              list redistribute-ps {
                description 'Redistribute PS route.'
                            ;
                key type ;
                leaf type {
                  description 'PS route type.'
                              ;
                  type enumeration {
                    enum ps-busi-addr {
                      value 12 ;
                      description 'ps-busi-addr routes.'
                                  ;
                    }
                    enum ps-user-addr {
                      value 13 ;
                      description 'ps-user-addr routes.'
                                  ;
                    }
                  }
                }
                leaf with-origin-metric {
                  description 'Use origin metric of the route.'
                              ;
                  type empty ;
                }
                leaf metric {
                  description 'Metric for redistributed routes.'
                              ;
                  type uint32 {
                    range 1..16777214 ;
                  }
                }
                leaf metric-type {
                  description 'Metric type for redistributed routes.'
                              ;
                  type enumeration {
                    enum ext-2 {
                      value 0 ;
                      description 'External metric-type 2.'
                                  ;
                    }
                    enum ext-1 {
                      value 1 ;
                      description 'External metric-type 1.'
                                  ;
                    }
                  }
                  default ext-2 ;
                }
                leaf route-map-name {
                  description 'Route map reference.'
                              ;
                  type string {
                    length 1..200 ;
                  }
                }
                leaf tag {
                  description 'Tag for redistributed routes.'
                              ;
                  type uint32 {
                    range 0..4294967295 ;
                  }
                  default 0 ;
                }
                leaf host-only {
                  type empty ;
                  ncd:revise-date 2019-06-20 ;
                }
              }
              ncd:revise-date 2015-05-04 ;
            }
          }
          container summary-prefixs {
            description 'Summarize external routes matching prefix/length.'
                        ;
            list summary-prefix {
              description 'Summarize external routes matching prefix/length.'
                          ;
              key 'summary-prefix prefix-len'
                  ;
              leaf summary-prefix {
                description 'IPv6 address prefix.'
                            ;
                type ncd:ipv6-address ;
              }
              leaf prefix-len {
                description 'Prefix length.'
                            ;
                type ncd:ipv6-mask-length ;
              }
            }
          }
          container timers-throttle {
            description 'Timers for throttle.'
                        ;
            presence throttle-presence ;
            container spf {
              description 'Ospf SPF throttle timers'
                          ;
              presence spf ;
              leaf hold-time {
                description 'Hold time for SPF calculation in milliseconds'
                            ;
                type uint32 {
                  range 1..600000 {
                    description 'Hold time for SPF calculation in milliseconds'
                                ;
                  }
                }
                units millisecond ;
                mandatory true ;
              }
              leaf delay-time {
                description 'Min delay for SPF calculation in milliseconds'
                            ;
                type uint32 {
                  range 1..600000 {
                    description 'Min delay for SPF calculation in milliseconds'
                                ;
                  }
                }
                units millisecond ;
                mandatory true ;
              }
              leaf max-delay-time {
                description 'Max delay for SPF calculation in milliseconds'
                            ;
                type uint32 {
                  range 1..600000 {
                    description 'Max delay for SPF calculation in milliseconds'
                                ;
                  }
                }
                units millisecond ;
                mandatory true ;
              }
            }
            container lsa-update {
              description 'Ospf LSA update throttle timers'
                          ;
              presence lsa-update ;
              leaf hold-time {
                description 'Hold time for LSA update in milliseconds'
                            ;
                type uint32 {
                  range 1..600000 {
                    description 'Hold time for LSA update in milliseconds'
                                ;
                  }
                }
                units millisecond ;
                mandatory true ;
              }
              leaf delay-time {
                description 'Min delay for LSA update in milliseconds'
                            ;
                type uint32 {
                  range 1..600000 {
                    description 'Min delay for LSA update in milliseconds'
                                ;
                  }
                }
                units millisecond ;
                mandatory true ;
              }
              leaf max-delay-time {
                description 'Max delay for LSA update in milliseconds'
                            ;
                type uint32 {
                  range 1..600000 {
                    description 'Max delay for LSA update in milliseconds'
                                ;
                  }
                }
                units millisecond ;
                mandatory true ;
              }
            }
            container lsa-arrival {
              description 'Ospf LSA arrival throttle timers'
                          ;
              presence lsa-arrival ;
              leaf hold-time {
                description 'Hold time for LSA arrival in milliseconds'
                            ;
                type uint32 {
                  range 0..600000 {
                    description 'Hold time for LSA arrival in milliseconds'
                                ;
                  }
                }
                units millisecond ;
                mandatory true ;
              }
              leaf delay-time {
                description 'Min delay for LSA arrival in milliseconds'
                            ;
                type uint32 {
                  range 0..600000 {
                    description 'Min delay for LSA arrival in milliseconds'
                                ;
                  }
                }
                units millisecond ;
                mandatory true ;
              }
              leaf max-delay-time {
                description 'Max delay for LSA arrival in milliseconds'
                            ;
                type uint32 {
                  range 0..600000 {
                    description 'Max delay for LSA update in milliseconds'
                                ;
                  }
                }
                units millisecond ;
                mandatory true ;
              }
            }
          }
          container notify-default-route {
            description 'Notify default route.'
                        ;
            leaf always {
              description 'Generate a type-5 LSA evenif there is no default rou'
                        + 'te.'
                          ;
              type empty ;
            }
            leaf metric {
              description 'Metric of generated type-5 LSA.'
                          ;
              type uint32 {
                range 1..16777214 ;
              }
              default 1 ;
            }
            leaf metric-type {
              description 'Metric type of generated type-5 LSA.'
                          ;
              type enumeration {
                enum ext-2 {
                  value 0 ;
                  description 'External metric-type 2.'
                              ;
                }
                enum ext-1 {
                  value 1 ;
                  description 'External metric-type 1.'
                              ;
                }
              }
              default ext-2 ;
            }
            leaf route-map {
              description 'Route map reference.'
                          ;
              type string {
                length 1..200 ;
              }
            }
          }
          container areas {
            description 'OSPFv3 area configuration.'
                        ;
            list area {
              description 'OSPFv3 area configuration.'
                          ;
              key area-id ;
              leaf area-id {
                description 'OSPFv3 area ID in IP address format.'
                            ;
                type ncd:ipv4-address ;
              }
              leaf bfd {
                description 'BFD configuration of OSPFv3 area.'
                            ;
                type enumeration {
                  enum enable {
                    value 1 ;
                    description 'Enable BFD capbility of the area.'
                                ;
                  }
                  enum disable {
                    value 2 ;
                    description 'Disable BFD capbility of the area.'
                                ;
                  }
                }
              }
              leaf bfd-template {
                description 'Configure BFD template for OSPFv3 area.'
                            ;
                type string {
                  length 1..31 ;
                }
                ncd:revise-date 2020-06-21 ;
              }
              leaf ldp-igp-sync {
                description 'Configure MPLS LDP IGP sync.'
                            ;
                type enumeration {
                  enum enable {
                    value 1 ;
                    description 'Enable MPLS LDP IGP sync.'
                                ;
                  }
                  enum disable {
                    value 2 ;
                    description 'Disable MPLS LDP IGP sync.'
                                ;
                  }
                }
                ncd:revise-date 2015-12-08 ;
              }
              container ranges {
                description 'Summarize inter-area routes matching prefix/length.'
                            ;
                list range {
                  description 'Summarize inter-area routes matching prefix/leng'
                            + 'th.'
                              ;
                  key 'prefix prefix-len'
                      ;
                  leaf prefix {
                    description 'IPv6 address prefix.'
                                ;
                    type ncd:ipv6-address ;
                  }
                  leaf prefix-len {
                    description 'Prefix length.'
                                ;
                    type ncd:ipv6-mask-length ;
                  }
                  leaf not-advertise {
                    description 'DoNotAdvertise this range.'
                                ;
                    type empty ;
                  }
                }
                list nssa-range {
                  description 'Summarize routes when nssa abr translates type-7'
                            + ' routes to type-5 lsa'
                              ;
                  key 'prefix prefix-len'
                      ;
                  leaf prefix {
                    description 'IPv6 address prefix.'
                                ;
                    type ncd:ipv6-address ;
                  }
                  leaf prefix-len {
                    description 'Prefix length'
                                ;
                    type ncd:ipv6-mask-length ;
                  }
                  leaf not-advertise {
                    description 'advertise this range or not'
                                ;
                    type empty ;
                  }
                  leaf metric {
                    description 'nssa range metric'
                                ;
                    type uint32 {
                      range 1..16777214 ;
                    }
                  }
                  leaf tag {
                    description 'nssa range tag'
                                ;
                    type uint32 ;
                  }
                  ncd:revise-date 2020-05-21 ;
                }
              }
              container interfaces {
                description 'OSPFv3 interface configuration.'
                            ;
                list interface {
                  description 'OSPFv3 interface configuration.'
                              ;
                  key interface-name ;
                  leaf interface-name {
                    description 'Interface name.'
                                ;
                    type ncd:ifname {
                      length 1..31 ;
                    }
                  }
                  leaf instance-id {
                    description 'Instance ID of OSPFv3 interface.'
                                ;
                    type uint32 {
                      range 0..255 ;
                    }
                    default 0 ;
                  }
                  leaf bfd {
                    description 'BFD configuration of OSPFv3 interface.'
                                ;
                    type enumeration {
                      enum enable {
                        value 1 ;
                        description 'Enable BFD capbility of the interface.'
                                    ;
                      }
                      enum disable {
                        value 2 ;
                        description 'Disable BFD capbility of the interface.'
                                    ;
                      }
                    }
                  }
                  leaf bfd-template {
                    description 'Configure BFD template for OSPFv3 interface.'
                                ;
                    type string {
                      length 1..31 ;
                    }
                    ncd:revise-date 2020-06-21 ;
                  }
                  leaf cost {
                    description 'Cost value of OSPFv3 interface.'
                                ;
                    type uint32 {
                      range 1..65535 ;
                    }
                  }
                  leaf hello-interval {
                    description 'Time between hello packets.'
                                ;
                    type uint32 {
                      range 1..65535 ;
                    }
                    units second ;
                  }
                  leaf dead-interval {
                    description 'Interval after which a neighbor is declared de'
                              + 'ad.'
                                ;
                    type uint32 {
                      range 1..65535 ;
                    }
                    units second ;
                  }
                  leaf retransmit-interval {
                    description 'Time between retransmitting lost link state ad'
                              + 'vertisements.'
                                ;
                    type uint32 {
                      range 1..65535 ;
                    }
                    units second ;
                    default 5 ;
                  }
                  leaf transmit-delay {
                    description 'LSA transmit delay.'
                                ;
                    type uint32 {
                      range 1..65535 ;
                    }
                    units second ;
                    default 1 ;
                  }
                  leaf priority {
                    description 'Router priority.'
                                ;
                    type uint32 {
                      range 0..255 ;
                    }
                    default 1 ;
                  }
                  leaf mtu-ignore {
                    description 'Ignore the mtu mismatch when exchanging DD pac'
                              + 'ket.'
                                ;
                    type empty ;
                  }
                  leaf linklsa-suppress-enable {
                    description 'DONOT originate link LSA.'
                                ;
                    type empty ;
                  }
                  leaf fast-reroute-disable {
                    description 'Disable this interface FRR capability.'
                                ;
                    type empty ;
                  }
                  leaf passive {
                    description 'Control routing updates on an interface.'
                                ;
                    type empty ;
                  }
                  leaf ldp-igp-sync {
                    description 'Enable MPLS LDP IGP sync.'
                                ;
                    type enumeration {
                      enum enable {
                        value 1 ;
                        description 'Enable MPLS LDP IGP sync.'
                                    ;
                      }
                      enum disable {
                        value 2 ;
                        description 'Disable MPLS LDP IGP sync.'
                                    ;
                      }
                    }
                    ncd:revise-date 2015-12-08 ;
                  }
                  container link-damping {
                    description 'Configure interface cost and time when link is'
                              + ' in damping status'
                                ;
                    presence link-damping ;
                    container cost {
                      description 'Configure interface cost when link is in dam'
                                + 'ping status'
                                  ;
                      choice cost {
                        description 'Configure interface cost when link is in d'
                                  + 'amping status'
                                    ;
                        mandatory true ;
                        case maximum {
                          description 'Set maximum cost when link is in damping'
                                    + ' status'
                                      ;
                          leaf maximum {
                            description 'Set maximum cost when link is in damping status'
                                        ;
                            type empty ;
                            mandatory true ;
                          }
                        }
                        case increase-value {
                          description 'Set increase cost when link is in dampin'
                                    + 'g status'
                                      ;
                          leaf increase-value {
                            description 'Set increase cost when link is in damping status'
                                        ;
                            type uint32 {
                              range 100..10000 {
                                description 'Set increase cost range when link is in damping status'
                                            ;
                              }
                            }
                            mandatory true ;
                          }
                        }
                      }
                    }
                    leaf damping-time {
                      description 'Configure interface damping time'
                                  ;
                      type uint32 {
                        range 1..3600000 {
                          description 'Set time range when link is in damping s'
                                    + 'tatus'
                                      ;
                        }
                      }
                      units millisecond ;
                      mandatory true ;
                    }
                    ncd:revise-date 2017-03-31 ;
                  }
                  container network-type {
                    description 'Network type of OSPFv3 interface.'
                                ;
                    choice network-type {
                      description 'Network type of OSPFv3 interface.'
                                  ;
                      case broadcast {
                        description Broadcast. ;
                        leaf broadcast {
                          description Broadcast. ;
                          type empty ;
                          mandatory true ;
                        }
                      }
                      case nbma {
                        description 'Non-broadcast multiple access.'
                                    ;
                        leaf nbma {
                          description 'Non-broadcast multiple access.'
                                      ;
                          type empty ;
                          mandatory true ;
                        }
                      }
                      case point-to-point {
                        description Point-to-point. ;
                        leaf point-to-point {
                          description Point-to-point. ;
                          type empty ;
                          mandatory true ;
                        }
                      }
                      case point-to-multipoint {
                        description Point-to-multipoint. ;
                        leaf point-to-multipoint {
                          description Point-to-multipoint. ;
                          type empty ;
                          mandatory true ;
                        }
                      }
                      case p-to-mp-nb {
                        description 'Point-to-multipoint non-broadcast.'
                                    ;
                        leaf p-to-mp-nb {
                          description 'Point-to-multipoint non-broadcast.'
                                      ;
                          type empty ;
                          mandatory true ;
                        }
                      }
                    }
                  }
                  container neighbors {
                    description 'Neighbor configuration of OSPFv3 interface.'
                                ;
                    list neighbor {
                      description 'Neighbor configuration of OSPFv3 interface.'
                                  ;
                      key nbr-linklocal-address ;
                      leaf nbr-linklocal-address {
                        description 'Link-local address of the neighbor.'
                                    ;
                        type ncd:ipv6-address ;
                      }
                      leaf priority {
                        description 'OSPF priority of non-broadcast neighbor.'
                                    ;
                        type uint32 {
                          range 0..255 ;
                        }
                        default 1 ;
                      }
                      leaf poll-interval {
                        description 'Poll interval time of non-broadcast neighb'
                                  + 'or.'
                                    ;
                        type uint32 {
                          range 120..65535 ;
                        }
                        units second ;
                        default 120 ;
                      }
                      leaf cost {
                        description 'OSPF cost of point-to-multipoint neighbor.'
                                    ;
                        type uint32 {
                          range 1..65535 ;
                        }
                      }
                    }
                  }
                  container ipsec {
                    description 'IPSEC configuration of interface.'
                                ;
                    choice ipsec {
                      description 'IPSEC configuration of interface.'
                                  ;
                      case authentication {
                        description 'IPSEC authentication configuration of inte'
                                  + 'rface.'
                                    ;
                        container authentication {
                          description 'IPSEC authentication configuration of in'
                                    + 'terface.'
                                      ;
                          presence intf-auth-presence ;
                          choice authentication {
                            description 'IPSEC authentication configuration of interface.'
                                        ;
                            case authentication-ipsec {
                              description 'IPSEC authentication configuration of interface.'
                                          ;
                              leaf spi-id {
                                description 'Security parameters index ID.'
                                            ;
                                type uint32 {
                                  range 256..32767 ;
                                }
                                mandatory true ;
                              }
                              container authentication-key {
                                description 'Key of authentication algorithm.'
                                            ;
                                choice authentication-key {
                                  description 'Key of authentication algorithm.'
                                              ;
                                  mandatory true ;
                                  case md5 {
                                    description 'Message Digest Algorithm.'
                                                ;
                                    choice md5-password-type {
                                      case unencrypted {
                                        leaf md5-key {
                                          description 'MD5 key.'
                                                      ;
                                          type string {
                                            length 32 ;
                                          }
                                          mandatory true ;
                                        }
                                      }
                                      case encrypted {
                                        leaf encry-md5-key {
                                          description 'Encrypted md5 key.'
                                                      ;
                                          type string {
                                            length 1..128 ;
                                          }
                                          mandatory true ;
                                        }
                                        ncd:revise-date 2019-12-16 ;
                                      }
                                    }
                                  }
                                  case sha1 {
                                    description 'Secure Hash Algorithm.'
                                                ;
                                    choice sha1-password-type {
                                      case unencrypted {
                                        leaf sha1-key {
                                          description 'SHA1 key.'
                                                      ;
                                          type string {
                                            length 40 ;
                                          }
                                          mandatory true ;
                                        }
                                      }
                                      case encrypted {
                                        leaf encry-sha1-key {
                                          description 'Encrypte sha1 key.'
                                                      ;
                                          type string {
                                            length 1..128 ;
                                          }
                                          mandatory true ;
                                        }
                                        ncd:revise-date 2019-12-16 ;
                                      }
                                    }
                                  }
                                  case keychain {
                                    description Keychain. ;
                                    leaf keychain-name {
                                      description 'Keychain name.'
                                                  ;
                                      type string {
                                        length 1..31 ;
                                      }
                                      mandatory true ;
                                    }
                                    ncd:revise-date 2017-06-04 ;
                                  }
                                }
                              }
                              leaf roll-interval {
                                description 'Rollover interval.'
                                            ;
                                type uint32 {
                                  range 0..100000 ;
                                }
                                units minute ;
                                default 0 ;
                              }
                            }
                            case authentication-null {
                              description 'NO authentication.'
                                          ;
                              leaf authentication-null {
                                description 'NO authentication.'
                                            ;
                                type empty ;
                                mandatory true ;
                              }
                            }
                          }
                        }
                      }
                      case encryption {
                        description 'IPSEC encryption configuration of interfac'
                                  + 'e.'
                                    ;
                        container encryption {
                          description 'IPSEC encryption configuration of interf'
                                    + 'ace.'
                                      ;
                          presence intf-encryption-presence ;
                          choice encryption {
                            description 'IPSEC encryption configuration of interface.'
                                        ;
                            case encryption-ipsec {
                              description 'IPSEC encryption configuration of interface.'
                                          ;
                              leaf spi-id {
                                description 'Security parameters index ID.'
                                            ;
                                type uint32 {
                                  range 256..32767 ;
                                }
                                mandatory true ;
                              }
                              container encryption-key {
                                description 'Key of encryption algorithm.'
                                            ;
                                choice encryption-key {
                                  description 'Key of encryption algorithm.'
                                              ;
                                  mandatory true ;
                                  case null {
                                    description 'ESP without encryption.'
                                                ;
                                    leaf null {
                                      description 'NULL encryption.'
                                                  ;
                                      type empty ;
                                      mandatory true ;
                                    }
                                  }
                                  case des {
                                    description 'Data Encrypt Standard algorithm.'
                                                ;
                                    choice des-password-type {
                                      case unencrypted {
                                        leaf des-key {
                                          description 'DES key.'
                                                      ;
                                          type string {
                                            length 16 ;
                                          }
                                          mandatory true ;
                                        }
                                      }
                                      case encrypted {
                                        leaf encry-des-key {
                                          description 'Encrypted des key.'
                                                      ;
                                          type string {
                                            length 1..128 ;
                                          }
                                          mandatory true ;
                                        }
                                        ncd:revise-date 2019-12-16 ;
                                      }
                                    }
                                  }
                                  case triple-des {
                                    description 'Triple Data Encryption algorithm.'
                                                ;
                                    choice triple-des-password-type {
                                      case unencrypted {
                                        leaf triple-des-key {
                                          description '3DES key.'
                                                      ;
                                          type string {
                                            length 48 ;
                                          }
                                          mandatory true ;
                                        }
                                      }
                                      case encrypted {
                                        leaf encry-triple-des-key {
                                          description 'Encrypted 3des key.'
                                                      ;
                                          type string {
                                            length 1..128 ;
                                          }
                                          mandatory true ;
                                        }
                                        ncd:revise-date 2019-12-16 ;
                                      }
                                    }
                                  }
                                  case aes-cbc {
                                    description 'Advanced Encryption Standard algorithm.'
                                                ;
                                    choice aes-password-type {
                                      case unencrypted {
                                        leaf aes-cbc-key {
                                          description 'AES key.'
                                                      ;
                                          type string {
                                            length 32 ;
                                          }
                                          mandatory true ;
                                        }
                                      }
                                      case encrypted {
                                        leaf encry-aes-cbc-key {
                                          description 'Encrypted aes key.'
                                                      ;
                                          type string {
                                            length 1..128 ;
                                          }
                                          mandatory true ;
                                        }
                                        ncd:revise-date 2019-12-16 ;
                                      }
                                    }
                                  }
                                  case keychain {
                                    description Keychain. ;
                                    leaf keychain-name {
                                      description 'Keychain name.'
                                                  ;
                                      type string {
                                        length 1..31 ;
                                      }
                                      mandatory true ;
                                    }
                                    ncd:revise-date 2017-06-04 ;
                                  }
                                }
                              }
                              container authentication-key {
                                description 'Key of authentication algorithm.'
                                            ;
                                choice authentication-key {
                                  description 'Key of authentication algorithm.'
                                              ;
                                  mandatory true ;
                                  case md5 {
                                    description 'Message Digest Algorithm.'
                                                ;
                                    choice md5-password-type {
                                      case unencrypted {
                                        leaf md5-key {
                                          description 'MD5 key.'
                                                      ;
                                          type string {
                                            length 32 ;
                                          }
                                          mandatory true ;
                                        }
                                      }
                                      case encrypted {
                                        leaf encry-md5-key {
                                          description 'Encrypted MD5 key.'
                                                      ;
                                          type string {
                                            length 1..128 ;
                                          }
                                          mandatory true ;
                                        }
                                        ncd:revise-date 2019-12-16 ;
                                      }
                                    }
                                  }
                                  case sha1 {
                                    description 'Secure Hash Algorithm.'
                                                ;
                                    choice sha1-password-type {
                                      case unencrypted {
                                        leaf sha1-key {
                                          description 'SHA1 key.'
                                                      ;
                                          type string {
                                            length 40 ;
                                          }
                                          mandatory true ;
                                        }
                                      }
                                      case encrypted {
                                        leaf encry-sha1-key {
                                          description 'Encrypted sha1 key.'
                                                      ;
                                          type string {
                                            length 1..128 ;
                                          }
                                          mandatory true ;
                                        }
                                        ncd:revise-date 2019-12-16 ;
                                      }
                                    }
                                  }
                                  case keychain {
                                    description Keychain ;
                                    leaf keychain-name {
                                      description 'Keychain name.'
                                                  ;
                                      type string {
                                        length 1..31 ;
                                      }
                                      mandatory true ;
                                    }
                                    ncd:revise-date 2017-06-04 ;
                                  }
                                }
                              }
                              leaf roll-interval {
                                description 'Rollover interval.'
                                            ;
                                type uint32 {
                                  range 0..100000 ;
                                }
                                units minute ;
                                default 0 ;
                              }
                            }
                            case encryption-null {
                              description 'NO encryption.'
                                          ;
                              leaf encryption-null {
                                description 'NO encryption.'
                                            ;
                                type empty ;
                                mandatory true ;
                              }
                            }
                          }
                        }
                      }
                    }
                  }
                  container keychain {
                    description 'Keychain configuration of interface.'
                                ;
                    presence intf-auth-keychain-presence ;
                    leaf keychain-name {
                      description 'The name of interface authentication keychai'
                                + 'n.'
                                  ;
                      type string {
                        length 1..31 ;
                      }
                      mandatory true ;
                    }
                    ncd:revise-date 2017-06-04 ;
                  }
                  container cost-lag-down {
                    description 'Configure interface cost when link detects lag'
                              + ' down.'
                                ;
                    choice cost-lag-down {
                      description 'Configure interface cost when link detects l'
                                + 'ag down.'
                                  ;
                      case increase-value {
                        description 'Set increase cost when link detects lag do'
                                  + 'wn.'
                                    ;
                        leaf increase-value {
                          description 'The increase cost value'
                                      ;
                          type uint16 {
                            range 100..10000 ;
                          }
                        }
                      }
                      case maximum {
                        description 'Set maximum cost when link detects lag dow'
                                  + 'n.'
                                    ;
                        leaf maximum {
                          description 'Set maximum cost'
                                      ;
                          type empty ;
                        }
                      }
                    }
                    ncd:revise-date 2019-08-03 ;
                  }
                  container segment-routing {
                    description 'Configure segment-routing parameters'
                                ;
                    container srv6 {
                      description 'Set IPv6 segment routing for IPv6 dataplane.'
                                  ;
                      leaf pspFlag {
                        // if-feature segment-routing ;
                        description 'PSP flavour'
                                    ;
                        type enumeration {
                          enum enable {
                            value 1 ;
                            description enable ;
                          }
                          enum disable {
                            value 0 ;
                            description disable ;
                          }
                        }
                        default disable ;
                      }
                    }
                    ncd:revise-date 2019-08-20 ;
                  }
                  container cost-bfd-down {
                    description 'Configure interface cost when link detects bfd'
                              + ' down.'
                                ;
                    choice cost-bfd-down {
                      description 'Configure interface cost when link detects b'
                                + 'fd down.'
                                  ;
                      case increase-value {
                        description 'Set increase cost when link detects bfd do'
                                  + 'wn.'
                                    ;
                        leaf increase-value {
                          description 'The increase cost value'
                                      ;
                          type uint16 {
                            range 100..10000 ;
                          }
                        }
                      }
                      case maximum {
                        description 'Set maximum cost when link detects bfd dow'
                                  + 'n.'
                                    ;
                        leaf maximum {
                          description 'Set maximum cost'
                                      ;
                          type empty ;
                        }
                      }
                    }
                    ncd:revise-date 2019-11-23 ;
                  }
                  container ti-lfa {
                    description 'tilfa attribute of interface'
                                ;
                    list srlg {
                      description 'shared risk link group of this interface'
                                  ;
                      key srlg-id ;
                      leaf srlg-id {
                        description 'identity of srlg'
                                    ;
                        type uint32 ;
                      }
                    }
                    ncd:revise-date 2020-04-10 ;
                  }
                  container suppress-flapping {
                    description 'Suppress flapping.'
                                ;
                    container adjacency {
                      description 'Suppress flapping for adjacency.'
                                  ;
                      leaf capability {
                        description 'Capability of suppress flapping for adjace'
                                  + 'ncy.'
                                    ;
                        type enumeration {
                          enum enable {
                            value 1 ;
                            description 'Enable suppress flapping for adjacency.'
                                        ;
                          }
                          enum disable {
                            value 2 ;
                            description 'Disable suppress flapping for adjacency.'
                                        ;
                          }
                        }
                      }
                      container detect-parameter {
                        description 'Set detect parameter of suppress flapping '
                                  + 'for adjacency.'
                                    ;
                        presence detect-parameter ;
                        leaf detect-interval {
                          description 'Detect interval.'
                                      ;
                          type uint16 {
                            range 1..300 ;
                          }
                          units second ;
                          mandatory true ;
                        }
                        leaf threshold {
                          description 'Threshold of flapping.'
                                      ;
                          type uint16 {
                            range 1..1000 ;
                          }
                          units second ;
                          mandatory true ;
                        }
                        leaf resume-interval {
                          description 'Resume interval.'
                                      ;
                          type uint16 {
                            range 2..1000 ;
                          }
                          units second ;
                          mandatory true ;
                        }
                      }
                      container hold-down {
                        description 'Hold down mode.'
                                    ;
                        presence hold-down ;
                        leaf hold-interval {
                          description 'Hold down interval.'
                                      ;
                          type uint16 {
                            range 1..600 ;
                          }
                          units second ;
                          mandatory true ;
                        }
                      }
                    }
                    ncd:revise-date 2020-07-23 ;
                  }
                  container link-sd {
                    description 'Configure interface cost  when link is detecte'
                              + 'd SD signal.'
                                ;
                    presence link-sd ;
                    container cost {
                      description 'Configure interface cost when link is detect'
                                + 'ed SD signal.'
                                  ;
                      choice cost {
                        description 'Configure interface cost when link is dete'
                                  + 'cted SD signal.'
                                    ;
                        default increase-value ;
                        case maximum {
                          description 'Set maximum cost when link is in detecte'
                                    + 'd SD siginal.'
                                      ;
                          leaf maximum {
                            description 'Set maximum cost when link is in detected SD siginal.'
                                        ;
                            type empty ;
                          }
                        }
                        case increase-value {
                          description 'Set increase cost when link is detected '
                                    + 'SD siginal.'
                                      ;
                          leaf increase-value {
                            description 'Set increase cost when link is detected SD siginal.'
                                        ;
                            type uint16 {
                              range 100..10000 ;
                            }
                            default 3000 ;
                          }
                        }
                      }
                    }
                    ncd:revise-date 2020-09-12 ;
                  }
                }
              }
              container stub {
                description 'Specify a stub area.'
                            ;
                leaf no-summary {
                  description 'Do not inject inter-area routes into area.'
                              ;
                  type empty ;
                }
                leaf default-cost {
                  description "Stub's advertised default summary cost."
                              ;
                  type uint32 {
                    range 0..16777215 ;
                  }
                  default 1 ;
                }
                leaf default-origin {
                  description 'Notify default route in stub area.'
                              ;
                  type empty ;
                  ncd:revise-date 2016-07-04 ;
                }
              }
              container virtual-links {
                description 'Configuration of virtual link.'
                            ;
                list virtual-link {
                  description 'Configuration of virtual link.'
                              ;
                  key neighbor-id ;
                  leaf neighbor-id {
                    description 'Router ID of the virtual link neighbor.'
                                ;
                    type ncd:ipv4-address ;
                  }
                  leaf hello-interval {
                    description 'Time between hello packets over virtual link.'
                                ;
                    type uint32 {
                      range 1..8192 ;
                    }
                    units second ;
                    default 10 ;
                  }
                  leaf dead-interval {
                    description 'Interval after which a virtual link neighbor i'
                              + 's declared dead.'
                                ;
                    type uint32 {
                      range 1..8192 ;
                    }
                    units second ;
                  }
                  leaf retransmit-interval {
                    description 'Time between retransmitting lost link state ad'
                              + 'vertisements over virtual link.'
                                ;
                    type uint32 {
                      range 1..8192 ;
                    }
                    units second ;
                    default 5 ;
                  }
                  leaf transmit-delay {
                    description 'LSA transmit delay over virtual link.'
                                ;
                    type uint32 {
                      range 1..8192 ;
                    }
                    units second ;
                    default 1 ;
                  }
                  container ipsec {
                    description 'IPSEC configuration of virtual link.'
                                ;
                    choice ipsec {
                      description 'IPSEC configuration of virtual link.'
                                  ;
                      case authentication {
                        description 'IPSEC authentication configuration of virt'
                                  + 'ual link.'
                                    ;
                        container authentication {
                          description 'IPSEC authentication configuration of vi'
                                    + 'rtual link.'
                                      ;
                          presence vlink-auth-presence ;
                          leaf spi-id {
                            description 'Security parameters index ID.'
                                        ;
                            type uint32 {
                              range 256..32767 ;
                            }
                            mandatory true ;
                          }
                          container authentication-key {
                            description 'Key of authentication algorithm.'
                                        ;
                            choice authentication-key {
                              description 'Key of authentication algorithm.'
                                          ;
                              mandatory true ;
                              case md5 {
                                description 'Message Digest Algorithm.'
                                            ;
                                choice md5-password-type {
                                  case unencrypted {
                                    leaf md5-key {
                                      description 'MD5 key.'
                                                  ;
                                      type string {
                                        length 32 ;
                                      }
                                      mandatory true ;
                                    }
                                  }
                                  case encrypted {
                                    leaf encry-md5-key {
                                      description 'Encrpyted MD5 key.'
                                                  ;
                                      type string {
                                        length 1..128 ;
                                      }
                                      mandatory true ;
                                    }
                                    ncd:revise-date 2019-12-16 ;
                                  }
                                }
                              }
                              case sha1 {
                                description 'Secure Hash Algorithm.'
                                            ;
                                choice sha1-password-type {
                                  case unencrypted {
                                    leaf sha1-key {
                                      description 'SHA1 key.'
                                                  ;
                                      type string {
                                        length 40 ;
                                      }
                                      mandatory true ;
                                    }
                                  }
                                  case encrypted {
                                    leaf encry-sha1-key {
                                      description 'Encrypted SHA1 key.'
                                                  ;
                                      type string {
                                        length 1..128 ;
                                      }
                                      mandatory true ;
                                    }
                                    ncd:revise-date 2019-12-16 ;
                                  }
                                }
                              }
                              case keychain {
                                description Keychain. ;
                                leaf keychain-name {
                                  description 'Keychain name.'
                                              ;
                                  type string {
                                    length 1..31 ;
                                  }
                                  mandatory true ;
                                }
                                ncd:revise-date 2017-06-04 ;
                              }
                            }
                          }
                          leaf roll-interval {
                            description 'Rollover interval.'
                                        ;
                            type uint32 {
                              range 0..100000 ;
                            }
                            units minute ;
                            default 0 ;
                          }
                        }
                      }
                      case encryption {
                        description 'IPSEC encryption configuration of virtual '
                                  + 'link.'
                                    ;
                        container encryption {
                          description 'IPSEC encryption configuration of virtua'
                                    + 'l link.'
                                      ;
                          presence vlink-encryption-presence ;
                          leaf spi-id {
                            description 'Security parameters index ID.'
                                        ;
                            type uint32 {
                              range 256..32767 ;
                            }
                            mandatory true ;
                          }
                          container encryption-key {
                            description 'Key of encryption algorithm.'
                                        ;
                            choice encryption-key {
                              description 'Key of encryption algorithm.'
                                          ;
                              mandatory true ;
                              case null {
                                description 'NULL encryption.'
                                            ;
                                leaf null {
                                  description 'NULL encryption.'
                                              ;
                                  type empty ;
                                  mandatory true ;
                                }
                              }
                              case des {
                                description 'Data Encrypt Standard algorithm.'
                                            ;
                                choice des-password-type {
                                  case unencrypted {
                                    leaf des-key {
                                      description 'DES key.'
                                                  ;
                                      type string {
                                        length 16 ;
                                      }
                                      mandatory true ;
                                    }
                                  }
                                  case encrypted {
                                    leaf encry-des-key {
                                      description 'Encrypted des key.'
                                                  ;
                                      type string {
                                        length 1..128 ;
                                      }
                                      mandatory true ;
                                    }
                                    ncd:revise-date 2019-12-16 ;
                                  }
                                }
                              }
                              case triple-des {
                                description 'Triple Data Encryption algorithm.'
                                            ;
                                choice triple-des-password-type {
                                  case unencrypted {
                                    leaf triple-des-key {
                                      description '3DES key.'
                                                  ;
                                      type string {
                                        length 48 ;
                                      }
                                      mandatory true ;
                                    }
                                  }
                                  case encrypted {
                                    leaf encry-triple-des-key {
                                      description 'Encrypted 3des key.'
                                                  ;
                                      type string {
                                        length 1..128 ;
                                      }
                                      mandatory true ;
                                    }
                                    ncd:revise-date 2019-12-16 ;
                                  }
                                }
                              }
                              case aes-cbc {
                                description 'Advanced Encryption Standard algorithm.'
                                            ;
                                choice aes-password-type {
                                  case unencrypted {
                                    leaf aes-cbc-key {
                                      description 'AES key.'
                                                  ;
                                      type string {
                                        length 32 ;
                                      }
                                      mandatory true ;
                                    }
                                  }
                                  case encrypted {
                                    leaf encry-aes-cbc-key {
                                      description 'Encrypted aes key.'
                                                  ;
                                      type string {
                                        length 1..128 ;
                                      }
                                      mandatory true ;
                                    }
                                    ncd:revise-date 2019-12-16 ;
                                  }
                                }
                              }
                              case keychain {
                                description Keychain. ;
                                leaf keychain-name {
                                  description 'Keychain name.'
                                              ;
                                  type string {
                                    length 1..31 ;
                                  }
                                  mandatory true ;
                                }
                                ncd:revise-date 2017-06-04 ;
                              }
                            }
                          }
                          container authentication-key {
                            description 'Key of authentication algorithm.'
                                        ;
                            choice authentication-key {
                              description 'Key of authentication algorithm.'
                                          ;
                              mandatory true ;
                              case md5 {
                                description 'Message Digest Algorithm.'
                                            ;
                                choice md5-password-type {
                                  case unencrypted {
                                    leaf md5-key {
                                      description 'MD5 key.'
                                                  ;
                                      type string {
                                        length 32 ;
                                      }
                                      mandatory true ;
                                    }
                                  }
                                  case encrypted {
                                    leaf encry-md5-key {
                                      description 'Encrypted MD5 key.'
                                                  ;
                                      type string {
                                        length 1..128 ;
                                      }
                                      mandatory true ;
                                    }
                                    ncd:revise-date 2019-12-16 ;
                                  }
                                }
                              }
                              case sha1 {
                                description 'Secure Hash Algorithm.'
                                            ;
                                choice sha1-password-type {
                                  case unencrypted {
                                    leaf sha1-key {
                                      description 'SHA1 key.'
                                                  ;
                                      type string {
                                        length 40 ;
                                      }
                                      mandatory true ;
                                    }
                                  }
                                  case encrypted {
                                    leaf encry-sha1-key {
                                      description 'Encrypted sha1 key.'
                                                  ;
                                      type string {
                                        length 1..128 ;
                                      }
                                      mandatory true ;
                                    }
                                    ncd:revise-date 2019-12-16 ;
                                  }
                                }
                              }
                              case keychain {
                                description Keychain ;
                                leaf keychain-name {
                                  description 'Keychain name.'
                                              ;
                                  type string {
                                    length 1..31 ;
                                  }
                                  mandatory true ;
                                }
                                ncd:revise-date 2017-06-04 ;
                              }
                            }
                          }
                          leaf roll-interval {
                            description 'Rollover interval.'
                                        ;
                            type uint32 {
                              range 0..100000 ;
                            }
                            units minute ;
                            default 0 ;
                          }
                        }
                      }
                    }
                  }
                }
              }
              container ipsec {
                description 'IPSEC configuration of area.'
                            ;
                choice ipsec {
                  description 'IPSEC configuration of area.'
                              ;
                  case authentication {
                    description 'IPSEC authentication configuration of area.'
                                ;
                    container authentication {
                      description 'IPSEC authentication configuration of area.'
                                  ;
                      presence area-auth-presence ;
                      leaf spi-id {
                        description 'Security parameters index ID.'
                                    ;
                        type uint32 {
                          range 256..32767 ;
                        }
                        mandatory true ;
                      }
                      container authentication-key {
                        description 'Key of authentication algorithm.'
                                    ;
                        choice authentication-key {
                          description 'Key of authentication algorithm.'
                                      ;
                          mandatory true ;
                          case md5 {
                            description 'Message Digest Algorithm.'
                                        ;
                            choice md5-password-type {
                              case unencrypted {
                                leaf md5-key {
                                  description 'MD5 key.'
                                              ;
                                  type string {
                                    length 32 ;
                                  }
                                  mandatory true ;
                                }
                              }
                              case encrypted {
                                leaf encry-md5-key {
                                  description 'Encrypted MD5 key.'
                                              ;
                                  type string {
                                    length 1..128 ;
                                  }
                                  mandatory true ;
                                }
                                ncd:revise-date 2019-12-16 ;
                              }
                            }
                          }
                          case sha1 {
                            description 'Secure Hash Algorithm.'
                                        ;
                            choice sha1-password-type {
                              case unencrypted {
                                leaf sha1-key {
                                  description 'SHA1 key.'
                                              ;
                                  type string {
                                    length 40 ;
                                  }
                                  mandatory true ;
                                }
                              }
                              case encrypted {
                                leaf encry-sha1-key {
                                  description 'SHA1 key.'
                                              ;
                                  type string {
                                    length 1..128 ;
                                  }
                                  mandatory true ;
                                }
                                ncd:revise-date 2019-12-16 ;
                              }
                            }
                          }
                          case keychain {
                            description Keychain. ;
                            leaf keychain-name {
                              description 'Keychain name.'
                                          ;
                              type string {
                                length 1..31 ;
                              }
                              mandatory true ;
                            }
                            ncd:revise-date 2017-06-04 ;
                          }
                        }
                      }
                      leaf roll-interval {
                        description 'Rollover interval.'
                                    ;
                        type uint32 {
                          range 0..100000 ;
                        }
                        units minute ;
                        default 0 ;
                      }
                    }
                  }
                  case encryption {
                    description 'IPSEC encryption configuration of area.'
                                ;
                    container encryption {
                      description 'IPSEC encryption configuration of area.'
                                  ;
                      presence area-encryption-presence ;
                      leaf spi-id {
                        description 'Security parameters index ID.'
                                    ;
                        type uint32 {
                          range 256..32767 ;
                        }
                        mandatory true ;
                      }
                      container encryption-key {
                        description 'Key of encryption algorithm.'
                                    ;
                        choice encryption-key {
                          description 'Key of encryption algorithm.'
                                      ;
                          mandatory true ;
                          case null {
                            description 'NULL encryption.'
                                        ;
                            leaf null {
                              description 'NULL encryption.'
                                          ;
                              type empty ;
                              mandatory true ;
                            }
                          }
                          case des {
                            description 'Data Encrypt Standard algorithm.'
                                        ;
                            choice des-password-type {
                              case unencrypted {
                                leaf des-key {
                                  description 'DES key.'
                                              ;
                                  type string {
                                    length 16 ;
                                  }
                                  mandatory true ;
                                }
                              }
                              case encrypted {
                                leaf encry-des-key {
                                  description 'Encrypted des key.'
                                              ;
                                  type string {
                                    length 1..128 ;
                                  }
                                  mandatory true ;
                                }
                                ncd:revise-date 2019-12-16 ;
                              }
                            }
                          }
                          case triple-des {
                            description 'Triple Data Encryption algorithm.'
                                        ;
                            choice triple-des-password-type {
                              case unencrypted {
                                leaf triple-des-key {
                                  description '3DES key.'
                                              ;
                                  type string {
                                    length 48 ;
                                  }
                                  mandatory true ;
                                }
                              }
                              case encrypted {
                                leaf encry-triple-des-key {
                                  description 'Encrypted 3DES key.'
                                              ;
                                  type string {
                                    length 1..128 ;
                                  }
                                  mandatory true ;
                                }
                                ncd:revise-date 2019-12-16 ;
                              }
                            }
                          }
                          case aes-cbc {
                            description 'Advanced Encryption Standard algorithm.'
                                        ;
                            choice aes-password-type {
                              case unencrypted {
                                leaf aes-cbc-key {
                                  description 'AES key.'
                                              ;
                                  type string {
                                    length 32 ;
                                  }
                                  mandatory true ;
                                }
                              }
                              case encrypted {
                                leaf encry-aes-cbc-key {
                                  description 'AES key.'
                                              ;
                                  type string {
                                    length 1..128 ;
                                  }
                                  mandatory true ;
                                }
                                ncd:revise-date 2019-12-16 ;
                              }
                            }
                          }
                          case keychain {
                            description Keychain. ;
                            leaf keychain-name {
                              description 'Keychain name.'
                                          ;
                              type string {
                                length 1..31 ;
                              }
                              mandatory true ;
                            }
                            ncd:revise-date 2017-06-04 ;
                          }
                        }
                      }
                      container authentication-key {
                        description 'Key of authentication algorithm.'
                                    ;
                        choice authentication-key {
                          description 'Key of authentication algorithm.'
                                      ;
                          mandatory true ;
                          case md5 {
                            description 'Message Digest Algorithm.'
                                        ;
                            choice md5-password-type {
                              case unencrypted {
                                leaf md5-key {
                                  description 'MD5 key.'
                                              ;
                                  type string {
                                    length 32 ;
                                  }
                                  mandatory true ;
                                }
                              }
                              case encrypted {
                                leaf encry-md5-key {
                                  description 'Encrypted MD5 key.'
                                              ;
                                  type string {
                                    length 1..128 ;
                                  }
                                  mandatory true ;
                                }
                                ncd:revise-date 2019-12-16 ;
                              }
                            }
                          }
                          case sha1 {
                            description 'Secure Hash Algorithm.'
                                        ;
                            choice sha1-password-type {
                              case unencryted {
                                leaf sha1-key {
                                  description 'SHA1 key.'
                                              ;
                                  type string {
                                    length 40 ;
                                  }
                                  mandatory true ;
                                }
                              }
                              case encrypted {
                                leaf encry-sha1-key {
                                  description 'Encrypted SHA1 key.'
                                              ;
                                  type string {
                                    length 1..128 ;
                                  }
                                  mandatory true ;
                                }
                                ncd:revise-date 2019-12-16 ;
                              }
                            }
                          }
                          case keychain {
                            description Keychain ;
                            leaf keychain-name {
                              description 'Keychain name.'
                                          ;
                              type string {
                                length 1..31 ;
                              }
                              mandatory true ;
                            }
                            ncd:revise-date 2017-06-04 ;
                          }
                        }
                      }
                      leaf roll-interval {
                        description 'Rollover interval.'
                                    ;
                        type uint32 {
                          range 0..100000 ;
                        }
                        units minute ;
                        default 0 ;
                      }
                    }
                  }
                }
              }
              container keychain {
                description 'Keychain configuration of area.'
                            ;
                presence area-auth-keychain-presence ;
                leaf keychain-name {
                  description 'The name of area authentication keychain.'
                              ;
                  type string {
                    length 1..31 ;
                  }
                  mandatory true ;
                }
                ncd:revise-date 2017-06-04 ;
              }
              container nssa {
                description 'Specify a NSSA area'
                            ;
                leaf translator-role {
                  description "Config the router's translator role when transla"
                            + "ting type-7 route to type-5 route"
                              ;
                  type enumeration {
                    enum candidate {
                      value 0 ;
                      description 'The router is a member of candidate list'
                                  ;
                    }
                    enum always {
                      value 1 ;
                      description 'The router is always a translator'
                                  ;
                    }
                  }
                  default candidate ;
                }
                leaf trans-stab-interval {
                  description 'The interval of keep translating when translatin'
                            + 'g state becomes disable'
                              ;
                  type uint32 {
                    range 0..65535 {
                      description 'The interval of keep translating when transl'
                                + 'ating state becomes disable'
                                  ;
                    }
                  }
                  default 40 ;
                }
                leaf no-summary {
                  description 'Do not send summary LSA into area'
                              ;
                  type empty ;
                }
                leaf no-redistribution {
                  description 'Do not redistribute external LSA into NSSA area'
                              ;
                  type empty ;
                }
                leaf suppress-fa {
                  description 'Suppress FA when translating Type-7 to Type-5'
                              ;
                  type empty ;
                }
                container default-information-originate {
                  description 'nssa area default information config'
                              ;
                  presence default-information-originate-presence ;
                  leaf metric {
                    description 'The metric of default type-7 route'
                                ;
                    type uint32 {
                      range 1..16777214 {
                        description 'The metirc of default type-7 route'
                                    ;
                      }
                    }
                    default 1 ;
                  }
                  leaf metric-type {
                    description 'The metric type of default type-7 route'
                                ;
                    type enumeration {
                      enum ext-2 {
                        value 0 ;
                        description 'The metric of default type-7 route is ext-2'
                                    ;
                      }
                      enum ext-1 {
                        value 1 ;
                        description 'The metric of default type-7 route is ext-1'
                                    ;
                      }
                    }
                    default ext-2 ;
                  }
                }
                ncd:revise-date 2020-05-21 ;
              }
              container multi-area-interfaces {
                description 'Configure multi-area adjacency'
                            ;
                list multi-area-interface {
                  description 'Configure multi-area adjacency on this interface'
                              ;
                  key interface-name ;
                  leaf interface-name {
                    description 'Interface name'
                                ;
                    type ncd:ifname {
                      length 1..31 ;
                    }
                  }
                  leaf hello-interval {
                    description 'The time between hello packets, Seconds'
                                ;
                    type uint32 {
                      range 1..65535 ;
                    }
                    units second ;
                  }
                  leaf dead-interval {
                    description 'The interval after which a neighbor is declare'
                              + 'd dead, Seconds'
                                ;
                    type uint32 {
                      range 1..65535 ;
                    }
                    units second ;
                  }
                  leaf cost {
                    description 'The cost of sending a data packet on the inter'
                              + 'face, expressed in the link state metric.'
                                ;
                    type uint32 {
                      range 1..65535 ;
                    }
                  }
                  leaf mtu-ignore {
                    description 'Ignore the mtu mismatch when exchanging DD pac'
                              + 'ket'
                                ;
                    type empty ;
                  }
                  leaf retransmit-interval {
                    description 'Time between retransmitting lost link state ad'
                              + 'vertisements, Seconds'
                                ;
                    type uint32 {
                      range 1..65535 ;
                    }
                    units second ;
                    default 5 ;
                  }
                  leaf transmit-delay {
                    description 'The estimated number of seconds it takes to tr'
                              + 'ansmit a LSU packet over this interface.'
                                ;
                    type uint32 {
                      range 1..65535 ;
                    }
                    units second ;
                    default 1 ;
                  }
                  container authentication {
                    description Authentication ;
                    choice authentication {
                      description Authentication ;
                      case keychain {
                        description 'Authentication keychain name'
                                    ;
                        leaf keychain {
                          description 'Authentication keychain name'
                                      ;
                          type string {
                            length 1..31 ;
                          }
                        }
                      }
                    }
                  }
                }
                ncd:revise-date 2020-08-20 ;
              }
            }
          }
          container domain-ids {
            description 'OSPFv3 domain ID configuration.'
                        ;
            list domain-id {
              description 'OSPFv3 domain ID configuration.'
                          ;
              key 'type value'
                  ;
              leaf type {
                description 'domain ID type.'
                            ;
                type enumeration {
                  enum 0005 {
                    value 1 ;
                    description 'Type 0x0005.'
                                ;
                  }
                  enum 0105 {
                    value 2 ;
                    description 'Type 0x0105.'
                                ;
                  }
                  enum 0205 {
                    value 3 ;
                    description 'Type 0x0205.'
                                ;
                  }
                }
              }
              leaf value {
                description 'domain ID value.'
                            ;
                type string {
                  length 12 ;
                }
              }
              leaf flag {
                description 'Specify the domain ID is primary domain ID or seco'
                          + 'ndary domain ID.'
                            ;
                type enumeration {
                  enum primary {
                    value 0 ;
                    description 'Primary domain ID.'
                                ;
                  }
                  enum secondary {
                    value 1 ;
                    description 'Secondary domain ID.'
                                ;
                  }
                }
              }
            }
            ncd:revise-date 2016-07-04 ;
          }
          container distance-policy {
            // if-feature distance-policy ;
            description 'Distance of policy.'
                        ;
            leaf policy-type {
              description 'The type of policy.'
                          ;
              type enumeration {
                enum route-policy {
                  value 1 ;
                  description 'Route-type is route-policy.'
                              ;
                }
                enum route-map {
                  value 2 ;
                  description 'Route-type is route-map.'
                              ;
                }
              }
            }
            leaf policy-name {
              description 'The name of policy.'
                          ;
              type string {
                length 1..200 {
                  description 'Name of policy,characters from 1 to 200.'
                              ;
                }
              }
            }
            ncd:revise-date 2018-11-28 ;
          }
          container segment-routing {
            description 'Configure segment-routing parameters'
                        ;
            container mpls {
              description 'Configure segment-routing mpls parameters'
                          ;
              leaf capability {
                // if-feature segment-routing ;
                description 'Configure segment-routing mpls capability'
                            ;
                type enumeration {
                  enum enable {
                    value 1 ;
                    description enable ;
                  }
                  enum disable {
                    value 2 ;
                    description disable ;
                  }
                }
                default disable ;
              }
              container adj-sid {
                description 'Set segment routing MPLS adj-sid type.'
                            ;
                leaf type {
                  description 'Configure segment routing MPLS adj-sid type.'
                              ;
                  type enumeration {
                    enum hybrid {
                      value 1 ;
                      description hybrid ;
                    }
                    enum static {
                      value 2 ;
                      description static ;
                    }
                  }
                  default hybrid ;
                }
                ncd:revise-date 2020-03-28 ;
              }
              container entropy-label {
                description 'Configure segment routing mpls entropy label.'
                            ;
                leaf capability {
                  description 'Configure segment routing mpls entropy label.'
                              ;
                  type enumeration {
                    enum enable {
                      value 1 ;
                      description Enable ;
                    }
                    enum disable {
                      value 2 ;
                      description Disable ;
                    }
                  }
                  default disable ;
                }
                ncd:revise-date 2019-11-13 ;
              }
            }
            container srv6 {
              description 'Set IPv6 segment routing for IPv6 dataplane.'
                          ;
              leaf capability {
                // if-feature segment-routing ;
                description 'Configure  capability'
                            ;
                type enumeration {
                  enum enable {
                    value 1 ;
                    description enable ;
                  }
                  enum disable {
                    value 2 ;
                    description disable ;
                  }
                }
                default disable ;
              }
              leaf pspFlag {
                // if-feature segment-routing ;
                description 'PSP flavour'
                            ;
                type enumeration {
                  enum enable {
                    value 1 ;
                    description enable ;
                  }
                  enum disable {
                    value 0 ;
                    description disable ;
                  }
                }
                default disable ;
              }
              container locators {
                description 'SRv6 locator configuration.'
                            ;
                list locator {
                  description 'SRv6 locator configuration.'
                              ;
                  key locator-name ;
                  leaf locator-name {
                    description 'The name of locator.'
                                ;
                    type string {
                      length 1..31 ;
                    }
                  }
                  container end-sids {
                    description 'End-SID configuration.'
                                ;
                    list end-sid {
                      description 'End-SID configuration.'
                                  ;
                      key func-code ;
                      leaf func-code {
                        description 'The function code of End-SID.'
                                    ;
                        type ncd:ipv6-address ;
                      }
                      leaf psp {
                        description 'The psp attribute of End-SID.'
                                    ;
                        type int8 ;
                        default 0 ;
                      }
                      leaf usp {
                        description 'The usp attribute of End-SID.'
                                    ;
                        type int8 ;
                        default 0 ;
                      }
                    }
                  }
                  container end-x-sids {
                    description 'End-X-SID configuration.'
                                ;
                    list end-x-sid {
                      description 'End-X-SID configuration.'
                                  ;
                      key func-code ;
                      leaf func-code {
                        description 'The function code of End-X-SID.'
                                    ;
                        type ncd:ipv6-address ;
                      }
                      leaf interface-name {
                        description 'The name of interface associated with End-'
                                  + 'X-SID.'
                                    ;
                        type ncd:ifname {
                          length 1..31 ;
                        }
                        mandatory true ;
                      }
                      leaf neighbor-id {
                        description 'The router-id of neighbor associated with '
                                  + 'End-X-SID.'
                                    ;
                        type ncd:ipv4-address ;
                      }
                      leaf psp {
                        description 'The psp attribute of End-X-SID.'
                                    ;
                        type uint8 ;
                        default 0 ;
                      }
                      leaf usp {
                        description 'The usp attribute of End-SID.'
                                    ;
                        type uint8 ;
                        default 0 ;
                      }
                    }
                  }
                  container end-sid-auto {
                    description 'Configure the SRv6 End SID automatically.'
                                ;
                    presence end-sid-auto ;
                    leaf psp {
                      description 'The psp attribute of End-SID-AUTO.'
                                  ;
                      type empty ;
                    }
                    leaf usp {
                      description 'The usp attribute of End-SID-AUTO.'
                                  ;
                      type empty ;
                    }
                    ncd:revise-date 2021-01-08 ;
                  }
                  container end-x-sid-auto {
                    description 'Configure the SRv6 End X SID automatically.'
                                ;
                    presence end-x-sid-auto ;
                    leaf psp {
                      description 'The psp attribute of End-X-SID-AUTO.'
                                  ;
                      type empty ;
                    }
                    leaf usp {
                      description 'The usp attribute of End-X-SID-AUTO.'
                                  ;
                      type empty ;
                    }
                    ncd:revise-date 2021-01-08 ;
                  }
                }
                ncd:revise-date 2020-09-23 ;
              }
              ncd:revise-date 2019-08-20 ;
            }
            ncd:revise-date 2019-03-28 ;
          }
          container bgp-ls {
            description 'Distribute link-state data using BGP.'
                        ;
            presence bgp-ls ;
            leaf instance-id {
              description 'Link-state data instance identifier.'
                          ;
              type uint32 {
                range 0..65535 ;
              }
              default 0 ;
            }
            ncd:revise-date 2019-07-11 ;
          }
          container frr {
            description 'OSPF fast reroute parameters'
                        ;
            presence fast-route ;
            container ti-lfa {
              description 'Set OSPF TI-LFA'
                          ;
              presence ti-lfa ;
              container protection-type {
                description 'Specify protection type'
                            ;
                presence protection-type ;
                leaf node-protecting {
                  description 'Specify node protecting'
                              ;
                  type empty ;
                }
              }
              leaf srv6 {
                // if-feature segment-routing ;
                description 'Configure srv6 fast-reroute TI-LFA'
                            ;
                type enumeration {
                  enum enable {
                    value 1 ;
                    description enable ;
                  }
                  enum disable {
                    value 2 ;
                    description disable ;
                  }
                }
                default disable ;
              }
              leaf sr-mpls {
                // if-feature segment-routing ;
                description 'Configure sr-mpls fast-reroute TI-LFA'
                            ;
                type enumeration {
                  enum enable {
                    value 1 ;
                    description enable ;
                  }
                  enum disable {
                    value 2 ;
                    description disable ;
                  }
                }
                default disable ;
              }
            }
            container tilfa-priority {
              description 'OSPF fast-reroute TI-LFA priority'
                          ;
              presence priority ;
              leaf tilfa-priority {
                description 'OSPF fast-reroute TI-LFA priority'
                            ;
                type uint8 {
                  range 1..255 ;
                }
                default 110 ;
              }
            }
            container ipfrr-priority {
              description 'OSPF fast-reroute IP-FRR priority'
                          ;
              presence priority ;
              leaf ipfrr-priority {
                description 'OSPF fast-reroute IP-FRR priority'
                            ;
                type uint8 {
                  range 1..255 ;
                }
                default 110 ;
              }
            }
            ncd:revise-date 2019-10-08 ;
          }
          container microloop-prevention {
            description 'Configure microloop prevention for OSPFv3.'
                        ;
            container segment-routing {
              // if-feature segment-routing ;
              description 'Configure microloop prevention for segment routing.'
                          ;
              container mpls {
                description 'Configure microloop prevention for IPv6 SR-MPLS.'
                            ;
                leaf capability {
                  description 'Microloop prevention capability for SR-MPLS.'
                              ;
                  type enumeration {
                    enum enable {
                      value 1 ;
                      description 'Enable microloop-prevention for SR MPLS.'
                                  ;
                    }
                    enum disable {
                      value 2 ;
                      description 'Disable microloop-prevention for SR MPLS.'
                                  ;
                    }
                  }
                  default disable ;
                }
              }
              container srv6 {
                description 'Configure microloop prevention for SRv6.'
                            ;
                leaf capability {
                  description 'Microloop prevention capability for SRv6.'
                              ;
                  type enumeration {
                    enum enable {
                      value 1 ;
                      description 'Enable microloop-prevention for SRv6.'
                                  ;
                    }
                    enum disable {
                      value 2 ;
                      description 'Disable microloop-prevention for SRv6.'
                                  ;
                    }
                  }
                  default disable ;
                }
              }
              leaf delay-time {
                description 'Delay time of microloop prevention for SR.'
                            ;
                type uint32 {
                  range 1..300000 {
                    description 'delay time'
                                ;
                  }
                }
                units milliseconds ;
                default 3000 ;
              }
            }
            ncd:revise-date 2019-10-17 ;
          }
          container max-metric {
            description 'Origin max-metric router-LSAs'
                        ;
            container router-lsa {
              description 'Origin max-metric router-LSAs'
                          ;
              presence router-lsa ;
              container on-startup {
                description 'Origin max-metric router-LSAs after reboot'
                            ;
                leaf timeout {
                  description 'Configure timeout of origining max-metric router'
                            + '-LSAs'
                              ;
                  type uint32 {
                    range 5..86400 {
                      description 'Configure timeout of origining max-metric ro'
                                + 'uter-LSAs'
                                  ;
                    }
                  }
                }
              }
            }
            ncd:revise-date 2020-07-15 ;
          }
          container suppress-flapping {
            description 'Suppress flapping.'
                        ;
            container adjacency {
              description 'Suppress flapping for adjacency.'
                          ;
              leaf capability {
                description 'Capability of suppress flapping for adjacency.'
                            ;
                type enumeration {
                  enum enable {
                    value 1 ;
                    description 'Enable suppress flapping.'
                                ;
                  }
                  enum disable {
                    value 2 ;
                    description 'Disable suppress flapping.'
                                ;
                  }
                }
                default enable ;
              }
            }
            ncd:revise-date 2020-07-23 ;
          }
        }
      }
    }
  }
  container state {
    config false ;
    description State. ;
    container ospfv3 {
      description 'State of OSPFv3.'
                  ;
      container processes {
        description 'OSPFv3 process.'
                    ;
        list process {
          description 'OSPFv3 process.'
                      ;
          key process-id ;
          leaf process-id {
            description 'OSPFv3 process ID.'
                        ;
            type uint32 {
              range 1..65535 ;
            }
          }
          leaf router-id {
            description Router-id. ;
            type ncd:ipv4-address ;
          }
          leaf vrf-name {
            description 'VPN routing/forwarding instance (VRF) name.'
                        ;
            type string {
              length 1..32 ;
            }
          }
          leaf socket-state {
            description 'State of socket.'
                        ;
            type enumeration {
              enum enable {
                value 1 ;
                description 'Enable socket.'
                            ;
              }
              enum disable {
                value 2 ;
                description 'Disable socket.'
                            ;
              }
            }
          }
          container distance {
            description 'Distance of OSPF route.'
                        ;
            leaf external {
              description 'Distance for external routes.'
                          ;
              type uint8 ;
            }
            leaf inter-area {
              description 'Distance for inter-area routes.'
                          ;
              type uint8 ;
            }
            leaf intra-area {
              description 'Distance for intra-area routes.'
                          ;
              type uint8 ;
            }
          }
          leaf external-lsa-count {
            description 'Count of external LSA.'
                        ;
            type uint32 ;
          }
          leaf route-count {
            description 'Count of route.'
                        ;
            type uint32 ;
          }
          leaf default-metric {
            description 'Default metric of Type 5 LSA.'
                        ;
            type uint32 {
              range 1..16777214 ;
            }
          }
          container area-count {
            description 'Count of area.'
                        ;
            leaf total-count {
              description 'Count of area.'
                          ;
              type uint32 ;
            }
            leaf normal-count {
              description 'Count of normal area.'
                          ;
              type uint32 ;
            }
            leaf stub-count {
              description 'Count of stub area.'
                          ;
              type uint32 ;
            }
          }
          container areas {
            description 'OSPFv3 area.'
                        ;
            list area {
              description 'OSPFv3 area.'
                          ;
              key area-id ;
              leaf area-id {
                description 'OSPFv3 area ID in IP address format.'
                            ;
                type ncd:ipv4-address ;
              }
              leaf interface-count {
                description 'Count of interface.'
                            ;
                type uint32 ;
              }
              container ipsec {
                description 'IPSEC configuration of area.'
                            ;
                leaf spi-id {
                  description 'Security parameters index ID.'
                              ;
                  type uint32 {
                    range 256..32767 ;
                  }
                }
                leaf type {
                  description 'Type of authentication or encryption.'
                              ;
                  type enumeration {
                    enum authentication {
                      value 1 ;
                    }
                    enum encryption {
                      value 2 ;
                    }
                  }
                }
                leaf authentication-algorithm {
                  description 'Type of authentication algorithm.'
                              ;
                  type enumeration {
                    enum md5 {
                      value 1 ;
                      description 'Message Digest Algorithm.'
                                  ;
                    }
                    enum sha1 {
                      value 2 ;
                      description 'Secure Hash Algorithm.'
                                  ;
                    }
                    enum keychain {
                      value 4 ;
                      description 'Use keychain for authentication.'
                                  ;
                    }
                  }
                }
                leaf encryption-algorithm {
                  description 'Type of encryption algorithm.'
                              ;
                  type enumeration {
                    enum null {
                      value 1 ;
                      description 'NULL encryption.'
                                  ;
                    }
                    enum des {
                      value 2 ;
                      description 'Data Encrypt Standard algorithm.'
                                  ;
                    }
                    enum triple-des {
                      value 3 ;
                      description 'Triple Data Encryption algorithm.'
                                  ;
                    }
                    enum aes-cbc {
                      value 4 ;
                      description 'Advanced Encryption Standard algorithm.'
                                  ;
                    }
                    enum keychain-encryption {
                      value 6 ;
                      description 'Use keychain for encryption.'
                                  ;
                    }
                  }
                }
              }
              leaf area-type {
                description 'Type of area.'
                            ;
                type enumeration {
                  enum stub {
                    value 1 ;
                  }
                  enum normal {
                    value 2 ;
                  }
                  enum nssa {
                    value 3 ;
                  }
                }
              }
              leaf default-cost {
                description "Stub's advertised default summary cost."
                            ;
                type uint32 {
                  range 0..16777215 ;
                }
              }
              leaf spf-calculate-times {
                description 'SPF calculate times.'
                            ;
                type uint32 ;
              }
              leaf ispf-calculate-times {
                description 'Incremental SPF calculate times'
                            ;
                type uint32 ;
              }
              leaf lsa-count {
                description 'Count of LSA.'
                            ;
                type uint32 ;
              }
              leaf unknown-lsa-count {
                description 'Count of unknown LSA.'
                            ;
                type uint32 ;
              }
            }
          }
          ncd:select process-id ;
        }
      }
      container interfaces {
        description 'OSPFv3 interface.'
                    ;
        container normal-interfaces {
          description 'OSPFv3 normal interface.'
                      ;
          list normal-interface {
            description 'OSPFv3 normal interface.'
                        ;
            key 'process-id area-id interface-name'
                ;
            leaf process-id {
              description 'OSPFv3 process ID.'
                          ;
              type uint32 {
                range 1..65535 ;
              }
            }
            leaf area-id {
              description 'OSPFv3 area ID in IP address format.'
                          ;
              type ncd:ipv4-address ;
            }
            leaf interface-name {
              description 'Interface name.'
                          ;
              type ncd:ifname {
                length 1..31 ;
              }
            }
            leaf admin-state {
              description 'Interface admin state.'
                          ;
              type enumeration {
                enum up {
                  value 1 ;
                }
                enum down {
                  value 2 ;
                }
              }
            }
            leaf protocol-state {
              description 'Interface protocol state.'
                          ;
              type enumeration {
                enum up {
                  value 1 ;
                }
                enum down {
                  value 2 ;
                }
              }
            }
            leaf linklocal-address {
              description 'Link-local address.'
                          ;
              type ncd:ipv6-address ;
            }
            leaf interface-id {
              description 'Interface ID.'
                          ;
              type uint32 ;
            }
            leaf instance-id {
              description 'Interface ID.'
                          ;
              type uint8 ;
            }
            leaf network-type {
              description 'Network type.'
                          ;
              type enumeration {
                enum Nbma {
                  value 3 ;
                }
                enum Point-to-point {
                  value 1 ;
                }
                enum Point-to-multipoint {
                  value 4 ;
                }
                enum P-to-mp-nb {
                  value 5 ;
                }
                enum Broadcast {
                  value 2 ;
                }
                enum Loopback {
                  value 6 ;
                }
              }
            }
            leaf cost {
              description 'Cost value of OSPFv3 interface.'
                          ;
              type uint32 {
                range 1..65535 ;
              }
            }
            leaf transmit-delay {
              description 'LSA transmit delay over link.'
                          ;
              type uint32 {
                range 1..65535 ;
              }
              units second ;
            }
            leaf interface-state {
              description 'State of OSPF interface machine.'
                          ;
              type enumeration {
                enum Down {
                  value 1 ;
                  description 'This is the initial interface state.'
                              ;
                }
                enum Standby {
                  value 2 ;
                  description 'In this state, the interface is one of multiple '
                            + 'interfaces to a link and this interface is desig'
                            + 'nated Standby and is not sending or receiving co'
                            + 'ntrol packets.'
                              ;
                }
                enum Loopback {
                  value 3 ;
                  description "In this state, the router's interface to the net"
                            + "work is looped back."
                              ;
                }
                enum Waiting {
                  value 4 ;
                  description 'In this state, the router is trying to determine'
                            + ' the identity of the (Backup) Designated Router '
                            + 'for the network.'
                              ;
                }
                enum Point-to-point {
                  value 5 ;
                  description 'In this state, the interface is operational, and'
                            + ' connects either to a physical point-to-point ne'
                            + 'twork or to a virtual link.'
                              ;
                }
                enum DROther {
                  value 6 ;
                  description 'The interface is to a broadcast or NBMA network '
                            + 'on which another router has been selected to be '
                            + 'the Designated Router.'
                              ;
                }
                enum Backup {
                  value 7 ;
                  description 'In this state, the router itself is the Backup D'
                            + 'esignated Router on the attached network.'
                              ;
                }
                enum DR {
                  value 8 ;
                  description 'In this state, this router itself is the Designa'
                            + 'ted Router on the attached network.'
                              ;
                }
              }
            }
            leaf priority {
              description 'Router priority.'
                          ;
              type uint32 {
                range 0..255 ;
              }
            }
            leaf ldp-sync-config {
              description 'MPLS LDP IGP sync.'
                          ;
              type enumeration {
                enum disable {
                  value 0 ;
                  description 'MPLS LDP IGP sync is disabled.'
                              ;
                }
                enum enable {
                  value 1 ;
                  description 'MPLS LDP IGP sync is enabled.'
                              ;
                }
              }
              ncd:revise-date 2015-12-08 ;
            }
            leaf ldp-sync-state {
              description 'MPLS LDP IGP sync of the interface.'
                          ;
              type enumeration {
                enum unachieve {
                  value 0 ;
                  description 'MPLS LDP IGP sync state is unachieved.'
                              ;
                }
                enum achieve {
                  value 1 ;
                  description 'MPLS LDP IGP sync state is achieved.'
                              ;
                }
                enum unknown {
                  value 2 ;
                  description 'MPLS LDP IGP sync state is unknown.'
                              ;
                }
              }
              ncd:revise-date 2015-12-08 ;
            }
            leaf ldp-link-state {
              description 'Router lsa link state caused by MPLS LDP IGP state.'
                          ;
              type enumeration {
                enum send-max-metric {
                  value 0 ;
                  description 'MPLS LDP IGP link state is sending max metric.'
                              ;
                }
                enum unreachable {
                  value 1 ;
                  description 'MPLS LDP IGP link state is unreachable.'
                              ;
                }
                enum send-normal-metric {
                  value 2 ;
                  description 'MPLS LDP IGP link state is sending normal metric.'
                              ;
                }
              }
              ncd:revise-date 2015-12-08 ;
            }
            leaf no-cut-edge {
              description 'There is alternate path for the directly connected n'
                        + 'etwork.'
                          ;
              type empty ;
              ncd:revise-date 2015-12-08 ;
            }
            leaf dr {
              description 'Designated Router ID.'
                          ;
              type ncd:ipv4-address ;
            }
            leaf dr-linklocal-address {
              description 'Link-local address of the DR.'
                          ;
              type ncd:ipv6-address ;
            }
            leaf bdr {
              description 'Backup designated Router ID.'
                          ;
              type ncd:ipv4-address ;
            }
            leaf bdr-linklocal-address {
              description 'Link-local address of the BDR.'
                          ;
              type ncd:ipv6-address ;
            }
            leaf hello-interval {
              description 'Time between hello packets.'
                          ;
              type uint32 {
                range 1..65535 ;
              }
              units second ;
            }
            leaf dead-interval {
              description 'Interval after which a neighbor is declared dead.'
                          ;
              type uint32 {
                range 1..65535 ;
              }
              units second ;
            }
            leaf wait-interval {
              description 'The Interval that interface exit waiting state.'
                          ;
              type uint32 {
                range 1..65535 ;
              }
              units second ;
            }
            leaf retransmit-interval {
              description 'Time between retransmitting lost link state advertis'
                        + 'ements.'
                          ;
              type uint32 {
                range 1..65535 ;
              }
              units second ;
              default 5 ;
            }
            leaf neighbor-count {
              description 'Count of neighbor.'
                          ;
              type uint32 ;
            }
            leaf full-neighbor-count {
              description 'Full neighbor count.'
                          ;
              type uint32 ;
            }
            leaf linklsa-suppress {
              description 'Link lsa suppress.'
                          ;
              type empty ;
            }
            leaf damp-state {
              description 'Link damp state of the interface.'
                          ;
              type enumeration {
                enum inactive {
                  value 0 ;
                  description 'Link Damp state of this interface is inactive.'
                              ;
                }
                enum active {
                  value 1 ;
                  description 'Link Damp state of this interface is active.'
                              ;
                }
              }
              ncd:revise-date 2017-03-31 ;
            }
            leaf damp-remain {
              description 'Link damp remaining time.'
                          ;
              type uint32 {
                range 0..3600000 {
                  description 'Link damp remaining time.'
                              ;
                }
              }
              ncd:revise-date 2017-03-31 ;
            }
            container ipsec {
              description 'IPSEC states of interface.'
                          ;
              leaf spi-id {
                description 'Security parameters index ID.'
                            ;
                type uint32 ;
              }
              leaf type {
                description 'Type of authentication or encryption.'
                            ;
                type enumeration {
                  enum authentication-null {
                    value 1 ;
                  }
                  enum encryption-null {
                    value 2 ;
                  }
                  enum authentication {
                    value 3 ;
                  }
                  enum encryption {
                    value 4 ;
                  }
                }
              }
              leaf authentication-algorithm {
                description 'Type of authentication algorithm.'
                            ;
                type enumeration {
                  enum md5 {
                    value 1 ;
                    description 'Message Digest Algorithm.'
                                ;
                  }
                  enum sha1 {
                    value 2 ;
                    description 'Secure Hash Algorithm.'
                                ;
                  }
                  enum keychain {
                    value 4 ;
                    description 'Use keychain for authentication.'
                                ;
                  }
                }
              }
              leaf encryption-algorithm {
                description 'Type of encryption algorithm.'
                            ;
                type enumeration {
                  enum null {
                    value 1 ;
                    description 'NULL encryption.'
                                ;
                  }
                  enum des {
                    value 2 ;
                    description 'Data Encrypt Standard algorithm.'
                                ;
                  }
                  enum triple-des {
                    value 3 ;
                    description 'Triple Data Encryption algorithm.'
                                ;
                  }
                  enum aes-cbc {
                    value 4 ;
                    description 'Advanced Encryption Standard algorithm.'
                                ;
                  }
                  enum keychain-encryption {
                    value 6 ;
                    description 'Use keychain for encryption.'
                                ;
                  }
                }
              }
              leaf state {
                description 'State of IPSEC.'
                            ;
                type enumeration {
                  enum down {
                    value 0 ;
                  }
                  enum start {
                    value 1 ;
                  }
                  enum rekeying-add-new-in {
                    value 2 ;
                  }
                  enum rekeying-add-new-out {
                    value 3 ;
                  }
                  enum rekeying-del-old-in {
                    value 4 ;
                  }
                  enum up {
                    value 5 ;
                  }
                }
              }
            }
            ncd:select interface-name ;
            ncd:select process-id ;
            ncd:select 'process-id interface-name'
                       ;
          }
        }
        container virtual-interfaces {
          description 'OSPFv3 virtual interface.'
                      ;
          list virtual-interface {
            description 'OSPFv3 virtual interface.'
                        ;
            key 'process-id area-id neighbor-id'
                ;
            leaf process-id {
              description 'OSPFv3 process ID.'
                          ;
              type uint32 {
                range 1..65535 ;
              }
            }
            leaf area-id {
              description 'OSPFv3 area ID in IP address format.'
                          ;
              type ncd:ipv4-address ;
            }
            leaf neighbor-id {
              description 'Router ID of the virtual link neighbor.'
                          ;
              type ncd:ipv4-address ;
            }
            leaf interface-id {
              description 'Virtual interface ID.'
                          ;
              type uint32 {
                range 2147483648..4294967294 ;
              }
            }
            leaf state {
              description 'State of the virtual link.'
                          ;
              type enumeration {
                enum down {
                  value 0 ;
                  description 'The virtual-link is down.'
                              ;
                }
                enum up {
                  value 1 ;
                  description 'The virtual-link is up.'
                              ;
                }
              }
            }
            leaf neighbor-ipv6-address {
              description 'IPv6 address of the virtual neighbor.'
                          ;
              type ncd:ipv6-address ;
            }
            leaf out-interface-name {
              description 'The outgoing interface name of virtual interface.'
                          ;
              type ncd:ifname {
                length 1..31 ;
              }
            }
            leaf cost {
              description 'Cost value of OSPFv3 virtual link interface.'
                          ;
              type uint32 {
                range 1..65535 ;
              }
            }
            leaf hello-interval {
              description 'Time between hello packets over virtual link.'
                          ;
              type uint32 {
                range 1..8192 ;
              }
              units second ;
              default 10 ;
            }
            leaf dead-interval {
              description 'Interval after which a virtual neighbor is declared '
                        + 'dead.'
                          ;
              type uint32 {
                range 1..8192 ;
              }
              units second ;
            }
            leaf wait-interval {
              description 'Interval after which a virtual interface to exit the'
                        + ' waiting state.'
                          ;
              type uint32 {
                range 1..8192 ;
              }
              units second ;
            }
            leaf retransmit-interval {
              description 'Time between retransmitting lost link state advertis'
                        + 'ements over virtual link.'
                          ;
              type uint32 {
                range 1..8192 ;
              }
              units second ;
              default 5 ;
            }
            leaf transmit-delay {
              description 'LSA transmit delay over virtual link.'
                          ;
              type uint32 {
                range 1..8192 ;
              }
              units second ;
              default 1 ;
            }
            leaf interface-state {
              description 'State of the virtual interface.'
                          ;
              type enumeration {
                enum Down {
                  value 1 ;
                  description 'This is the initial interface state.'
                              ;
                }
                enum Point-to-point {
                  value 5 ;
                  description 'In this state, the interface is operational, and'
                            + ' connects either to a physical point-to-point ne'
                            + 'twork or to a virtual link.'
                              ;
                }
              }
            }
            leaf neighbor-state {
              description 'State of the virtual neighbor.'
                          ;
              type enumeration {
                enum Down {
                  value 1 ;
                  description 'This is the initial state of a neighbor conversa'
                            + 'tion.'
                              ;
                }
                enum Init {
                  value 3 ;
                  description 'In this state, an Hello packet has recently been'
                            + ' seen from the neighbor.'
                              ;
                }
                enum 2-Way {
                  value 4 ;
                  description 'In this state, communication between the two rou'
                            + 'ters is bidirectional.'
                              ;
                }
                enum ExStart {
                  value 5 ;
                  description 'This is the first step in creating an adjacency '
                            + 'between the two neighboring routers.'
                              ;
                }
                enum Exchange {
                  value 6 ;
                  description 'In this state the router is describing its entir'
                            + 'e link state database by sending Database Descri'
                            + 'ption packets to the neighbor.'
                              ;
                }
                enum Loading {
                  value 7 ;
                  description 'In this state, Link State Request packets are se'
                            + 'nt to the neighbor asking for the more recent LS'
                            + 'As that have been discovered (but not yet receiv'
                            + 'ed) in the Exchange state.'
                              ;
                }
                enum Full {
                  value 8 ;
                  description 'In this state, the neighboring routers are fully'
                            + ' adjacent.'
                              ;
                }
              }
            }
            container ipsec {
              description 'IPSEC states of virtual link.'
                          ;
              leaf spi-id {
                description 'Security parameters index ID.'
                            ;
                type uint32 {
                  range 256..32767 ;
                }
              }
              leaf type {
                description 'Type of authentication or encryption.'
                            ;
                type enumeration {
                  enum authentication {
                    value 3 ;
                    description 'Authentication type.'
                                ;
                  }
                  enum encryption {
                    value 4 ;
                    description 'Encryption type.'
                                ;
                  }
                }
              }
              leaf authentication-algorithm {
                description 'Type of authentication algorithm.'
                            ;
                type enumeration {
                  enum md5 {
                    value 1 ;
                    description 'Message Digest Algorithm.'
                                ;
                  }
                  enum sha1 {
                    value 2 ;
                    description 'Secure Hash Algorithm.'
                                ;
                  }
                  enum keychain {
                    value 4 ;
                    description 'Use keychain for authentication.'
                                ;
                  }
                }
              }
              leaf encryption-algorithm {
                description 'Type of encryption algorithm.'
                            ;
                type enumeration {
                  enum null {
                    value 1 ;
                    description 'NULL encryption.'
                                ;
                  }
                  enum des {
                    value 2 ;
                    description 'Data Encrypt Standard algorithm.'
                                ;
                  }
                  enum triple-des {
                    value 3 ;
                    description 'Triple Data Encryption algorithm.'
                                ;
                  }
                  enum aes-cbc {
                    value 4 ;
                    description 'Advanced Encryption Standard algorithm.'
                                ;
                  }
                  enum keychain-encryption {
                    value 6 ;
                    description 'Use keychain for encryption.'
                                ;
                  }
                }
              }
              leaf state {
                description 'State of IPSEC.'
                            ;
                type enumeration {
                  enum down {
                    value 0 ;
                    description 'Down state.'
                                ;
                  }
                  enum start {
                    value 1 ;
                    description 'Start state.'
                                ;
                  }
                  enum rekeying-add-new-in {
                    value 2 ;
                    description 'Rekeying(add-new-in) state.'
                                ;
                  }
                  enum rekeying-add-new-out {
                    value 3 ;
                    description 'Rekeying(add-new-out) state.'
                                ;
                  }
                  enum rekeying-del-old-in {
                    value 4 ;
                    description 'Rekeying(del-old-in) state.'
                                ;
                  }
                  enum up {
                    value 5 ;
                    description 'Up state.'
                                ;
                  }
                }
              }
            }
            ncd:select process-id ;
          }
        }
      }
      container neighbors {
        description 'OSPFv3 neighbor.'
                    ;
        container normal-neighbors {
          description 'OSPFv3 normal neighbor.'
                      ;
          list normal-neighbor {
            description 'OSPFv3 normal neighbor.'
                        ;
            key 'process-id area-id interface-name neighbor-id'
                ;
            leaf process-id {
              description 'OSPFv3 process ID.'
                          ;
              type uint32 {
                range 1..65535 ;
              }
            }
            leaf area-id {
              description 'OSPFv3 area ID in IP address format.'
                          ;
              type ncd:ipv4-address ;
            }
            leaf interface-name {
              description 'The outgoing interface name of  interface.'
                          ;
              type ncd:ifname {
                length 1..31 ;
              }
            }
            leaf neighbor-id {
              description 'Router ID of the neighbor.'
                          ;
              type ncd:ipv4-address ;
            }
            leaf interface-id {
              description 'Interface ID.'
                          ;
              type uint32 ;
            }
            leaf neighbor-linklocal-address {
              description 'Link-local address of neighbor.'
                          ;
              type ncd:ipv6-address ;
            }
            leaf priority {
              description 'Neighbor router priority.'
                          ;
              type uint32 {
                range 0..255 ;
              }
            }
            leaf neighbor-state {
              description 'Neighbor router state.'
                          ;
              type enumeration {
                enum Init {
                  value 3 ;
                }
                enum 2-Way {
                  value 4 ;
                }
                enum Exstart {
                  value 5 ;
                }
                enum Exchange {
                  value 6 ;
                }
                enum Loading {
                  value 7 ;
                }
                enum Full {
                  value 8 ;
                }
              }
            }
            leaf neighbor-role {
              description 'State of the interface.'
                          ;
              type enumeration {
                enum DR {
                  value 1 ;
                }
                enum Backup {
                  value 2 ;
                }
                enum DROther {
                  value 3 ;
                }
              }
            }
            leaf state-change-times {
              description 'Neighbor router state change times.'
                          ;
              type uint32 ;
            }
            leaf dr {
              description 'Designated Router ID.'
                          ;
              type ncd:ipv4-address ;
            }
            leaf bdr {
              description 'Backup designated Router ID.'
                          ;
              type ncd:ipv4-address ;
            }
            leaf retransmit-list-count {
              description 'Database retransmit packet count.'
                          ;
              type uint32 ;
            }
            leaf dd-list-count {
              description 'DD packet count in list.'
                          ;
              type uint32 ;
            }
            leaf request-list-count {
              description 'Request packet count in list.'
                          ;
              type uint32 ;
            }
            leaf dead-time {
              description 'Dead Time.'
                          ;
              type string {
                length 1..15 ;
              }
            }
            leaf full-time {
              description 'Neighbor full time.'
                          ;
              type string {
                length 1..15 ;
              }
            }
            leaf options-field {
              description 'Options field of neighbor.'
                          ;
              type uint32 ;
            }
            container options {
              description 'Options of neighbor.'
                          ;
              leaf v6-bit {
                description 'If this bit is clear, the router/link should be ex'
                          + 'cluded from IPv6 routing calculations.'
                            ;
                type empty ;
              }
              leaf e-bit {
                description 'This bit describes the way AS-external-LSAs are fl'
                          + 'ooded.'
                            ;
                type empty ;
              }
              leaf n-bit {
                description 'This bit indicates whether or not the router is at'
                          + 'tached to an NSSA.'
                            ;
                type empty ;
              }
              leaf r-bit {
                description "This bit (the `Router' bit) indicates whether the "
                          + "originator is an active router."
                            ;
                type empty ;
              }
              leaf dc-bit {
                description "This bit describes the router's handling of demand"
                          + " circuits."
                            ;
                type empty ;
              }
            }
            ncd:select neighbor-id ;
            ncd:select 'process-id neighbor-id'
                       ;
            ncd:select process-id ;
            ncd:select interface-name ;
            ncd:select 'interface-name neighbor-id'
                       ;
            ncd:select 'process-id interface-name'
                       ;
            ncd:select 'process-id interface-name neighbor-id'
                       ;
          }
        }
        container virtual-neighbors {
          description 'OSPFv3 virtual neighbor.'
                      ;
          list virtual-neighbor {
            description 'OSPFv3 virtual neighbor.'
                        ;
            key 'process-id transit-area-id neighbor-id'
                ;
            leaf process-id {
              description 'OSPFv3 process ID.'
                          ;
              type uint32 {
                range 1..65535 ;
              }
            }
            leaf transit-area-id {
              description 'OSPFv3 virtual link transit area ID in IP address fo'
                        + 'rmat.'
                          ;
              type ncd:ipv4-address ;
            }
            leaf neighbor-id {
              description 'Router ID of the neighbor.'
                          ;
              type ncd:ipv4-address ;
            }
            leaf area-id {
              description 'OSPFv3 area ID in IP address format.'
                          ;
              type ncd:ipv4-address ;
            }
            leaf out-interface-name {
              description 'The outgoing interface name of virtual interface.'
                          ;
              type ncd:ifname {
                length 1..31 ;
              }
            }
            leaf interface-id {
              description 'Interface ID.'
                          ;
              type uint32 ;
            }
            leaf neighbor-ipv6-address {
              description 'IPv6 address of the virtual neighbor.'
                          ;
              type ncd:ipv6-address ;
            }
            leaf priority {
              description 'Neighbor router priority.'
                          ;
              type uint32 {
                range 0..255 ;
              }
            }
            leaf neighbor-state {
              description 'Neighbor router state.'
                          ;
              type enumeration {
                enum Down {
                  value 1 ;
                }
                enum Init {
                  value 3 ;
                }
                enum 2-Way {
                  value 4 ;
                }
                enum Exstart {
                  value 5 ;
                }
                enum Exchange {
                  value 6 ;
                }
                enum Loading {
                  value 7 ;
                }
                enum Full {
                  value 8 ;
                }
              }
            }
            leaf state-change-times {
              description 'Neighbor router state change times.'
                          ;
              type uint32 ;
            }
            leaf retransmit-list-count {
              description 'Database retransmit packet count.'
                          ;
              type uint32 ;
            }
            leaf dd-list-count {
              description 'DD packet count in list.'
                          ;
              type uint32 ;
            }
            leaf request-list-count {
              description 'Request packet count in list.'
                          ;
              type uint32 ;
            }
            leaf dead-time {
              description 'Dead Time.'
                          ;
              type string {
                length 1..15 ;
              }
            }
            leaf full-time {
              description 'Neighbor full time.'
                          ;
              type string {
                length 1..15 ;
              }
            }
            leaf options-field {
              description 'Options field of neighbor.'
                          ;
              type uint32 ;
            }
            container options {
              description 'Options of neighbor.'
                          ;
              leaf v6-bit {
                description 'If this bit is clear, the router/link should be ex'
                          + 'cluded from IPv6 routing calculations.'
                            ;
                type empty ;
              }
              leaf e-bit {
                description 'This bit describes the way AS-external-LSAs are fl'
                          + 'ooded.'
                            ;
                type empty ;
              }
              leaf n-bit {
                description 'This bit indicates whether or not the router is at'
                          + 'tached to an NSSA.'
                            ;
                type empty ;
              }
              leaf r-bit {
                description "This bit (the `Router' bit) indicates whether the "
                          + "originator is an active router."
                            ;
                type empty ;
              }
              leaf dc-bit {
                description "This bit describes the router's handling of demand"
                          + " circuits."
                            ;
                type empty ;
              }
            }
          }
        }
      }
    }
    ncd:revise-date 2015-03-26 ;
  }
  container operation {
    config false ;
    description 'Operation model.'
                ;
    container ospfv3 {
      description 'Operation of OSPFv3.'
                  ;
      container clear {
        description 'Clear Operation.'
                    ;
        container process {
          description 'Clear an OSPFv3 process based on the process-id.'
                      ;
          leaf process-id {
            description 'OSPFv3 process ID.'
                        ;
            type uint32 {
              range 1..65535 ;
            }
          }
        }
      }
    }
    ncd:revise-date 2015-03-26 ;
  }
}
