module zxr10-aps {
  namespace 'http://www.zte.com.cn/zxr10/netconf/schema/rosng/aps'
            ;
  prefix aps ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf model to describe aps.'
              ;
  revision 2020-08-19 {
    description '1.Add the container of configuration/aps/port-group-flexe-subs'
              + ''+"\n"
              + '2.Add the container of state/aps/port-group-flexe-subs'
                ;
  }
  revision 2020-07-08 {
    description 'Add the leaf of configuration/aps/erps-groups/erps-group/versi'
              + 'on.'+"\n"
              + 'Add the leaf of configuration/aps/erps-vlan-groups/erps-vlan-g'
              + 'roup/version.'
                ;
  }
  revision 2020-06-15 {
    description 'Add the container of configuration/aps/erps-vlan-groups.'+"\n"
              + 'Add the container of configuration/aps/erps-groups/erps-group/'
              + 'ring-cfg.'+"\n"
              + 'Obsolete the leaf of configuration/aps/erps-groups/erps-group/'
              + 'ring-id.'
                ;
  }
  revision 2019-10-13 {
    description 'modify the leaf of configuration/aps/pw-groups/pw-group/wtr-ti'
              + 'me max value'
                ;
  }
  revision 2019-06-21 {
    description '1.Obsolete the leaf of configuration/aps/port-groups/extra-eth'
              + 'ernet/send-packet-mode'+"\n"
              + '2.Obsolete the leaf of configuration/aps/port-groups/extra-eth'
              + 'ernet/bridge-type'+"\n"
              + '3.Obsolete the leaf of configuration/aps/port-groups/extra-eth'
              + 'ernet/mel'+"\n"
              + '4.Obsolete the leaf of configuration/aps/port-groups/extra-eth'
              + 'ernet/sd-preferred'+"\n"
              + '5.Add the container of configuration/aps/port-group-multicasts'
              + ''+"\n"
              + '6.Add the container of configuration/aps/port-group-otns'+"\n"
              + '7.Add the container of configuration/aps/port-group-ether-serv'
              + 'ices'+"\n"
              + '8.Add the container of configuration/aps/port-group-flexes'+"\n"
              + '9.Add the container of state/aps/port-group-multicasts'+"\n"
              + '10.Add the container of state/aps/port-group-otns'+"\n"
              + '11.Add the container of state/aps/port-group-ether-services'+"\n"
              + '12.Add the container of state/aps/port-group-flexes'
                ;
  }
  revision 2018-01-25 {
    description '1.Add description of leaf of configuration/aps/section-groups/'
              + 'section-group/base-id'+"\n"
              + '2.Add description of leaf of configuration/aps/section-groups/'
              + 'section-group/east-id'+"\n"
              + '3.Add description of leaf of configuration/aps/section-groups/'
              + 'section-group/west-id'+"\n"
              + '4.Add description of leaf of configuration/aps/section-groups/'
              + 'section-group/east-switch'+"\n"
              + '5.Add description of leaf of configuration/aps/section-groups/'
              + 'section-group/west-switch'+"\n"
              + '6.Add description of leaf of configuration/aps/section-groups/'
              + 'section-group/ring-map'+"\n"
              + '7.Add description of leaf of configuration/aps/erps-groups/erp'
              + 's-group/ring-id'+"\n"
              + '8.Add description of leaf of configuration/aps/erps-groups/erp'
              + 's-group/east-switch'+"\n"
              + '9.Add description of leaf of configuration/aps/erps-groups/erp'
              + 's-group/west-switch'
                ;
  }
  revision 2018-01-02 {
    description '1.Add the leaf of configuration/aps/tunnel-groups/tunnel-group'
              + '/hold-off-precise'+"\n"
              + '2.Add the leaf of configuration/aps/port-groups/port-group/hol'
              + 'd-off-precise'+"\n"
              + '3.Add the leaf of configuration/aps/pw-groups/pw-group/hold-of'
              + 'f-precise'+"\n"
              + '4.Add the leaf of configuration/aps/section-groups/section-gro'
              + 'up/hold-off-precise'+"\n"
              + '5.Add the leaf of configuration/aps/ac-groups/ac-group/hold-of'
              + 'f-precise'+"\n"
              + '6.Add the leaf of configuration/aps/mtunnel-groups/mtunnel-gro'
              + 'up/hold-off-precise'+"\n"
              + '7.Add the leaf of configuration/aps/erps-groups/erps-group/hol'
              + 'd-off-precise'
                ;
  }
  revision 2017-05-12 {
    description '1 Add description of leaf "state/aps/port-groups/port-group/pr'
              + 'otect-status"'+"\n"
              + '2 Modify native description of leaf "state/aps/port-groups/por'
              + 't-group/protect-status"'+"\n"
              + '3 Add 28 and 29 for leaf "state/aps/port-groups/port-group/pro'
              + 'tect-status"'
                ;
  }
  revision 2017-04-22 {
    description '1.Add the leaf of configuration/aps/sd-preferred'+"\n"
              + '2.Add the leaf of configuration/aps/tunnel-groups/tunnel-group'
              + '/sd-preferred'+"\n"
              + '3.Add the leaf of configuration/aps/pw-groups/pw-group/sd-pref'
              + 'erred'+"\n"
              + '4.Add the leaf of configuration/aps/ac-groups/ac-group/sd-pref'
              + 'erred'+"\n"
              + '5.Add the leaf of configuration/aps/mtunnel-groups/mtunnel-gro'
              + 'up/sd-preferred'+"\n"
              + '6.Add the leaf of configuration/aps/port-groups/extra-ethernet'
              + '/sd-preferred'
                ;
  }
  revision 2017-01-11 {
    description '1.Add a new list extra-ethernet in configuration/aps/port-grou'
              + 'ps which contains leafs send-packet-mode, bridge-type, mel, wh'
              + 'ich are the extra parameters of ethernet port-group parameters'
              + '.'
                ;
  }
  revision 2016-11-08 {
    description '1.Add enum ms-w for switch-cmd-linear.'+"\n"
              + '2.Modify the description of configuration/aps/tunnel-groups/tu'
              + 'nnel-group/switch-cmd,'+"\n"
              + 'configuration/aps/pw-groups/pw-group/switch-cmd,'+"\n"
              + 'configuration/aps/ac-groups/ac-group/switch-cmd,'+"\n"
              + 'configuration/aps/mtunnel-groups/mtunnel-group/switch-cmd.'+"\n"
              + '3.Add the type of bridge-type.'+"\n"
              + '4.Add the leaf of configuration/aps/tunnel-groups/tunnel-group'
              + '/bridge-type,'+"\n"
              + 'configuration/aps/pw-groups/pw-group/bridge-type,'+"\n"
              + 'configuration/aps/ac-groups/ac-group/bridge-type,'+"\n"
              + 'configuration/aps/mtunnel-groups/mtunnel-group/bridge-type.'
                ;
  }
  revision 2016-07-22 {
    description "Expand the maxmum value of '/state/aps/tunnel-groups/tunnel-gr"
              + "oup/pg-index' from performance ID 67305513 to 4294967295."
                ;
  }
  revision 2016-04-26 {
    description 'In accordance with ITU G.8032, modify the configuration range '
              + 'of leaf "configuration/aps/erps-groups/erps-group/wtr-time" as'
              + ' [1,12].'
                ;
  }
  revision 2016-03-03 {
    description 'Modify the enumeration type name of leaf "state/aps/erps-group'
              + 's/erps-group/protect-status".'
                ;
  }
  revision 2016-02-24 {
    description 'Add default value of leaf "configuration/aps/erps-groups/erps-'
              + 'group/node-id" as "ffff.ffff.ffff".'
                ;
  }
  revision 2015-12-24 {
    description 'Add two containers: erps-groups in configuration/aps and erps-'
              + 'groups in state/aps.'
                ;
  }
  revision 2015-10-26 {
    description 'Modify the unit from min to minute for all wtr-time leaf.'
                ;
  }
  revision 2015-07-01 {
    description 'Add two containers: configuration/aps/mtunnel-groups/mtunnel-g'
              + 'roup and state/aps/mtunnel-groups'
                ;
  }
  revision 2014-11-24 {
    description '1)modify state/section-groups/section-group/object-index type '
              + 'from uint16 to uint32.'+"\n"
              + '2)modify state/tunnel-groups/tunnel-group/pg-index type from u'
              + 'int16 to uint32.'+"\n"
              + '3)modify state/port-groups/port-group/pg-index type from uint1'
              + '6 to uint32.'+"\n"
              + '4)modify state/lsp-groups/lsp-group/pg-index type from uint16 '
              + 'to uint32.'+"\n"
              + '5)modify description aps to APS, pw to PW ,ac to AC.'
                ;
  }
  revision 2014-09-02 {
    description 'Add new list ac-groups in path of zxr10-aps/state/aps.'
                ;
  }
  revision 2014-07-10 {
    description '1)Modify configuration group id of port-group range from [1, 2'
              + '56] to[1,65536],and the max number depends on perf-code(673055'
              + '24).'+"\n"
              + '2)Modify state pg-index of port-group range from [1, 256] to[1'
              + ',65536],and the max number depends on perf-code(67305524).'
                ;
  }
  revision 2014-04-23 {
    description "Modify the second item's name of enumeration revertive-mode fr"
              + "om no-revertive to non-revertive."
                ;
  }
  revision 2014-03-10 {
    description '1 Modify description of leaf is-active in ac-group in configur'
              + 'ation from  Active flag of pw group aps to Active flag of ac g'
              + 'roup aps.'+"\n"
              + '2 Delete list ring-maps, add container ring-map.'+"\n"
              + '3 Modify MimDataType of leaf group-id of section-group in conf'
              + 'iguration from int32 to unit32.'
                ;
  }
  revision 2014-02-11 {
    description "1) Add Perf-code for leaf group-id of tunnel-group in configur"
              + "ation and state.
\n2) Add Perf-code for leaf group-id of secti"
              + "on-group in configuration and state.
\n3) Add if-filter-id for"
              + " leafgroup-name of pw-group in configuration.
\n4) Add if-filt"
              + "er-id for leaf pg-name of pw-group in state.
\n5) Add if-filte"
              + "r-id forleaf pg-name of mc-selection-group in state.
\n6) Modi"
              + "fy group-id range from 1-2565 to 1-256 of port-group in config"
              + "uration.
\n7) Add range for leaf pg-index of all group in stat"
              + "e.
\n8) Add anew ac-groups configuration container.Its leaf no"
              + "de is the sameas pw-groups configuration's.
\n9) Add value map"
              + " for leaf node wtr-time of pw-groups configuration container.
"
              + "\n10) Modify description of leaf node active-state of port-gro"
              + "ups configuration container.
\n11) Modify description of leaf "
              + "node active-state of pw-groups configuration container.
\n12) "
              + "Modify description of leaf node active-state of section-groups"
              + " configuration container.\n13) Modify description of leaf node"
              + " hold-off-time of port-groups configuration container.
\n14) M"
              + "odify description of leaf node wtr-time of port-groups configu"
              + "ration container.
\n15) Modifyrange of leaf node of ring-maps "
              + "in section-group configration from 0-127 to 1-127
\n16) Delete"
              + " select key of state container oflist tunnel-group,por-group,p"
              + "w-group,lsp-group,mc-selection-group.
\n17)Modify the module p"
              + "refix from APS to aps.
\n18) Add range for leaf object-index o"
              + "f list section-group in state container."
                ;
  }
  revision 2013-12-10 {
    description '1)Modify send-packet-mode of pw group attribute id from 15 to '
              + '5.'+"\n"
              + '2)Add default value active-or-restore for leaf active-state of'
              + ' all list.'+"\n"
              + '3)Add default value send for leaf send-packet-mode of all list'
              + '.'+"\n"
              + '4)Add default value revertive for leaf revertive-mode of all l'
              + 'ist.'+"\n"
              + '5)Add default value null for leaf switch-cmd of all list.'+"\n"
              + '6)Add default value active for leaf is-active of all list.'+"\n"
              + '7)Add default value null for Leaf east-switch and leaf west-sw'
              + 'itch.'
                ;
  }
  revision 2013-11-15 {
    description 'Add default value 0 for leaf base-id, east-id and west-id.'
                ;
  }
  revision 2013-10-16 {
    description '1.Add enum null for switch-cmd-linear,switch-cmd-msp,switch-cm'
              + 'd-ring.'+"\n"
              + '2.Remove leaf section-group-id and leaf cycle-index for list r'
              + 'ing-map.'+"\n"
              + '3.Modify leaf map range from 0-64 to 0-127 for list ring-map. '
              + ''+"\n"
              + '4.Delete list linear-aps,list ring-aps for state ; add list tu'
              + 'nnel-group,list section-group,list pw-group,list port-group,li'
              + 'st lsp-group,list mc-selection-group, delete typedef protect-g'
              + 'roup-state.'+"\n"
              + '5.Delete mandatory true for key node. '+"\n"
              + '6.Modify range from 1-64 to 0-127 leaf base-id, east-id,west-i'
              + 'd. '+"\n"
              + '7.Add container for list.'
                ;
  }
  revision 2013-07-18 {
    description 'Initial version.'
                ;
  }
  typedef active-state {
    type enumeration {
      enum active-or-restore {
        value 0 ;
        description 'APS active state is active or restore.'
                    ;
      }
      enum pause {
        value 1 ;
        description 'APS active state is pause.'
                    ;
      }
    }
    default active-or-restore ;
    description 'Active state of APS.'
                ;
  }
  typedef send-packet-mode {
    type enumeration {
      enum send {
        value 0 ;
        description 'APS send pakcet mode is send.'
                    ;
      }
      enum no-send {
        value 1 ;
        description 'APS send pakcet mode is no send.'
                    ;
      }
    }
    default send ;
    description 'Send packet mode of APS.'
                ;
  }
  typedef revertive-mode {
    type enumeration {
      enum revertive {
        value 0 ;
        description 'APS revertive mode is revertive.'
                    ;
      }
      enum non-revertive {
        value 1 ;
        description 'APS revertive mode is no revertive.'
                    ;
      }
    }
    default revertive ;
    description 'Revertive mode of APS.'
                ;
  }
  typedef is-active {
    type enumeration {
      enum restore {
        value 0 ;
        description 'APS active state is restore.'
                    ;
      }
      enum active {
        value 1 ;
        description 'APS active state is active.'
                    ;
      }
    }
    default active ;
    description 'Active state of APS.'
                ;
  }
  typedef switch-cmd-linear {
    type enumeration {
      enum null {
        value 0 ;
        description 'Linear APS switch command is null.'
                    ;
      }
      enum clear {
        value 1 ;
        description 'Linear APS switch command is clear.'
                    ;
      }
      enum lock-out {
        value 2 ;
        description 'Linear APS switch command is force switch of protect.'
                    ;
      }
      enum fs-p {
        value 3 ;
        description 'Linear APS switch command is force switch of protect.'
                    ;
      }
      enum ms-p {
        value 4 ;
        description 'Linear APS switch command is manual switch of protect.'
                    ;
      }
      enum exercise {
        value 5 ;
        description 'Linear APS switch command is exercise.'
                    ;
      }
      enum ms-w {
        value 7 ;
        description 'Linear APS switch command is manual switch of work.'
                    ;
      }
    }
    default null ;
    description 'Switch command of linear APS.'
                ;
  }
  typedef switch-cmd-msp {
    type enumeration {
      enum null {
        value 0 ;
        description 'Switch command of msp APS is null.'
                    ;
      }
      enum clear {
        value 1 ;
        description 'Switch command of msp APS is clear.'
                    ;
      }
      enum lock-out {
        value 2 ;
        description 'Switch command of msp APS is lock out.'
                    ;
      }
      enum fs-p {
        value 3 ;
        description 'Switch command of msp APS is force switch of protect.'
                    ;
      }
      enum ms-p {
        value 4 ;
        description 'Switch command of msp APS is manual switch of protect.'
                    ;
      }
      enum exercise {
        value 5 ;
        description 'Switch command of msp APS is exercise.'
                    ;
      }
      enum fs-w {
        value 6 ;
        description 'Switch command of msp APS is force switch of work.'
                    ;
      }
      enum ms-w {
        value 7 ;
        description 'Switch command of msp APS is manual switch of work.'
                    ;
      }
    }
    default null ;
    description 'Switch command of msp APS.'
                ;
  }
  typedef switch-cmd-ring {
    type enumeration {
      enum null {
        value 0 ;
        description 'Switch command of ring APS is null.'
                    ;
      }
      enum clear {
        value 1 ;
        description 'Switch command of ring APS is clear.'
                    ;
      }
      enum lock-out {
        value 2 ;
        description 'Switch command of ring APS is lock out of protect.'
                    ;
      }
      enum low {
        value 3 ;
        description 'Switch command of ring APS is lock out of work.'
                    ;
      }
      enum force-switch {
        value 4 ;
        description 'Switch command of ring APS is force switch.'
                    ;
      }
      enum manual-switch {
        value 5 ;
        description 'Switch command of ring APS is manual switch.'
                    ;
      }
      enum exercise {
        value 6 ;
        description 'Switch command of ring APS is exercise.'
                    ;
      }
    }
    default null ;
    description 'Switch command of ring APS.'
                ;
  }
  typedef ring-aps-direction {
    type enumeration {
      enum east {
        value 1 ;
        description 'East direction of ring APS.'
                    ;
      }
      enum west {
        value 2 ;
        description 'West direction of ring APS.'
                    ;
      }
    }
    description 'Ring APS direction of APS.'
                ;
  }
  typedef group-type-erps {
    type enumeration {
      enum l2vpn-erps {
        value 2 ;
        description 'ERPS type of L2VPN.'
                    ;
      }
      enum vlan-erps {
        value 3 ;
        description 'ERPS type of VLAN'
                    ;
      }
    }
    description 'The group type of ERPS APS.'
                ;
  }
  typedef switch-cmd-erps {
    type enumeration {
      enum null {
        value 0 ;
        description 'Switch command of erps APS is null.'
                    ;
      }
      enum clear {
        value 1 ;
        description 'Switch command of erps APS is clear.'
                    ;
      }
      enum fs {
        value 4 ;
        description 'Switch command of erps APS is force-switch.'
                    ;
      }
      enum ms {
        value 5 ;
        description 'Switch command of erps APS is manual-switch.'
                    ;
      }
    }
    description 'Switch command of ERPS APS.'
                ;
  }
  typedef bridge-type {
    type enumeration {
      enum selector {
        value 0 ;
        description 'The type of bridge is selector bridge.'
                    ;
      }
      enum broadcast {
        value 1 ;
        description 'The type of bridge is broadcast bridge.'
                    ;
      }
    }
    default selector ;
    description 'Bridge type of APS.'
                ;
  }
  typedef sd-preferred {
    type enumeration {
      enum invalid {
        value 0 ;
      }
      enum enabled {
        value 1 ;
      }
      enum disabled {
        value 2 ;
      }
    }
    default invalid ;
    description 'SD preferred of APS.'
                ;
  }
  container configuration {
    description 'Configuration model info.'
                ;
    container aps {
      description 'Configure APS parameters.'
                  ;
      container tunnel-groups {
        description 'Configure tunnel group APS parameters.'
                    ;
        list tunnel-group {
          description 'Configure tunnel group APS parameters.'
                      ;
          key group-id ;
          leaf group-id {
            description 'Group ID of tunnel group APS.'
                        ;
            type uint32 {
              range 1..32768 {
                description 'Group ID.'
                            ;
              }
            }
          }
          leaf active-state {
            description 'Active state of tunnel group APS.'
                        ;
            type active-state ;
            default active-or-restore ;
          }
          leaf send-packet-mode {
            description 'Send packet mode of tunnel group APS.'
                        ;
            type send-packet-mode ;
            default send ;
          }
          leaf hold-off-time {
            description 'Hold-off timer for tunnel group APS(100ms).'
                        ;
            type uint8 {
              range 0..100 {
                description 'hold off time(100ms)'
                            ;
              }
            }
            units 100ms ;
            default 0 ;
          }
          leaf hold-off-precise {
            description 'Hold-off precise timer for tunnel group APS(10ms).'
                        ;
            type uint8 {
              range 1..9 {
                description 'hold off precise time(10ms)'
                            ;
              }
            }
            units 10ms ;
            ncd:revise-date 2018-01-02 ;
          }
          leaf revertive-mode {
            description 'Revertive mode of tunnel group APS.'
                        ;
            type revertive-mode ;
            default revertive ;
          }
          leaf wtr-time {
            description 'Wait-to-restore timer for tunnel group APS(minute).'
                        ;
            type uint8 {
              range 0..12 {
                description 'Wait to restore time(minute).'
                            ;
              }
            }
            units minute ;
            default 5 ;
          }
          leaf switch-cmd {
            description 'Switch command of tunnel group APS.'
                        ;
            type switch-cmd-linear ;
            default null ;
          }
          leaf is-active {
            description 'Active flag of tunnel group APS.'
                        ;
            type is-active ;
            default active ;
          }
          leaf bridge-type {
            description 'Bridge type of tunnel group APS.'
                        ;
            type bridge-type ;
            default selector ;
            ncd:revise-date 2016-11-08 ;
          }
          leaf sd-preferred {
            description 'SD preferred of tunnel group APS.'
                        ;
            type sd-preferred ;
            default invalid ;
            ncd:revise-date 2017-04-22 ;
          }
        }
      }
      container port-groups {
        description 'Configure port group APS parameters.'
                    ;
        list port-group {
          description 'Configure port group APS parameters.'
                      ;
          key group-id ;
          leaf group-id {
            description 'Group ID of port group APS.'
                        ;
            type uint32 {
              range 1..65535 {
                description 'Group ID.'
                            ;
              }
            }
          }
          leaf active-state {
            description 'Active state of port group APS.'
                        ;
            type active-state ;
            default active-or-restore ;
          }
          leaf hold-off-time {
            description 'Hold-off timer for port group APS(100ms).'
                        ;
            type uint8 {
              range 0..100 {
                description 'Hold off time(100ms).'
                            ;
              }
            }
            units 100ms ;
            default 0 ;
          }
          leaf hold-off-precise {
            description 'Hold-off precise timer for port group APS(10ms).'
                        ;
            type uint8 {
              range 1..9 {
                description 'hold off precise time(10ms)'
                            ;
              }
            }
            units 10ms ;
            ncd:revise-date 2018-01-02 ;
          }
          leaf revertive-mode {
            description 'Revertive mode of port group APS.'
                        ;
            type revertive-mode ;
            default revertive ;
          }
          leaf wtr-time {
            description 'Wait-to-restore timer for port group APS(minute).'
                        ;
            type uint8 {
              range 0..12 {
                description 'Wait to restore time(minute).'
                            ;
              }
            }
            units minute ;
            default 5 ;
          }
          leaf swtich-cmd {
            description 'Switch command of port group APS.'
                        ;
            type switch-cmd-msp ;
            default null ;
          }
          leaf is-active {
            description 'Active flag of port group aps.'
                        ;
            type is-active ;
            default active ;
          }
        }
        list extra-ethernet {
          status obsolete {
            ncd:revise-date 2019-06-21 ;
          }
          description 'Configure the extra parameters of ether port group APS.'
                      ;
          key group-id ;
          leaf group-id {
            status obsolete {
              ncd:revise-date 2019-06-21 ;
            }
            description 'Group ID of ether port group APS.'
                        ;
            type uint32 {
              range 6145..65535 {
                description 'Group ID.'
                            ;
              }
            }
          }
          leaf send-packet-mode {
            status obsolete {
              ncd:revise-date 2019-06-21 ;
            }
            description 'Send packet mode of ether port group APS.'
                        ;
            type send-packet-mode ;
            default send ;
          }
          leaf bridge-type {
            status obsolete {
              ncd:revise-date 2019-06-21 ;
            }
            description 'Bridge type of ether port group APS.'
                        ;
            type bridge-type ;
            default selector ;
          }
          leaf mel {
            status obsolete {
              ncd:revise-date 2019-06-21 ;
            }
            description 'MEG level of ether port group APS.'
                        ;
            type uint8 {
              range 0..7 {
                description 'MEG level.'
                            ;
              }
            }
            default 7 ;
          }
          leaf sd-preferred {
            status obsolete {
              ncd:revise-date 2019-06-21 ;
            }
            description 'SD preferred of ether port group APS.'
                        ;
            type sd-preferred ;
            default invalid ;
            ncd:revise-date 2017-04-22 ;
          }
          ncd:revise-date 2017-01-11 ;
        }
      }
      container pw-groups {
        description 'Configure PW group APS parameters.'
                    ;
        list pw-group {
          description 'Configure PW group APS parameters.'
                      ;
          key group-name ;
          leaf group-name {
            description "Group name of PW group's APS."
                        ;
            type ncd:ifname ;
          }
          leaf active-state {
            description "Active state of PW group's APS."
                        ;
            type active-state ;
            default active-or-restore ;
          }
          leaf is-active {
            description "Active flag of PW group's APS."
                        ;
            type is-active ;
            default active ;
          }
          leaf hold-off-time {
            description 'Hold-off timer for PW group APS(100ms).'
                        ;
            type uint8 {
              range 0..100 {
                description 'Hold off time(100ms).'
                            ;
              }
            }
            units 100ms ;
            default 0 ;
          }
          leaf hold-off-precise {
            description 'Hold-off precise timer for PW group APS(10ms).'
                        ;
            type uint8 {
              range 1..9 {
                description 'hold off precise time(10ms)'
                            ;
              }
            }
            units 10ms ;
            ncd:revise-date 2018-01-02 ;
          }
          leaf revertive-mode {
            description 'Revertive mode of PW group APS.'
                        ;
            type revertive-mode ;
            default revertive ;
          }
          leaf wtr-time {
            description 'Wait-to-restore timer for PW group APS(minute).'
                        ;
            type uint8 {
              range 0..20 {
                description 'Wait to restore time(minute).'
                            ;
              }
            }
            units minute ;
            default 5 ;
          }
          leaf switch-cmd {
            description 'Switch command of PW group APS.'
                        ;
            type switch-cmd-linear ;
            default null ;
          }
          leaf send-packet-mode {
            description 'Send packet mode of PW group APS.'
                        ;
            type send-packet-mode ;
            default send ;
          }
          leaf bridge-type {
            description 'Bridge type of PW group APS.'
                        ;
            type bridge-type ;
            default selector ;
            ncd:revise-date 2016-11-08 ;
          }
          leaf sd-preferred {
            description 'SD preferred of PW group APS.'
                        ;
            type sd-preferred ;
            default invalid ;
            ncd:revise-date 2017-04-22 ;
          }
        }
      }
      container section-groups {
        description 'Configure section group aps parameters.'
                    ;
        list section-group {
          description 'Configure section group APS parameters.'
                      ;
          key group-id ;
          leaf group-id {
            description 'Group ID of section group APS.'
                        ;
            type uint32 {
              range 1..64 {
                description 'Group ID.'
                            ;
              }
            }
          }
          leaf base-id {
            description "Base APS ID of section group APS.
\n1) Base-id cann't "
                      + "be equal to east-id;
\n2) Base-id cann't be equal to w"
                      + "est-id;"
                        ;
            type uint8 {
              range 0..127 {
                description 'Base APS ID.'
                            ;
              }
            }
            default 0 ;
          }
          leaf east-id {
            description "East APS ID of section group APS.East-id cann't be equ"
                      + "al tobase-id."
                        ;
            type uint8 {
              range 0..127 {
                description 'East APS ID.'
                            ;
              }
            }
            default 0 ;
          }
          leaf west-id {
            description "West APS ID of section group APS.West-id cann't be equ"
                      + "al tobase-id."
                        ;
            type uint8 {
              range 0..127 {
                description 'West APS ID.'
                            ;
              }
            }
            default 0 ;
          }
          leaf hold-off-time {
            description 'Hold-off timer for section group APS(100ms).'
                        ;
            type uint8 {
              range 0..100 {
                description 'Hold off time(100ms).'
                            ;
              }
            }
            units 100ms ;
            default 0 ;
          }
          leaf hold-off-precise {
            description 'Hold-off precise timer for section group APS(10ms).'
                        ;
            type uint8 {
              range 1..9 {
                description 'hold off precise time(10ms)'
                            ;
              }
            }
            units 10ms ;
            ncd:revise-date 2018-01-02 ;
          }
          leaf wtr-time {
            description 'Wait-to-restore timer for section group APS(minute).'
                        ;
            type uint8 {
              range 0..12 {
                description 'Wait to restore time(minute).'
                            ;
              }
            }
            units minute ;
            default 5 ;
          }
          leaf active-state {
            description 'Active state section group APS.'
                        ;
            type active-state ;
            default active-or-restore ;
          }
          leaf east-switch {
            description 'East switch command of section group APS. The east swi'
                      + 'tching command is mutually exclusive to the west switc'
                      + 'hing command'
                        ;
            type switch-cmd-ring ;
            default null ;
          }
          leaf west-switch {
            description 'West switch command of section group APS.The west swit'
                      + 'ching command is mutually exclusive to the east switch'
                      + 'ing command.'
                        ;
            type switch-cmd-ring ;
            default null ;
          }
          leaf is-active {
            description 'Active flag of section group APS.'
                        ;
            type is-active ;
            default active ;
          }
          container ring-map {
            description "Aps ring map  of section group APS.
\n1 The first memb"
                      + "er ofring map should be equal to the APS ID.
\n2 The m"
                      + "iddle member of ring map shouldn't be equal.
\n3 The s"
                      + "econd member of APS ring map should be equal to the ea"
                      + "st APS ID or the west APS ID.
\n4 The maximum number o"
                      + "f APS ring map is 64.
\n5 The last member of APS ring "
                      + "map should be equal to the east APS ID or the west APS"
                      + " ID."
                        ;
            leaf node1 {
              description 'No.1 node id in the ring-map.'
                          ;
              type uint8 {
                range 1..127 {
                  description 'Aps node id'
                              ;
                }
              }
            }
            leaf node2 {
              description 'No.2 node id in the ring-map.'
                          ;
              type uint8 {
                range 1..127 {
                  description 'Aps node id'
                              ;
                }
              }
            }
            leaf node3 {
              description 'No.3 aps node id in the ring-map.'
                          ;
              type uint8 {
                range 1..127 {
                  description 'APS node id'
                              ;
                }
              }
            }
            leaf node4 {
              description 'No.4 node id in the ring-map.'
                          ;
              type uint8 {
                range 1..127 {
                  description 'Aps node id'
                              ;
                }
              }
            }
            leaf node5 {
              description 'No.5 node id in the ring-map.'
                          ;
              type uint8 {
                range 1..127 {
                  description 'Aps node id'
                              ;
                }
              }
            }
            leaf node6 {
              description 'No.6 aps node id in the ring-map.'
                          ;
              type uint8 {
                range 1..127 {
                  description 'APS node id'
                              ;
                }
              }
            }
            leaf node7 {
              description 'No.7 node id in the ring-map.'
                          ;
              type uint8 {
                range 1..127 {
                  description 'Aps node id'
                              ;
                }
              }
            }
            leaf node8 {
              description 'No.8 node id in the ring-map.'
                          ;
              type uint8 {
                range 1..127 {
                  description 'Aps node id'
                              ;
                }
              }
            }
            leaf node9 {
              description 'No.9 aps node id in the ring-map.'
                          ;
              type uint8 {
                range 1..127 {
                  description 'APS node id'
                              ;
                }
              }
            }
            leaf node10 {
              description 'No.10 node id in the ring-map.'
                          ;
              type uint8 {
                range 1..127 {
                  description 'Aps node id'
                              ;
                }
              }
            }
            leaf node11 {
              description 'No.11 node id in the ring-map.'
                          ;
              type uint8 {
                range 1..127 {
                  description 'Aps node id'
                              ;
                }
              }
            }
            leaf node12 {
              description 'No.12 aps node id in the ring-map.'
                          ;
              type uint8 {
                range 1..127 {
                  description 'APS node id'
                              ;
                }
              }
            }
            leaf node13 {
              description 'No.13 node id in the ring-map.'
                          ;
              type uint8 {
                range 1..127 {
                  description 'Aps node id'
                              ;
                }
              }
            }
            leaf node14 {
              description 'No.14 node id in the ring-map.'
                          ;
              type uint8 {
                range 1..127 {
                  description 'Aps node id'
                              ;
                }
              }
            }
            leaf node15 {
              description 'No.15 aps node id in the ring-map.'
                          ;
              type uint8 {
                range 1..127 {
                  description 'APS node id'
                              ;
                }
              }
            }
            leaf node16 {
              description 'No.16 node id in the ring-map.'
                          ;
              type uint8 {
                range 1..127 {
                  description 'Aps node id'
                              ;
                }
              }
            }
            leaf node17 {
              description 'No.17 node id in the ring-map.'
                          ;
              type uint8 {
                range 1..127 {
                  description 'Aps node id'
                              ;
                }
              }
            }
            leaf node18 {
              description 'No.18 aps node id in the ring-map.'
                          ;
              type uint8 {
                range 1..127 {
                  description 'APS node id'
                              ;
                }
              }
            }
            leaf node19 {
              description 'No.19 node id in the ring-map.'
                          ;
              type uint8 {
                range 1..127 {
                  description 'Aps node id'
                              ;
                }
              }
            }
            leaf node20 {
              description 'No.20 node id in the ring-map.'
                          ;
              type uint8 {
                range 1..127 {
                  description 'Aps node id'
                              ;
                }
              }
            }
            leaf node21 {
              description 'No.21 aps node id in the ring-map.'
                          ;
              type uint8 {
                range 1..127 {
                  description 'APS node id'
                              ;
                }
              }
            }
            leaf node22 {
              description 'No.22 node id in the ring-map.'
                          ;
              type uint8 {
                range 1..127 {
                  description 'Aps node id'
                              ;
                }
              }
            }
            leaf node23 {
              description 'No.23 node id in the ring-map.'
                          ;
              type uint8 {
                range 1..127 {
                  description 'Aps node id'
                              ;
                }
              }
            }
            leaf node24 {
              description 'No.24 aps node id in the ring-map.'
                          ;
              type uint8 {
                range 1..127 {
                  description 'APS node id'
                              ;
                }
              }
            }
            leaf node25 {
              description 'No.25 node id in the ring-map.'
                          ;
              type uint8 {
                range 1..127 {
                  description 'Aps node id'
                              ;
                }
              }
            }
            leaf node26 {
              description 'No.26 node id in the ring-map.'
                          ;
              type uint8 {
                range 1..127 {
                  description 'Aps node id'
                              ;
                }
              }
            }
            leaf node27 {
              description 'No.27 aps node id in the ring-map.'
                          ;
              type uint8 {
                range 1..127 {
                  description 'APS node id'
                              ;
                }
              }
            }
            leaf node28 {
              description 'No.28 node id in the ring-map.'
                          ;
              type uint8 {
                range 1..127 {
                  description 'Aps node id'
                              ;
                }
              }
            }
            leaf node29 {
              description 'No.29 aps node id in the ring-map.'
                          ;
              type uint8 {
                range 1..127 {
                  description 'APS node id'
                              ;
                }
              }
            }
            leaf node30 {
              description 'No.30 node id in the ring-map.'
                          ;
              type uint8 {
                range 1..127 {
                  description 'Aps node id'
                              ;
                }
              }
            }
            leaf node31 {
              description 'No.31 aps node id in the ring-map.'
                          ;
              type uint8 {
                range 1..127 {
                  description 'APS node id'
                              ;
                }
              }
            }
            leaf node32 {
              description 'No.32 node id in the ring-map.'
                          ;
              type uint8 {
                range 1..127 {
                  description 'Aps node id'
                              ;
                }
              }
            }
            leaf node33 {
              description 'No.33 node id in the ring-map.'
                          ;
              type uint8 {
                range 1..127 {
                  description 'Aps node id'
                              ;
                }
              }
            }
            leaf node34 {
              description 'No.34 aps node id in the ring-map.'
                          ;
              type uint8 {
                range 1..127 {
                  description 'APS node id'
                              ;
                }
              }
            }
            leaf node35 {
              description 'No.35 node id in the ring-map.'
                          ;
              type uint8 {
                range 1..127 {
                  description 'Aps node id'
                              ;
                }
              }
            }
            leaf node36 {
              description 'No.36 node id in the ring-map.'
                          ;
              type uint8 {
                range 1..127 {
                  description 'Aps node id'
                              ;
                }
              }
            }
            leaf node37 {
              description 'No.37 aps node id in the ring-map.'
                          ;
              type uint8 {
                range 1..127 {
                  description 'APS node id'
                              ;
                }
              }
            }
            leaf node38 {
              description 'No.38 node id in the ring-map.'
                          ;
              type uint8 {
                range 1..127 {
                  description 'Aps node id'
                              ;
                }
              }
            }
            leaf node39 {
              description 'No.39 node id in the ring-map.'
                          ;
              type uint8 {
                range 1..127 {
                  description 'Aps node id'
                              ;
                }
              }
            }
            leaf node40 {
              description 'No.40 aps node id in the ring-map.'
                          ;
              type uint8 {
                range 1..127 {
                  description 'APS node id'
                              ;
                }
              }
            }
            leaf node41 {
              description 'No.41 node id in the ring-map.'
                          ;
              type uint8 {
                range 1..127 {
                  description 'Aps node id'
                              ;
                }
              }
            }
            leaf node42 {
              description 'No.42 node id in the ring-map.'
                          ;
              type uint8 {
                range 1..127 {
                  description 'Aps node id'
                              ;
                }
              }
            }
            leaf node43 {
              description 'No.43 aps node id in the ring-map.'
                          ;
              type uint8 {
                range 1..127 {
                  description 'APS node id'
                              ;
                }
              }
            }
            leaf node44 {
              description 'No.44 node id in the ring-map.'
                          ;
              type uint8 {
                range 1..127 {
                  description 'Aps node id'
                              ;
                }
              }
            }
            leaf node45 {
              description 'No.45 node id in the ring-map.'
                          ;
              type uint8 {
                range 1..127 {
                  description 'Aps node id'
                              ;
                }
              }
            }
            leaf node46 {
              description 'No.46 aps node id in the ring-map.'
                          ;
              type uint8 {
                range 1..127 {
                  description 'APS node id'
                              ;
                }
              }
            }
            leaf node47 {
              description 'No.47 node id in the ring-map.'
                          ;
              type uint8 {
                range 1..127 {
                  description 'Aps node id'
                              ;
                }
              }
            }
            leaf node48 {
              description 'No.48 node id in the ring-map.'
                          ;
              type uint8 {
                range 1..127 {
                  description 'Aps node id'
                              ;
                }
              }
            }
            leaf node49 {
              description 'No.49 node id in the ring-map.'
                          ;
              type uint8 {
                range 1..127 {
                  description 'Aps node id'
                              ;
                }
              }
            }
            leaf node50 {
              description 'No.50 node id in the ring-map.'
                          ;
              type uint8 {
                range 1..127 {
                  description 'Aps node id'
                              ;
                }
              }
            }
            leaf node51 {
              description 'No.51 aps node id in the ring-map.'
                          ;
              type uint8 {
                range 1..127 {
                  description 'APS node id'
                              ;
                }
              }
            }
            leaf node52 {
              description 'No.52 node id in the ring-map.'
                          ;
              type uint8 {
                range 1..127 {
                  description 'Aps node id'
                              ;
                }
              }
            }
            leaf node53 {
              description 'No.53 node id in the ring-map.'
                          ;
              type uint8 {
                range 1..127 {
                  description 'Aps node id'
                              ;
                }
              }
            }
            leaf node54 {
              description 'No.54 aps node id in the ring-map.'
                          ;
              type uint8 {
                range 1..127 {
                  description 'APS node id'
                              ;
                }
              }
            }
            leaf node55 {
              description 'No.55 node id in the ring-map.'
                          ;
              type uint8 {
                range 1..127 {
                  description 'Aps node id'
                              ;
                }
              }
            }
            leaf node56 {
              description 'No.56 node id in the ring-map.'
                          ;
              type uint8 {
                range 1..127 {
                  description 'Aps node id'
                              ;
                }
              }
            }
            leaf node57 {
              description 'No.57 aps node id in the ring-map.'
                          ;
              type uint8 {
                range 1..127 {
                  description 'APS node id'
                              ;
                }
              }
            }
            leaf node58 {
              description 'No.58 node id in the ring-map.'
                          ;
              type uint8 {
                range 1..127 {
                  description 'Aps node id'
                              ;
                }
              }
            }
            leaf node59 {
              description 'No.59 node id in the ring-map.'
                          ;
              type uint8 {
                range 1..127 {
                  description 'Aps node id'
                              ;
                }
              }
            }
            leaf node60 {
              description 'No.60 aps node id in the ring-map.'
                          ;
              type uint8 {
                range 1..127 {
                  description 'APS node id'
                              ;
                }
              }
            }
            leaf node61 {
              description 'No.61 node id in the ring-map.'
                          ;
              type uint8 {
                range 1..127 {
                  description 'Aps node id'
                              ;
                }
              }
            }
            leaf node62 {
              description 'No.62 node id in the ring-map.'
                          ;
              type uint8 {
                range 1..127 {
                  description 'Aps node id'
                              ;
                }
              }
            }
          }
        }
      }
      container ac-groups {
        description 'Configure AC group APS parameters.'
                    ;
        list ac-group {
          description 'Configure AC group APS parameters.'
                      ;
          key group-name ;
          leaf group-name {
            description 'Group name of AC group APS.'
                        ;
            type ncd:ifname ;
          }
          leaf active-state {
            description "Active state of AC group's APS."
                        ;
            type active-state ;
            default active-or-restore ;
          }
          leaf is-active {
            description 'Active flag of AC group APS.'
                        ;
            type is-active ;
            default active ;
          }
          leaf hold-off-time {
            description 'Hold-off timer for AC group APS(100ms).'
                        ;
            type uint8 {
              range 0..100 {
                description 'Hold off time(100ms).'
                            ;
              }
            }
            units 100ms ;
            default 0 ;
          }
          leaf hold-off-precise {
            description 'Hold-off precise timer for AC group APS(10ms).'
                        ;
            type uint8 {
              range 1..9 {
                description 'hold off precise time(10ms)'
                            ;
              }
            }
            units 10ms ;
            ncd:revise-date 2018-01-02 ;
          }
          leaf revertive-mode {
            description 'Revertive mode of AC group APS.'
                        ;
            type revertive-mode ;
            default revertive ;
          }
          leaf wtr-time {
            description 'Wait-to-restore timer for AC group APS(minute).'
                        ;
            type uint8 {
              range 0..12 {
                description 'Wait to restore time(minute).'
                            ;
              }
            }
            units minute ;
            default 0 ;
          }
          leaf switch-cmd {
            description 'Switch command of AC group APS.'
                        ;
            type switch-cmd-linear ;
            default null ;
          }
          leaf send-packet-mode {
            description 'Send packet mode of AC group APS.'
                        ;
            type send-packet-mode ;
            default send ;
          }
          leaf bridge-type {
            description 'Bridge type of AC group APS.'
                        ;
            type bridge-type ;
            default selector ;
            ncd:revise-date 2016-11-08 ;
          }
          leaf sd-preferred {
            description 'SD preferred of AC PW group APS.'
                        ;
            type sd-preferred ;
            default invalid ;
            ncd:revise-date 2017-04-22 ;
          }
        }
      }
      container mtunnel-groups {
        description 'Configure P2MP tunnel group APS parame.'
                    ;
        list mtunnel-group {
          description 'Configure P2MP tunnel group APS parameters.'
                      ;
          key group-id ;
          leaf group-id {
            description 'Group ID of P2MP tunnel group APS.'
                        ;
            type uint32 {
              range 1..32768 {
                description 'Group ID.'
                            ;
              }
            }
          }
          leaf active-state {
            description 'Active state of P2MP tunnel group APS.'
                        ;
            type active-state ;
            default active-or-restore ;
          }
          leaf hold-off-time {
            description 'Hold-off timer for P2MP tunnel group APS(100ms).'
                        ;
            type uint8 {
              range 0..100 {
                description 'hold off time(100ms)'
                            ;
              }
            }
            units 100ms ;
            default 0 ;
          }
          leaf hold-off-precise {
            description 'Hold-off precise timer for P2MP tunnel group APS(10ms).'
                        ;
            type uint8 {
              range 1..9 {
                description 'hold off precise time(10ms)'
                            ;
              }
            }
            units 10ms ;
            ncd:revise-date 2018-01-02 ;
          }
          leaf revertive-mode {
            description 'Revertive mode of P2MP tunnel group APS.'
                        ;
            type revertive-mode ;
            default revertive ;
          }
          leaf wtr-time {
            description 'Wait-to-restore timer for P2MP tunnel group APS(minute'
                      + ').'
                        ;
            type uint8 {
              range 0..12 {
                description 'Wait to restore time(minute).'
                            ;
              }
            }
            units minute ;
            default 5 ;
          }
          leaf switch-cmd {
            description 'Switch command of P2MP tunnel group APS.'
                        ;
            type switch-cmd-linear ;
            default null ;
          }
          leaf bridge-type {
            description 'Bridge type of P2MP tunnel group APS.'
                        ;
            type bridge-type ;
            default selector ;
            ncd:revise-date 2016-11-08 ;
          }
          leaf sd-preferred {
            description 'SD preferred of mtunnel group APS.'
                        ;
            type sd-preferred ;
            default invalid ;
            ncd:revise-date 2017-04-22 ;
          }
        }
        ncd:revise-date 2015-07-01 ;
      }
      container erps-groups {
        description 'Configure APS parameters of ERPS group.'
                    ;
        list erps-group {
          description 'Configure APS parameters of ERPS group.'
                      ;
          key 'group-id group-type'
              ;
          leaf group-id {
            description 'Group ID of ERPS group.'
                        ;
            type uint32 {
              range 1..255 {
                description 'Group ID.'
                            ;
              }
            }
          }
          leaf group-type {
            description 'Group type of ERPS group.'
                        ;
            type group-type-erps ;
          }
          leaf ring-id {
            status obsolete {
              ncd:revise-date 2020-06-15 ;
            }
            description "Ring ID of ERPS APS.
\nThe same ring ID cann't be used"
                      + " by different groups."
                        ;
            type uint8 {
              range 1..239 {
                description 'ring id'
                            ;
              }
            }
          }
          leaf hold-off-time {
            description 'Hold-off timer for ERPS APS(100ms).'
                        ;
            type uint8 {
              range 0..100 {
                description 'Hold off time(100ms).'
                            ;
              }
            }
            units 100ms ;
            default 0 ;
          }
          leaf hold-off-precise {
            description 'Hold-off timer for ERPS APS(10ms).'
                        ;
            type uint8 {
              range 1..9 {
                description 'hold off precise time(10ms)'
                            ;
              }
            }
            units 10ms ;
            ncd:revise-date 2018-01-02 ;
          }
          leaf guard-time {
            description 'Guard timer for ERPS APS(10ms).'
                        ;
            type uint8 {
              range 1..200 {
                description 'Guard time(range:10ms~2000ms,step:10ms)'
                            ;
              }
            }
            units 10ms ;
            default 50 ;
          }
          leaf wtr-time {
            description 'Wait-to-restore timer for ERPS APS(minute).'
                        ;
            type uint8 {
              range 1..12 {
                description 'Wait to restore time(minute).'
                            ;
              }
            }
            units min ;
            default 5 ;
          }
          leaf mel {
            description 'MEG level of ERPS APS.'
                        ;
            type uint8 {
              range 0..7 {
                description 'MEG level.'
                            ;
              }
            }
            default 7 ;
          }
          leaf east-switch {
            description 'East switch command of ERPS APS.The east switching com'
                      + 'mand is mutually exclusive to the west switching comma'
                      + 'nd'
                        ;
            type switch-cmd-erps ;
            default null ;
          }
          leaf west-switch {
            description 'West switch command of ERPS APS.The west switching com'
                      + 'mand is mutually exclusive to the east switching comma'
                      + 'nd'
                        ;
            type switch-cmd-erps ;
            default null ;
          }
          leaf revertive-mode {
            description 'Revertive mode of ERPS APS.'
                        ;
            type revertive-mode ;
            default revertive ;
          }
          leaf node-id {
            description 'Node ID of ERPS APS.'
                        ;
            type ncd:mac-address ;
            default ff:ff:ff:ff:ff:ff ;
          }
          container ring-cfg {
            description 'Configure ring.'
                        ;
            presence ring-cfg ;
            leaf ring-id {
              description "Ring ID of ERPS APS.
\nThe same ring ID cann't be us"
                        + "ed by different groups."
                          ;
              type uint8 {
                range 1..239 {
                  description 'Ring ID.'
                              ;
                }
              }
              mandatory true ;
            }
            container sub-ring-cfg {
              description 'Configure sub-ring.'
                          ;
              presence sub-ring ;
              leaf sub-ring {
                description 'Configure sub-ring.'
                            ;
                type enumeration {
                  enum sub-ring {
                    value 1 ;
                    description sub-ring ;
                  }
                }
                mandatory true ;
              }
              leaf interconnect {
                description 'The interconnection node of sub-ring.'
                            ;
                type enumeration {
                  enum interconnect {
                    value 1 ;
                    description 'The interconnection node.'
                                ;
                  }
                }
              }
            }
            ncd:revise-date 2020-06-15 ;
          }
          leaf version {
            description 'Configure version.'
                        ;
            type uint8 {
              range 1..2 {
                description Version ;
              }
            }
            default 2 ;
            ncd:revise-date 2020-07-08 ;
          }
        }
        ncd:revise-date 2015-12-24 ;
      }
      leaf sd-preferred {
        description 'Configure APS instance SD preferred'
                    ;
        type enumeration {
          enum disabled {
            value 0 ;
          }
          enum enabled {
            value 1 ;
          }
        }
        default disabled ;
        ncd:revise-date 2017-04-22 ;
      }
      container port-group-multicasts {
        description 'Configure multicast port group APS parameters.'
                    ;
        list multicast {
          description 'Configure multicast port group APS parameters.'
                      ;
          key group-id ;
          leaf group-id {
            description 'Group ID of port group APS.'
                        ;
            type uint32 {
              range 1..65535 {
                description 'Group ID.'
                            ;
              }
            }
          }
          leaf active-state {
            description 'Active state of port group APS.'
                        ;
            type active-state ;
            default active-or-restore ;
          }
          leaf hold-off-time {
            description 'Hold-off timer for port group APS(100ms).'
                        ;
            type uint8 {
              range 0..100 {
                description 'Hold off time(100ms).'
                            ;
              }
            }
            units 100ms ;
            default 0 ;
          }
          leaf hold-off-precise {
            description 'Hold-off precise timer for port group APS(10ms).'
                        ;
            type uint8 {
              range 1..9 {
                description 'hold off precise time(10ms)'
                            ;
              }
            }
            units 10ms ;
          }
          leaf revertive-mode {
            description 'Revertive mode of port group APS.'
                        ;
            type revertive-mode ;
            default revertive ;
          }
          leaf wtr-time {
            description 'Wait-to-restore timer for port group APS(minute).'
                        ;
            type uint8 {
              range 0..12 {
                description 'Wait to restore time(minute).'
                            ;
              }
            }
            units minute ;
            default 5 ;
          }
          leaf swtich-cmd {
            description 'Switch command of port group APS.'
                        ;
            type switch-cmd-msp ;
            default null ;
          }
          leaf is-active {
            description 'Active flag of port group aps.'
                        ;
            type is-active ;
            default active ;
          }
        }
        ncd:revise-date 2019-06-21 ;
      }
      container port-group-otns {
        description 'Configure OTN port group APS parameters.'
                    ;
        list otn {
          description 'Configure OTN port group APS parameters.'
                      ;
          key group-id ;
          leaf group-id {
            description 'Group ID of port group APS.'
                        ;
            type uint32 {
              range 1..65535 {
                description 'Group ID.'
                            ;
              }
            }
          }
          leaf active-state {
            description 'Active state of port group APS.'
                        ;
            type active-state ;
            default active-or-restore ;
          }
          leaf hold-off-time {
            description 'Hold-off timer for port group APS(100ms).'
                        ;
            type uint8 {
              range 0..100 {
                description 'Hold off time(100ms).'
                            ;
              }
            }
            units 100ms ;
            default 0 ;
          }
          leaf hold-off-precise {
            description 'Hold-off precise timer for port group APS(10ms).'
                        ;
            type uint8 {
              range 1..9 {
                description 'hold off precise time(10ms)'
                            ;
              }
            }
            units 10ms ;
          }
          leaf revertive-mode {
            description 'Revertive mode of port group APS.'
                        ;
            type revertive-mode ;
            default revertive ;
          }
          leaf wtr-time {
            description 'Wait-to-restore timer for port group APS(minute).'
                        ;
            type uint8 {
              range 0..12 {
                description 'Wait to restore time(minute).'
                            ;
              }
            }
            units minute ;
            default 5 ;
          }
          leaf swtich-cmd {
            description 'Switch command of port group APS.'
                        ;
            type switch-cmd-msp ;
            default null ;
          }
          leaf is-active {
            description 'Active flag of port group aps.'
                        ;
            type is-active ;
            default active ;
          }
        }
        ncd:revise-date 2019-06-21 ;
      }
      container port-group-ether-services {
        description 'Configure ether-service port group APS parameters.'
                    ;
        list ether-service {
          description 'Configure ether-service port group APS parameters.'
                      ;
          key group-id ;
          leaf group-id {
            description 'Group ID of port group APS.'
                        ;
            type uint32 {
              range 1..65535 {
                description 'Group ID.'
                            ;
              }
            }
          }
          leaf active-state {
            description 'Active state of port group APS.'
                        ;
            type active-state ;
            default active-or-restore ;
          }
          leaf hold-off-time {
            description 'Hold-off timer for port group APS(100ms).'
                        ;
            type uint8 {
              range 0..100 {
                description 'Hold off time(100ms).'
                            ;
              }
            }
            units 100ms ;
            default 0 ;
          }
          leaf hold-off-precise {
            description 'Hold-off precise timer for port group APS(10ms).'
                        ;
            type uint8 {
              range 1..9 {
                description 'hold off precise time(10ms)'
                            ;
              }
            }
            units 10ms ;
          }
          leaf revertive-mode {
            description 'Revertive mode of port group APS.'
                        ;
            type revertive-mode ;
            default revertive ;
          }
          leaf wtr-time {
            description 'Wait-to-restore timer for port group APS(minute).'
                        ;
            type uint8 {
              range 0..12 {
                description 'Wait to restore time(minute).'
                            ;
              }
            }
            units minute ;
            default 5 ;
          }
          leaf swtich-cmd {
            description 'Switch command of port group APS.'
                        ;
            type switch-cmd-msp ;
            default null ;
          }
          leaf is-active {
            description 'Active flag of port group aps.'
                        ;
            type is-active ;
            default active ;
          }
          leaf send-packet-mode {
            description 'Send packet mode of ether port group APS.'
                        ;
            type send-packet-mode ;
            default send ;
          }
          leaf bridge-type {
            description 'Bridge type of ether port group APS.'
                        ;
            type bridge-type ;
            default selector ;
          }
          leaf mel {
            description 'MEG level of ether port group APS.'
                        ;
            type uint8 {
              range 0..7 {
                description 'MEG level.'
                            ;
              }
            }
            default 7 ;
          }
          leaf sd-preferred {
            description 'SD preferred of ether port group APS.'
                        ;
            type sd-preferred ;
            default invalid ;
          }
        }
        ncd:revise-date 2019-06-21 ;
      }
      container port-group-flexes {
        description 'Configure flexe-client port group APS parameters.'
                    ;
        list flexe {
          description 'Configure flexe-client port group APS parameters.'
                      ;
          key group-id ;
          leaf group-id {
            description 'Group ID of port group APS.'
                        ;
            type uint32 {
              range 1..65535 {
                description 'Group ID.'
                            ;
              }
            }
          }
          leaf active-state {
            description 'Active state of port group APS.'
                        ;
            type active-state ;
            default active-or-restore ;
          }
          leaf hold-off-time {
            description 'Hold-off timer for port group APS(100ms).'
                        ;
            type uint8 {
              range 0..100 {
                description 'Hold off time(100ms).'
                            ;
              }
            }
            units 100ms ;
            default 0 ;
          }
          leaf hold-off-precise {
            description 'Hold-off precise timer for port group APS(10ms).'
                        ;
            type uint8 {
              range 1..9 {
                description 'hold off precise time(10ms)'
                            ;
              }
            }
            units 10ms ;
          }
          leaf revertive-mode {
            description 'Revertive mode of port group APS.'
                        ;
            type revertive-mode ;
            default revertive ;
          }
          leaf wtr-time {
            description 'Wait-to-restore timer for port group APS(minute).'
                        ;
            type uint8 {
              range 0..12 {
                description 'Wait to restore time(minute).'
                            ;
              }
            }
            units minute ;
            default 5 ;
          }
          leaf swtich-cmd {
            description 'Switch command of port group APS.'
                        ;
            type switch-cmd-msp ;
            default null ;
          }
          leaf is-active {
            description 'Active flag of port group aps.'
                        ;
            type is-active ;
            default active ;
          }
        }
        ncd:revise-date 2019-06-21 ;
      }
      container port-group-flexe-subs {
        description 'Configure flexe-subclient port group APS parameters.'
                    ;
        list flexe-sub {
          description 'Configure flexe-subclient port group APS parameters.'
                      ;
          key group-id ;
          leaf group-id {
            description 'Group ID of port group APS.'
                        ;
            type uint32 {
              range 1..65535 {
                description 'Group ID.'
                            ;
              }
            }
          }
          leaf active-state {
            description 'Active state of port group APS.'
                        ;
            type active-state ;
            default active-or-restore ;
          }
          leaf hold-off-time {
            description 'Hold-off timer for port group APS(100ms).'
                        ;
            type uint8 {
              range 0..100 {
                description 'Hold off time(100ms).'
                            ;
              }
            }
            units 100ms ;
            default 0 ;
          }
          leaf hold-off-precise {
            description 'Hold-off precise timer for port group APS(10ms).'
                        ;
            type uint8 {
              range 1..9 {
                description 'hold off precise time(10ms)'
                            ;
              }
            }
            units 10ms ;
          }
          leaf revertive-mode {
            description 'Revertive mode of port group APS.'
                        ;
            type revertive-mode ;
            default revertive ;
          }
          leaf wtr-time {
            description 'Wait-to-restore timer for port group APS(minute).'
                        ;
            type uint8 {
              range 0..12 {
                description 'Wait to restore time(minute).'
                            ;
              }
            }
            units minute ;
            default 5 ;
          }
          leaf switch-cmd {
            description 'Switch command of port group APS.'
                        ;
            type switch-cmd-linear ;
            default null ;
          }
          leaf is-active {
            description 'Active flag of port group aps.'
                        ;
            type is-active ;
            default active ;
          }
          leaf send-packet-mode {
            description 'Send packet mode of port group APS.'
                        ;
            type send-packet-mode ;
            default send ;
          }
          leaf bridge-type {
            description 'Bridge type of port group APS.'
                        ;
            type bridge-type ;
            default selector ;
          }
          leaf mel {
            description 'MEG level of port group APS.'
                        ;
            type uint8 {
              range 0..7 {
                description 'MEG level.'
                            ;
              }
            }
            default 7 ;
          }
        }
        ncd:revise-date 2020-08-19 ;
      }
      container erps-vlan-groups {
        description 'Configure APS parameters of ERPS VLAN group.'
                    ;
        list erps-vlan-group {
          description 'Configure APS parameters of ERPS VLAN group.'
                      ;
          key 'group-id group-type'
              ;
          leaf group-id {
            description 'Group ID of ERPS VLAN group.'
                        ;
            type uint32 {
              range 1..239 {
                description 'Group ID.'
                            ;
              }
            }
          }
          leaf group-type {
            description 'Group type of ERPS group.'
                        ;
            type group-type-erps ;
          }
          leaf hold-off-time {
            description 'Hold-off timer for ERPS APS(100ms).'
                        ;
            type uint8 {
              range 0..100 {
                description 'Hold off time(100ms).'
                            ;
              }
            }
            units 100ms ;
            default 0 ;
          }
          leaf hold-off-precise {
            description 'Hold-off timer for ERPS APS(10ms).'
                        ;
            type uint8 {
              range 1..9 {
                description 'Hold off precise time(10ms)'
                            ;
              }
            }
            units 10ms ;
          }
          leaf guard-time {
            description 'Guard timer for ERPS APS(10ms).'
                        ;
            type uint8 {
              range 1..200 {
                description 'Guard time(range:10ms~2000ms,step:10ms)'
                            ;
              }
            }
            units 10ms ;
            default 50 ;
          }
          leaf wtr-time {
            description 'Wait-to-restore timer for ERPS APS(minute).'
                        ;
            type uint8 {
              range 1..12 {
                description 'Wait to restore time(minute).'
                            ;
              }
            }
            units min ;
            default 5 ;
          }
          leaf mel {
            description 'MEG level of ERPS APS.'
                        ;
            type uint8 {
              range 0..7 {
                description 'MEG level.'
                            ;
              }
            }
            default 7 ;
          }
          leaf east-switch {
            description 'East switch command of ERPS APS.The east switching com'
                      + 'mand is mutually exclusive to the west switching comma'
                      + 'nd.'
                        ;
            type switch-cmd-erps ;
            default null ;
          }
          leaf west-switch {
            description 'West switch command of ERPS APS.The west switching com'
                      + 'mand is mutually exclusive to the east switching comma'
                      + 'nd.'
                        ;
            type switch-cmd-erps ;
            default null ;
          }
          leaf revertive-mode {
            description 'Revertive mode of ERPS APS.'
                        ;
            type revertive-mode ;
            default revertive ;
          }
          leaf node-id {
            description 'Node ID of ERPS APS.'
                        ;
            type ncd:mac-address ;
            default ff:ff:ff:ff:ff:ff ;
          }
          container ring-cfg {
            description 'Configure ring.'
                        ;
            presence ring-cfg ;
            leaf ring-id {
              description "Ring ID of ERPS APS.
\nThe same ring ID cann't be us"
                        + "ed by different groups."
                          ;
              type uint8 {
                range 1..239 {
                  description 'Ring ID'
                              ;
                }
              }
              mandatory true ;
            }
            container sub-ring-cfg {
              description 'Configure sub-ring.'
                          ;
              presence sub-ring ;
              leaf sub-ring {
                description 'Configure sub-ring.'
                            ;
                type enumeration {
                  enum sub-ring {
                    value 1 ;
                    description sub-ring ;
                  }
                }
                mandatory true ;
              }
              leaf interconnect {
                description 'The interconnection node of sub-ring.'
                            ;
                type enumeration {
                  enum interconnect {
                    value 1 ;
                    description 'The interconnection node'
                                ;
                  }
                }
              }
            }
          }
          leaf version {
            description 'Configure version.'
                        ;
            type uint8 {
              range 1..2 {
                description Version ;
              }
            }
            default 2 ;
            ncd:revise-date 2020-07-08 ;
          }
        }
        ncd:revise-date 2020-06-15 ;
      }
    }
  }
  container state {
    config false ;
    description 'State model info.'
                ;
    container aps {
      description 'APS state information.'
                  ;
      container section-groups {
        description 'The state information of ring APS.'
                    ;
        list section-group {
          description 'The state information of ring APS.'
                      ;
          key 'pg-index object-index'
              ;
          leaf pg-index {
            description 'APS session ID of section group.'
                        ;
            type uint32 {
              range 1..64 {
                description 'Group Id'
                            ;
              }
            }
          }
          leaf object-index {
            description 'Section ID of ring APS.'
                        ;
            type uint32 {
              range 1..4000 {
                description 'Section ID.'
                            ;
              }
            }
          }
          leaf protect-status {
            description 'Protect status of ring APS.'
                        ;
            type uint8 {
              range 0..14 {
                description 'Protect status.'
                            ;
              }
            }
          }
          leaf direction {
            description 'Direction of ring APS.'
                        ;
            type ring-aps-direction ;
          }
          ncd:select 'pg-index object-index'
                     ;
        }
      }
      container tunnel-groups {
        description 'The state information of tunnel group aps.'
                    ;
        list tunnel-group {
          description 'The state information of tunnel group APS.'
                      ;
          key pg-index ;
          leaf pg-index {
            description 'APS session ID of tunnel group.'
                        ;
            type uint32 {
              range 1..4294967295 {
                description 'Group ID.'
                            ;
              }
            }
          }
          leaf protect-status {
            description 'Protect status of tunnel group APS.'
                        ;
            type uint8 {
              range 0..16 {
                description 'Protect status.'
                            ;
              }
            }
          }
        }
      }
      container mtunnel-groups {
        description 'The state information of P2MP tunnel group aps.'
                    ;
        list mtunnel-group {
          description 'The state information of P2MP tunnel group APS.'
                      ;
          key pg-index ;
          leaf pg-index {
            description 'APS session ID of P2MP tunnel group.'
                        ;
            type uint32 {
              range 1..32768 {
                description 'Group ID.'
                            ;
              }
            }
          }
          leaf protect-status {
            description 'Protect status of P2MP tunnel group APS.'
                        ;
            type uint8 {
              range 0..16 {
                description 'Protect status.'
                            ;
              }
            }
          }
        }
        ncd:revise-date 2015-07-01 ;
      }
      container port-groups {
        description 'The state information of port group aps.'
                    ;
        list port-group {
          description 'The state information of port group APS.'
                      ;
          key pg-index ;
          leaf pg-index {
            description 'APS session ID of port group.'
                        ;
            type uint32 {
              range 1..65535 {
                description 'Group ID.'
                            ;
              }
            }
          }
          leaf protect-status {
            description 'Protect status of port group APS:'+"\n"
                      + '0 NO_REQUEST_NULL'+"\n"
                      + '1 NO_REQUEST_NORMAL'+"\n"
                      + '2 MANUAL_SWITCH'+"\n"
                      + '3 MANUAL_SWITCH_W '+"\n"
                      + '4 SIGNAL_FAIL_W'+"\n"
                      + '5 SIGNAL_FAIL_P'+"\n"
                      + '6 SIGNAL_DEGR_W'+"\n"
                      + '7 SIGNAL_DEGR_P'+"\n"
                      + '8 WAIT_TO_RESTORE'+"\n"
                      + '9 FORCED_SWITCH'+"\n"
                      + '10 FORCED_SWITCH_W'+"\n"
                      + '11 LOCKOUT'+"\n"
                      + '12 EXERCISE_NULL'+"\n"
                      + '13 EXERCISE_NORMAL'+"\n"
                      + '14 NOT_READY'+"\n"
                      + '15 DO_NOT_REVERT'+"\n"
                      + '16 SIGNAL_FAIL_P with work and protection both failed'+"\n"
                      + '17 not finish MANUAL_SWITCH'+"\n"
                      + '18 not finish MANUAL_SWITCH_W'+"\n"
                      + '19 not finish SIGNAL_FAIL_W'+"\n"
                      + '20 not finish SIGNAL_FAIL_P'+"\n"
                      + '21 not finish SIGNAL_DEGR_W'+"\n"
                      + '22 not finish SIGNAL_DEGR_P'+"\n"
                      + '23 not finish FORCED_SWITCH'+"\n"
                      + '24 not finish FORCED_SWITCH_W'+"\n"
                      + '25 not finish LOCKOUT'+"\n"
                      + '26 not finish EXERCISE_NULL'+"\n"
                      + '27 not finish EXERCISE_NORMAL'+"\n"
                      + '28 REVERSE_REQUEST_NULL'+"\n"
                      + '29 REVERSE_REQUEST_NORMAL'
                        ;
            type uint8 ;
          }
        }
      }
      container pw-groups {
        description 'The state information of PW group aps.'
                    ;
        list pw-group {
          description 'The state information of PW group APS.'
                      ;
          key pg-name ;
          leaf pg-name {
            description 'APS session name of PW group.'
                        ;
            type ncd:ifname ;
          }
          leaf protect-status {
            description 'Protect status of PW group APS.'
                        ;
            type uint8 ;
          }
        }
      }
      container lsp-groups {
        description 'The state information of LSP group aps.'
                    ;
        list lsp-group {
          description 'The state information of LSP group APS.'
                      ;
          key pg-index ;
          leaf pg-index {
            description 'APS session ID of LSP group.'
                        ;
            type uint32 {
              range 1..4096 {
                description 'Group ID.'
                            ;
              }
            }
          }
          leaf protect-status {
            description 'Protect status of lsp group APS.'
                        ;
            type uint8 ;
          }
        }
      }
      container mc-selection-groups {
        description 'The state information of mc-selection group APS.'
                    ;
        list mc-selection-group {
          description 'The state information of mc-selection group APS.'
                      ;
          key pg-name ;
          leaf pg-name {
            description 'APS session name of mc-selection group.'
                        ;
            type ncd:ifname ;
          }
          leaf protect-status {
            description 'Protect status of mc-selection group APS.'
                        ;
            type uint8 ;
          }
        }
      }
      container ac-groups {
        description 'The state information of AC group APS.'
                    ;
        list ac-group {
          description 'The state information of AC group APS.'
                      ;
          key pg-name ;
          leaf pg-name {
            description 'APS session name of AC group.'
                        ;
            type ncd:ifname ;
          }
          leaf protect-status {
            description 'Protect status of AC group APS.'
                        ;
            type uint8 ;
          }
        }
      }
      container erps-groups {
        description 'The state information of ERPS APS.'
                    ;
        list erps-group {
          description 'The state information of ERPS APS.'
                      ;
          key 'group-index group-type'
              ;
          leaf group-index {
            description 'APS session ID of ERPS group.'
                        ;
            type uint32 {
              range 1..255 {
                description 'Group ID'
                            ;
              }
            }
          }
          leaf group-type {
            description 'Group type of ERPS APS.'
                        ;
            type group-type-erps ;
          }
          leaf protect-status {
            description 'Protection status of ERPS APS.'
                        ;
            type enumeration {
              enum IDLE {
                value 0 ;
                description 'Idle state.'
                            ;
              }
              enum Protection {
                value 1 ;
                description 'Protection state.'
                            ;
              }
              enum MS {
                value 2 ;
                description 'Manual switch state.'
                            ;
              }
              enum FS {
                value 3 ;
                description 'Force switch state.'
                            ;
              }
              enum Pending {
                value 4 ;
                description 'Pending state.'
                            ;
              }
            }
          }
          ncd:select 'group-index group-type'
                     ;
          ncd:select group-type ;
        }
        ncd:revise-date 2015-12-24 ;
      }
      container port-group-multicasts {
        description 'The state information of multicast port group aps.'
                    ;
        list multicast {
          description 'The state information of multicast port group APS.'
                      ;
          key pg-index ;
          leaf pg-index {
            description 'APS session ID of port group.'
                        ;
            type uint32 {
              range 1..65535 {
                description 'Group ID.'
                            ;
              }
            }
          }
          leaf protect-status {
            description 'Protect status of port group APS:'+"\n"
                      + '0 NO_REQUEST_NULL'+"\n"
                      + '1 NO_REQUEST_NORMAL'+"\n"
                      + '2 MANUAL_SWITCH'+"\n"
                      + '3 MANUAL_SWITCH_W '+"\n"
                      + '4 SIGNAL_FAIL_W'+"\n"
                      + '5 SIGNAL_FAIL_P'+"\n"
                      + '6 SIGNAL_DEGR_W'+"\n"
                      + '7 SIGNAL_DEGR_P'+"\n"
                      + '8 WAIT_TO_RESTORE'+"\n"
                      + '9 FORCED_SWITCH'+"\n"
                      + '10 FORCED_SWITCH_W'+"\n"
                      + '11 LOCKOUT'+"\n"
                      + '12 EXERCISE_NULL'+"\n"
                      + '13 EXERCISE_NORMAL'+"\n"
                      + '14 NOT_READY'+"\n"
                      + '15 DO_NOT_REVERT'+"\n"
                      + '16 SIGNAL_FAIL_P with work and protection both failed'+"\n"
                      + '17 not finish MANUAL_SWITCH'+"\n"
                      + '18 not finish MANUAL_SWITCH_W'+"\n"
                      + '19 not finish SIGNAL_FAIL_W'+"\n"
                      + '20 not finish SIGNAL_FAIL_P'+"\n"
                      + '21 not finish SIGNAL_DEGR_W'+"\n"
                      + '22 not finish SIGNAL_DEGR_P'+"\n"
                      + '23 not finish FORCED_SWITCH'+"\n"
                      + '24 not finish FORCED_SWITCH_W'+"\n"
                      + '25 not finish LOCKOUT'+"\n"
                      + '26 not finish EXERCISE_NULL'+"\n"
                      + '27 not finish EXERCISE_NORMAL'+"\n"
                      + '28 REVERSE_REQUEST_NULL'+"\n"
                      + '29 REVERSE_REQUEST_NORMAL'
                        ;
            type uint8 ;
          }
        }
        ncd:revise-date 2019-06-21 ;
      }
      container port-group-otns {
        description 'The state information of OTN port group aps.'
                    ;
        list otn {
          description 'The state information of OTN port group APS.'
                      ;
          key pg-index ;
          leaf pg-index {
            description 'APS session ID of port group.'
                        ;
            type uint32 {
              range 1..65535 {
                description 'Group ID.'
                            ;
              }
            }
          }
          leaf protect-status {
            description 'Protect status of port group APS:'+"\n"
                      + '0 NO_REQUEST_NULL'+"\n"
                      + '1 NO_REQUEST_NORMAL'+"\n"
                      + '2 MANUAL_SWITCH'+"\n"
                      + '3 MANUAL_SWITCH_W '+"\n"
                      + '4 SIGNAL_FAIL_W'+"\n"
                      + '5 SIGNAL_FAIL_P'+"\n"
                      + '6 SIGNAL_DEGR_W'+"\n"
                      + '7 SIGNAL_DEGR_P'+"\n"
                      + '8 WAIT_TO_RESTORE'+"\n"
                      + '9 FORCED_SWITCH'+"\n"
                      + '10 FORCED_SWITCH_W'+"\n"
                      + '11 LOCKOUT'+"\n"
                      + '12 EXERCISE_NULL'+"\n"
                      + '13 EXERCISE_NORMAL'+"\n"
                      + '14 NOT_READY'+"\n"
                      + '15 DO_NOT_REVERT'+"\n"
                      + '16 SIGNAL_FAIL_P with work and protection both failed'+"\n"
                      + '17 not finish MANUAL_SWITCH'+"\n"
                      + '18 not finish MANUAL_SWITCH_W'+"\n"
                      + '19 not finish SIGNAL_FAIL_W'+"\n"
                      + '20 not finish SIGNAL_FAIL_P'+"\n"
                      + '21 not finish SIGNAL_DEGR_W'+"\n"
                      + '22 not finish SIGNAL_DEGR_P'+"\n"
                      + '23 not finish FORCED_SWITCH'+"\n"
                      + '24 not finish FORCED_SWITCH_W'+"\n"
                      + '25 not finish LOCKOUT'+"\n"
                      + '26 not finish EXERCISE_NULL'+"\n"
                      + '27 not finish EXERCISE_NORMAL'+"\n"
                      + '28 REVERSE_REQUEST_NULL'+"\n"
                      + '29 REVERSE_REQUEST_NORMAL'
                        ;
            type uint8 ;
          }
        }
        ncd:revise-date 2019-06-21 ;
      }
      container port-group-ether-services {
        description 'The state information of ether-service port group aps.'
                    ;
        list ether-service {
          description 'The state information of ether-service port group APS.'
                      ;
          key pg-index ;
          leaf pg-index {
            description 'APS session ID of port group.'
                        ;
            type uint32 {
              range 1..65535 {
                description 'Group ID.'
                            ;
              }
            }
          }
          leaf protect-status {
            description 'Protect status of port group APS:'+"\n"
                      + '0 NO_REQUEST_NULL'+"\n"
                      + '1 NO_REQUEST_NORMAL'+"\n"
                      + '2 MANUAL_SWITCH'+"\n"
                      + '3 MANUAL_SWITCH_W '+"\n"
                      + '4 SIGNAL_FAIL_W'+"\n"
                      + '5 SIGNAL_FAIL_P'+"\n"
                      + '6 SIGNAL_DEGR_W'+"\n"
                      + '7 SIGNAL_DEGR_P'+"\n"
                      + '8 WAIT_TO_RESTORE'+"\n"
                      + '9 FORCED_SWITCH'+"\n"
                      + '10 FORCED_SWITCH_W'+"\n"
                      + '11 LOCKOUT'+"\n"
                      + '12 EXERCISE_NULL'+"\n"
                      + '13 EXERCISE_NORMAL'+"\n"
                      + '14 NOT_READY'+"\n"
                      + '15 DO_NOT_REVERT'+"\n"
                      + '16 SIGNAL_FAIL_P with work and protection both failed'+"\n"
                      + '17 not finish MANUAL_SWITCH'+"\n"
                      + '18 not finish MANUAL_SWITCH_W'+"\n"
                      + '19 not finish SIGNAL_FAIL_W'+"\n"
                      + '20 not finish SIGNAL_FAIL_P'+"\n"
                      + '21 not finish SIGNAL_DEGR_W'+"\n"
                      + '22 not finish SIGNAL_DEGR_P'+"\n"
                      + '23 not finish FORCED_SWITCH'+"\n"
                      + '24 not finish FORCED_SWITCH_W'+"\n"
                      + '25 not finish LOCKOUT'+"\n"
                      + '26 not finish EXERCISE_NULL'+"\n"
                      + '27 not finish EXERCISE_NORMAL'+"\n"
                      + '28 REVERSE_REQUEST_NULL'+"\n"
                      + '29 REVERSE_REQUEST_NORMAL'
                        ;
            type uint8 ;
          }
        }
        ncd:revise-date 2019-06-21 ;
      }
      container port-group-flexes {
        description 'The state information of flexe-clent port group aps.'
                    ;
        list flexe {
          description 'The state information of flexe-clent port group APS.'
                      ;
          key pg-index ;
          leaf pg-index {
            description 'APS session ID of port group.'
                        ;
            type uint32 {
              range 1..65535 {
                description 'Group ID.'
                            ;
              }
            }
          }
          leaf protect-status {
            description 'Protect status of port group APS:'+"\n"
                      + '0 NO_REQUEST_NULL'+"\n"
                      + '1 NO_REQUEST_NORMAL'+"\n"
                      + '2 MANUAL_SWITCH'+"\n"
                      + '3 MANUAL_SWITCH_W '+"\n"
                      + '4 SIGNAL_FAIL_W'+"\n"
                      + '5 SIGNAL_FAIL_P'+"\n"
                      + '6 SIGNAL_DEGR_W'+"\n"
                      + '7 SIGNAL_DEGR_P'+"\n"
                      + '8 WAIT_TO_RESTORE'+"\n"
                      + '9 FORCED_SWITCH'+"\n"
                      + '10 FORCED_SWITCH_W'+"\n"
                      + '11 LOCKOUT'+"\n"
                      + '12 EXERCISE_NULL'+"\n"
                      + '13 EXERCISE_NORMAL'+"\n"
                      + '14 NOT_READY'+"\n"
                      + '15 DO_NOT_REVERT'+"\n"
                      + '16 SIGNAL_FAIL_P with work and protection both failed'+"\n"
                      + '17 not finish MANUAL_SWITCH'+"\n"
                      + '18 not finish MANUAL_SWITCH_W'+"\n"
                      + '19 not finish SIGNAL_FAIL_W'+"\n"
                      + '20 not finish SIGNAL_FAIL_P'+"\n"
                      + '21 not finish SIGNAL_DEGR_W'+"\n"
                      + '22 not finish SIGNAL_DEGR_P'+"\n"
                      + '23 not finish FORCED_SWITCH'+"\n"
                      + '24 not finish FORCED_SWITCH_W'+"\n"
                      + '25 not finish LOCKOUT'+"\n"
                      + '26 not finish EXERCISE_NULL'+"\n"
                      + '27 not finish EXERCISE_NORMAL'+"\n"
                      + '28 REVERSE_REQUEST_NULL'+"\n"
                      + '29 REVERSE_REQUEST_NORMAL'
                        ;
            type uint8 ;
          }
        }
        ncd:revise-date 2019-06-21 ;
      }
      container port-group-flexe-subs {
        description 'The state information of flexe-subclent port group aps.'
                    ;
        list flexe-sub {
          description 'The state information of flexe-subclent port group APS.'
                      ;
          key pg-index ;
          leaf pg-index {
            description 'APS session ID of port group.'
                        ;
            type uint32 {
              range 1..65535 {
                description 'Group ID.'
                            ;
              }
            }
          }
          leaf protect-status {
            description 'Protect status of port group APS:'+"\n"
                      + '0 NO_REQUEST_NULL'+"\n"
                      + '1 NO_REQUEST_NORMAL'+"\n"
                      + '2 MANUAL_SWITCH'+"\n"
                      + '3 MANUAL_SWITCH_W '+"\n"
                      + '4 SIGNAL_FAIL_W'+"\n"
                      + '5 SIGNAL_FAIL_P'+"\n"
                      + '6 SIGNAL_DEGR_W'+"\n"
                      + '7 SIGNAL_DEGR_P'+"\n"
                      + '8 WAIT_TO_RESTORE'+"\n"
                      + '9 FORCED_SWITCH'+"\n"
                      + '10 FORCED_SWITCH_W'+"\n"
                      + '11 LOCKOUT'+"\n"
                      + '12 EXERCISE_NULL'+"\n"
                      + '13 EXERCISE_NORMAL'+"\n"
                      + '14 NOT_READY'+"\n"
                      + '15 DO_NOT_REVERT'+"\n"
                      + '16 SIGNAL_FAIL_P with work and protection both failed'+"\n"
                      + '17 not finish MANUAL_SWITCH'+"\n"
                      + '18 not finish MANUAL_SWITCH_W'+"\n"
                      + '19 not finish SIGNAL_FAIL_W'+"\n"
                      + '20 not finish SIGNAL_FAIL_P'+"\n"
                      + '21 not finish SIGNAL_DEGR_W'+"\n"
                      + '22 not finish SIGNAL_DEGR_P'+"\n"
                      + '23 not finish FORCED_SWITCH'+"\n"
                      + '24 not finish FORCED_SWITCH_W'+"\n"
                      + '25 not finish LOCKOUT'+"\n"
                      + '26 not finish EXERCISE_NULL'+"\n"
                      + '27 not finish EXERCISE_NORMAL'+"\n"
                      + '28 REVERSE_REQUEST_NULL'+"\n"
                      + '29 REVERSE_REQUEST_NORMAL'
                        ;
            type uint8 ;
          }
        }
        ncd:revise-date 2020-08-19 ;
      }
    }
  }
}
