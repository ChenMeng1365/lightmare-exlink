module zxr10-ipflow-dev-t8k {
  namespace 'http://www.zte.com.cn/zxr10/netconf/schema/rosng/ipflow-dev-t8k'
            ;
  prefix ipflow-dev-t8k ;
  yang-version 1 ;
  import zxr10-ipflow {
    prefix ipflow ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'Mse project deviation function.'
              ;
  revision 2020-02-08 {
    description "T8K project deviation function.
\nT8K does not support some ti"
              + "me-deterministic sampling fields in record,such as samplingTim"
              + "eInterval and samplingTimeSpace,and also doesn't support time-"
              + "deterministic sampling mode."
                ;
  }
  deviation '/ipflow:configuration/ipflow:ipflow/ipflow:samplers/ipflow:sampler'
          + '/ipflow:mode/ipflow:time-deterministic'
            {
    description 'Can not support time-deterministic sampling method.'
                ;
    deviate not-supported ;
  }
  deviation '/ipflow:configuration/ipflow:ipflow/ipflow:records/ipflow:record/i'
          + 'pflow:common-fields/ipflow:common-field/ipflow:field-type'
            {
    deviate replace {
      type enumeration {
        enum protocolIdentifier {
          value 4 ;
        }
        enum ipClassOfService {
          value 5 ;
        }
        enum tcpControlBits {
          value 6 ;
        }
        enum sourceTransportPort {
          value 7 ;
        }
        enum sourceIPv4Address {
          value 8 ;
        }
        enum sourceIPv4PrefixLength {
          value 9 ;
        }
        enum ingressInterface {
          value 10 ;
        }
        enum destinationTransportPort {
          value 11 ;
        }
        enum destinationIPv4Address {
          value 12 ;
        }
        enum destinationIPv4PrefixLength {
          value 13 ;
        }
        enum egressInterface {
          value 14 ;
        }
        enum ipNextHopIPv4Address {
          value 15 ;
        }
        enum bgpSourceAsNumber {
          value 16 ;
        }
        enum bgpDestinationAsNumber {
          value 17 ;
        }
        enum bgpNextHopIPv4Address {
          value 18 ;
        }
        enum sourceIPv6Address {
          value 27 ;
        }
        enum destinationIPv6Address {
          value 28 ;
        }
        enum sourceIPv6PrefixLength {
          value 29 ;
        }
        enum destinationIPv6PrefixLength {
          value 30 ;
        }
        enum flowLabelIPv6 {
          value 31 ;
        }
        enum samplingInverval {
          value 34 ;
        }
        enum sourceMacAddress {
          value 56 ;
        }
        enum destinationMacAddress {
          value 57 ;
        }
        enum ipVersion {
          value 60 ;
        }
        enum flowDirection {
          value 61 ;
        }
        enum ipNextHopIPv6Address {
          value 62 ;
        }
        enum bgpNextHopIPv6Address {
          value 63 ;
        }
        enum mplsTopLabelStackSection {
          value 70 ;
        }
        enum mplsLabelStackSection2 {
          value 71 ;
        }
        enum mplsLableStackSection3 {
          value 72 ;
        }
        enum mplsLableStackSection4 {
          value 73 ;
        }
        enum mplsLableStackSection5 {
          value 74 ;
        }
        enum bgpNextAdjacentAsNumber {
          value 128 ;
        }
        enum bgpPrevAdjacentAsNumber {
          value 129 ;
        }
        enum icmpTypeIPv4 {
          value 176 ;
        }
        enum icmpCodeIPv4 {
          value 177 ;
        }
        enum icmpTypeIPv6 {
          value 178 ;
        }
        enum icmpCodeIPv6 {
          value 179 ;
        }
        enum samplingAlgorithm {
          value 304 ;
        }
        enum samplingRandomSize {
          value 309 ;
        }
        enum samplingRandomPopulation {
          value 310 ;
        }
      }
    }
  }
}
