module zxr10-flexe-oam {
  namespace 'http://www.zte.com.cn/zxr10/netconf/schema/rosng/flexe-oam'
            ;
  prefix flexe-oam ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2020-08-25 {
    description '1.Add configuration/flexe-oam/megs/meg/meg-type/mep/mep/subcli'
              + 'ent-period.'+"\n"
              + '1.Add feature subclient-period which is available for PTN6100,'
              + 'PTN6700 and PTN65V5 product.'
                ;
  }
  revision 2019-07-30 {
    description '1.Add feature sd-propagate which is available for PTN6100,PTN6'
              + '700 and PTN65V5 product.'+"\n"
              + '2.Add configuration/flexe-oam/megs/meg/meg-type/mep/mep/sd-pro'
              + 'pagate.'
                ;
  }
  revision 2019-04-16 {
    description '1.Add feature cs-type which is available for PTN6100 product.'+"\n"
              + '2.Add configuration/flexe-oam/megs/meg/meg-type/mep/mep/cs-typ'
              + 'e.'
                ;
  }
  revision 2019-04-02 {
    description '1 Modify range for configuration/flexe-oam/megs/meg/meg-type/m'
              + 'ep/mep/local-mep'+"\n"
              + '2 Modify range for configuration/flexe-oam/megs/meg/meg-type/m'
              + 'ep/mep/peer-mep'
                ;
  }
  revision 2019-02-20 {
    description '1 Modify range for configuration/flexe-oam/megs/meg/meg-type/m'
              + 'ep/mep/loss-threshold.'+"\n"
              + '2 Add configuration/flexe-oam/megs/meg/meg-type/mep/mep/loss-m'
              + 'antissa.'+"\n"
              + '3 Add configuration/flexe-oam/megs/meg/meg-type/mep/mep/exc-ma'
              + 'ntissa.'+"\n"
              + '4 Add configuration/flexe-oam/megs/meg/meg-type/mep/mep/exc-th'
              + 'reshold.'+"\n"
              + '5 Add configuration/flexe-oam/megs/meg/meg-type/mip/mip/loss-m'
              + 'antissa.'+"\n"
              + '6 Add configuration/flexe-oam/megs/meg/meg-type/mip/mip/loss-t'
              + 'hreshold.'+"\n"
              + '7 Add configuration/flexe-oam/megs/meg/meg-type/mip/mip/exc-ma'
              + 'ntissa.'+"\n"
              + '8 Add configuration/flexe-oam/megs/meg/meg-type/mip/mip/exc-th'
              + 'reshold.'
                ;
  }
  revision 2019-01-17 {
    description '1.Add feature cc-bip-status which is available for PTN6100,PTN'
              + '6700 and PTN65V5 product.'+"\n"
              + '2.Add an enumeration value auto for configuration/flexe-oam/me'
              + 'gs/meg/mep/block-period and configuration/flexe-oam/megs/meg/m'
              + 'ip/block-period.'+"\n"
              + '3.Add configuration/flexe-oam/megs/meg/mep/cc-bip and configur'
              + 'ation/flexe-oam/megs/meg/mip/cc-bip.'
                ;
  }
  revision 2018-07-17 {
    description 'Initial version.'
                ;
  }
  feature sequence-number {
    description 'The fixed sequence number of base block.'
                ;
  }
  feature cc-bip-status {
    description 'The switch for turning on or off the CC and BIP function(defau'
              + 'lt:enable).'
                ;
  }
  feature cs-type {
    description 'The test type of CS function.'
                ;
  }
  feature sd-propagate {
    description 'The switch for turning on or off the SD propagate function(def'
              + 'ault:disable).'
                ;
  }
  feature subclient_period {
    description 'The subclient OAM period.'
                ;
  }
  typedef mep-type {
    type enumeration {
      enum source {
        value 1 ;
        description 'Source MEP.'
                    ;
      }
      enum destination {
        value 2 ;
        description 'Destination MEP.'
                    ;
      }
      enum bidirectional {
        value 3 ;
        description 'Bidirection MEP.'
                    ;
      }
    }
    description 'The type of MEP, including source MEP, destination MEP and bid'
              + 'irectional MEP.'
                ;
  }
  container configuration {
    description 'Configuration model Info.'
                ;
    container flexe-oam {
      description 'FlexE OAM megs configuration.'
                  ;
      container global {
        description 'Configure global Info of FlexE OAM.'
                    ;
        leaf oam-switch {
          description 'The switch for turning on or off FlexE OAM function(defa'
                    + 'ult:enable).'
                      ;
          type enumeration {
            enum disable {
              value 0 ;
              description 'Turn off FlexE OAM function.'
                          ;
            }
            enum enable {
              value 1 ;
              description 'Turn on FlexE OAM function.'
                          ;
            }
          }
          default enable ;
        }
        leaf rdi-to-sf-switch {
          description 'The switch for turning on or off FlexE OAM RDI transform'
                    + ' to sf function(default:enable).'
                      ;
          type enumeration {
            enum disable {
              value 0 ;
              description 'Turn off FlexE OAM RDI transform to sf function.'
                          ;
            }
            enum enable {
              value 1 ;
              description 'Turn on FlexE OAM RDI transform to sf function.'
                          ;
            }
          }
          default enable ;
        }
      }
      container megs {
        description 'Configure FlexE OAM megs.'
                    ;
        list meg {
          description 'Configure FlexE OAM megs.'
                      ;
          key meg-index ;
          leaf meg-index {
            description 'Meg index,ranges from 1 to 65535.'
                        ;
            type uint16 {
              range 1..65535 {
                description 'The value of meg index.'
                            ;
              }
            }
          }
          leaf ifname {
            description 'The FlexE client interface binded by OAM.'
                        ;
            type ncd:ifname {
              length 1..31 {
                description 'The range of interface name length.'
                            ;
              }
            }
            mandatory true ;
          }
          choice meg-type {
            description 'Configure MEP or MIP parameters of MEG.'
                        ;
            case mep {
              description 'MEP parameters.'
                          ;
              container mep {
                description 'MEP parameters.'
                            ;
                leaf local-mep {
                  description 'The local MEP.'
                              ;
                  type string {
                    length 1..15 {
                      description 'The string length ranges from 1 to 15.'
                                  ;
                    }
                  }
                }
                leaf local-mep-type {
                  description 'The type of local MEP, including source MEP, des'
                            + 'tination MEP and bidirectional MEP(default:bidir'
                            + 'ectional MEP).'
                              ;
                  type mep-type ;
                  default bidirectional ;
                }
                leaf peer-mep {
                  description 'The peer MEP.'
                              ;
                  type string {
                    length 1..15 {
                      description 'The string length ranges from 1 to 15.'
                                  ;
                    }
                  }
                }
                leaf base-block {
                  description 'The switch for turning on or off base block func'
                            + 'tion(default:disable).'
                              ;
                  type enumeration {
                    enum disable {
                      value 0 ;
                      description 'Disable base block.'
                                  ;
                    }
                    enum enable {
                      value 1 ;
                      description 'Enable base block.'
                                  ;
                    }
                  }
                  default disable ;
                }
                leaf block-period {
                  description 'The base block period,including 16k,32k,64k,512k'
                            + ' and auto(default:16k).'
                              ;
                  type enumeration {
                    enum 16k {
                      value 1 ;
                      description 'The block period is 16k.'
                                  ;
                    }
                    enum 32k {
                      value 5 ;
                      description 'The block period is 32k.'
                                  ;
                    }
                    enum 64k {
                      value 2 ;
                      description 'The block period is 64k.'
                                  ;
                    }
                    enum 512k {
                      value 4 ;
                      description 'The block period is 512k.'
                                  ;
                    }
                    enum auto {
                      value 6 ;
                      description 'The block period is auto.'
                                  ;
                    }
                  }
                  default 16k ;
                }
                leaf bip-check {
                  description 'Include or exclude OAM block in BIP check (defau'
                            + 'lt:include).'
                              ;
                  type enumeration {
                    enum include {
                      value 1 ;
                      description 'Include OAM in BIP check.'
                                  ;
                    }
                    enum exclude {
                      value 0 ;
                      description 'Exclude OAM in BIP check.'
                                  ;
                    }
                  }
                  default include ;
                }
                leaf circle-sequence {
                  description 'The switch for turning on or off circle sequence'
                            + ' function in the base block(default:enable).'
                              ;
                  type enumeration {
                    enum enable {
                      value 1 ;
                      description 'Enable the function of circle sequence in th'
                                + 'e base code block'
                                  ;
                    }
                    enum disable {
                      value 0 ;
                      description 'Disable the function of circle sequence in t'
                                + 'he base code block'
                                  ;
                    }
                  }
                  default enable ;
                }
                leaf cv {
                  description 'The switch for turning on or off the CV function'
                            + '(default:disable).'
                              ;
                  type enumeration {
                    enum enable {
                      value 1 ;
                      description 'Enable the CV function.'
                                  ;
                    }
                    enum disable {
                      value 0 ;
                      description 'Disable the CV function.'
                                  ;
                    }
                  }
                  default disable ;
                }
                leaf cv-period {
                  description 'The period of sending packets in CV function(def'
                            + 'ault:10s).'
                              ;
                  type enumeration {
                    enum 1s {
                      value 1 ;
                      description 'Packet send period:1s(default:10s)'
                                  ;
                    }
                    enum 10s {
                      value 2 ;
                      description 'Packet send period:10s(default:10s)'
                                  ;
                    }
                    enum 1min {
                      value 3 ;
                      description 'Packet send period:1min(default:10s)'
                                  ;
                    }
                  }
                  default 10s ;
                }
                leaf cs {
                  description 'The switch for turning on or off the CS function'
                            + '(default:disable).'
                              ;
                  type enumeration {
                    enum enable {
                      value 1 ;
                      description 'Enable the CS function(default:disable).'
                                  ;
                    }
                    enum disable {
                      value 0 ;
                      description 'Disable the CS function(default:disable).'
                                  ;
                    }
                  }
                  default disable ;
                }
                leaf cs-period {
                  description 'The period of sending packets in CS function(def'
                            + 'ault:10s).'
                              ;
                  type enumeration {
                    enum 1s {
                      value 1 ;
                      description 'Packet send period:1s(default:10s)'
                                  ;
                    }
                    enum 10s {
                      value 2 ;
                      description 'Packet send period:10s(default:10s)'
                                  ;
                    }
                    enum 1min {
                      value 3 ;
                      description 'Packet send period:1min(default:10s)'
                                  ;
                    }
                  }
                  default 10s ;
                }
                leaf loss-threshold {
                  description 'The exponent of the packet loss threshold(defaul'
                            + 't:9).'
                              ;
                  type uint8 {
                    range 9..12 {
                      description 'This parameter ranges from 9 to 12(default:9'
                                + ').'
                                  ;
                    }
                  }
                  default 9 ;
                }
                leaf sequence-number {
                  // if-feature sequence-number ;
                  description 'The fixed sequence number of base block that ran'
                            + 'ging from 0 to 15(default:0).'
                              ;
                  type uint8 {
                    range 0..15 {
                      description 'The fixed sequence number of base block rang'
                                + 'ing from 0 to 15(default:0)'
                                  ;
                    }
                  }
                  default 0 ;
                }
                leaf cc-bip {
                  // if-feature cc-bip-status ;
                  description 'The switch for turning on or off the CC and BIP '
                            + 'function(default:enable).'
                              ;
                  type enumeration {
                    enum disable {
                      value 0 ;
                      description 'Disable the CC and BIP function(default:enab'
                                + 'le).'
                                  ;
                    }
                    enum enable {
                      value 1 ;
                      description 'Enable the CC and BIP function(default:enabl'
                                + 'e).'
                                  ;
                    }
                  }
                  default enable ;
                  ncd:revise-date 2019-01-17 ;
                }
                leaf loss-mantissa {
                  description 'The mantissa of the packet loss threshold(defaul'
                            + 't:1).'
                              ;
                  type uint8 {
                    range 1..9 {
                      description 'This parameter ranges from 1 to 9(default:1).'
                                  ;
                    }
                  }
                  default 1 ;
                  ncd:revise-date 2019-02-20 ;
                }
                leaf exc-mantissa {
                  description 'The mantissa of the packet EXC threshold(default'
                            + ':1).'
                              ;
                  type uint8 {
                    range 1..9 {
                      description 'This parameter ranges from 1 to 9(default:1).'
                                  ;
                    }
                  }
                  default 1 ;
                  ncd:revise-date 2019-02-20 ;
                }
                leaf exc-threshold {
                  description 'The exponent of the packet EXC threshold(default'
                            + ':7).'
                              ;
                  type uint8 {
                    range 7..8 {
                      description 'This parameter ranges from 7 to 8(default:7).'
                                  ;
                    }
                  }
                  default 7 ;
                  ncd:revise-date 2019-02-20 ;
                }
                leaf cs-type {
                  // if-feature cs-type ;
                  description 'The test type of CS function(default:unequipped).'
                              ;
                  type enumeration {
                    enum unequipped {
                      value 1 ;
                      description 'The CS type is signal unequipped(default:une'
                                + 'quipped).'
                                  ;
                    }
                    enum eth {
                      value 2 ;
                      description 'The CS type is ETH service(default:unequippe'
                                + 'd).'
                                  ;
                    }
                    enum sdh {
                      value 3 ;
                      description 'The CS type is SDH service(default:unequippe'
                                + 'd).'
                                  ;
                    }
                    enum fc {
                      value 4 ;
                      description 'The CS type is FC service(default:unequipped'
                                + ').'
                                  ;
                    }
                    enum cpri {
                      value 5 ;
                      description 'The CS type is CPRI service(default:unequipp'
                                + 'ed).'
                                  ;
                    }
                  }
                  default unequipped ;
                  ncd:revise-date 2019-04-16 ;
                }
                leaf sd-propagate {
                  // if-feature sd-propagate ;
                  description 'The switch for turning on or off the SD propagat'
                            + 'e function(default:disable).'
                              ;
                  type enumeration {
                    enum enable {
                      value 1 ;
                      description 'Enable the SD propagate function(default:dis'
                                + 'able).'
                                  ;
                    }
                    enum disable {
                      value 0 ;
                      description 'Disable the SD propagate function(default:di'
                                + 'sable).'
                                  ;
                    }
                  }
                  default disable ;
                  ncd:revise-date 2019-07-30 ;
                }
                leaf subclient-period {
                  // if-feature subclient_period ;
                  description 'The subclient OAM period.'
                              ;
                  type enumeration {
                    enum auto {
                      value 1 ;
                      description 'The subclient OAM period is auto.'
                                  ;
                    }
                  }
                  default auto ;
                  ncd:revise-date 2020-08-25 ;
                }
              }
            }
            case mip {
              description 'MIP parameters.'
                          ;
              container mip {
                leaf base-block {
                  description 'The switch for turning on or off base block func'
                            + 'tion(default:disable).'
                              ;
                  type enumeration {
                    enum disable {
                      value 0 ;
                      description 'Disable base block.'
                                  ;
                    }
                    enum enable {
                      value 1 ;
                      description 'Enable base block.'
                                  ;
                    }
                  }
                  default disable ;
                }
                leaf block-period {
                  description 'The base block period,including 16k,32k,64k,512k'
                            + ' and auto(default:16k).'
                              ;
                  type enumeration {
                    enum 16k {
                      value 1 ;
                      description 'The block period is 16k.'
                                  ;
                    }
                    enum 32k {
                      value 5 ;
                      description 'The block period is 32k.'
                                  ;
                    }
                    enum 64k {
                      value 2 ;
                      description 'The block period is 64k.'
                                  ;
                    }
                    enum 512k {
                      value 4 ;
                      description 'The block period is 512k.'
                                  ;
                    }
                    enum auto {
                      value 6 ;
                      description 'The block period is auto.'
                                  ;
                    }
                  }
                  default 16k ;
                }
                leaf bip-check {
                  description 'Include or exclude OAM block in BIP check (defau'
                            + 'lt:include).'
                              ;
                  type enumeration {
                    enum include {
                      value 1 ;
                      description 'Include OAM in BIP check.'
                                  ;
                    }
                    enum exclude {
                      value 0 ;
                      description 'Exclude OAM in BIP check.'
                                  ;
                    }
                  }
                  default include ;
                }
                leaf circle-sequence {
                  description 'The switch for turning on or off circle sequence'
                            + ' function in the base block(default:enable).'
                              ;
                  type enumeration {
                    enum enable {
                      value 1 ;
                      description 'Enable the function of circle sequence in th'
                                + 'e base code block'
                                  ;
                    }
                    enum disable {
                      value 0 ;
                      description 'Disable the function of circle sequence in t'
                                + 'he base code block'
                                  ;
                    }
                  }
                  default enable ;
                }
                leaf sequence-number {
                  // if-feature sequence-number ;
                  description 'The fixed sequence number of base block that ran'
                            + 'ging from 0 to 15(default:0).'
                              ;
                  type uint8 {
                    range 0..15 {
                      description 'The fixed sequence number of base block rang'
                                + 'ing from 0 to 15(default:0)'
                                  ;
                    }
                  }
                  default 0 ;
                }
                leaf cc-bip {
                  // if-feature cc-bip-status ;
                  description 'The switch for turning on or off the CC and BIP '
                            + 'function(default:enable).'
                              ;
                  type enumeration {
                    enum disable {
                      value 0 ;
                      description 'Disable the CC and BIP function(default:enab'
                                + 'le).'
                                  ;
                    }
                    enum enable {
                      value 1 ;
                      description 'Enable the CC and BIP function(default:enabl'
                                + 'e).'
                                  ;
                    }
                  }
                  default enable ;
                  ncd:revise-date 2019-01-17 ;
                }
                leaf loss-mantissa {
                  description 'The mantissa of the packet loss threshold(defaul'
                            + 't:1).'
                              ;
                  type uint8 {
                    range 1..9 {
                      description 'This parameter ranges from 1 to 9(default:1).'
                                  ;
                    }
                  }
                  default 1 ;
                  ncd:revise-date 2019-02-20 ;
                }
                leaf loss-threshold {
                  description 'The exponent of the packet loss threshold(defaul'
                            + 't:9).'
                              ;
                  type uint8 {
                    range 9..12 {
                      description 'This parameter ranges from 9 to 12(default:9'
                                + ').'
                                  ;
                    }
                  }
                  default 9 ;
                  ncd:revise-date 2019-02-20 ;
                }
                leaf exc-mantissa {
                  description 'The mantissa of the packet EXC threshold(default'
                            + ':1).'
                              ;
                  type uint8 {
                    range 1..9 {
                      description 'This parameter ranges from 1 to 9(default:1).'
                                  ;
                    }
                  }
                  default 1 ;
                  ncd:revise-date 2019-02-20 ;
                }
                leaf exc-threshold {
                  description 'The exponent of the packet EXC threshold(default'
                            + ':7).'
                              ;
                  type uint8 {
                    range 7..8 {
                      description 'This parameter ranges from 7 to 8(default:7).'
                                  ;
                    }
                  }
                  default 7 ;
                  ncd:revise-date 2019-02-20 ;
                }
                leaf subclient-period {
                  // if-feature subclient_period ;
                  description 'The subclient OAM period.'
                              ;
                  type enumeration {
                    enum auto {
                      value 1 ;
                      description 'The subclient OAM period is auto.'
                                  ;
                    }
                  }
                  default auto ;
                  ncd:revise-date 2020-08-25 ;
                }
              }
            }
          }
        }
      }
    }
  }
  container operation {
    config false ;
    container flexe-oam {
      container dms {
        list dm {
          description 'On demand dm function.'
                      ;
          key index ;
          leaf index {
            description 'OAM index.'
                        ;
            type uint16 {
              range 1..65535 {
                description 'This oam index ranges from 1 to 65535.'
                            ;
              }
            }
            mandatory true ;
          }
          choice dm-switch {
            description 'The switch for enable or disable the DM function(defau'
                      + 'lt:disable).'
                        ;
            case enable {
              description 'Turn on the DM function.'
                          ;
              leaf enable {
                description 'Turn on the DM function.'
                            ;
                type empty ;
              }
              leaf type {
                description 'The type of DM function.'
                            ;
                type enumeration {
                  enum one-way {
                    value 1 ;
                    description 'One-way on demand dm type'
                                ;
                  }
                  enum two-way {
                    value 2 ;
                    description 'Twao-way on demand dm type'
                                ;
                  }
                }
                mandatory true ;
              }
              leaf period {
                description 'The sending period of on-demand DM packets(default'
                          + ':10s).'
                            ;
                type enumeration {
                  enum 1s {
                    value 1 ;
                    description 'Packet send period:1s(default:10s)'
                                ;
                  }
                  enum 10s {
                    value 2 ;
                    description 'Packet send period:10s(default:10s)'
                                ;
                  }
                  enum 1min {
                    value 3 ;
                    description 'Packet send period:1min(default:10s)'
                                ;
                  }
                }
                default 10s ;
              }
              leaf send-time {
                description 'Duration time of on-demand DM(default:600s).'
                            ;
                type uint32 {
                  range 300..86400 {
                    description 'This parameter ranges from 300s to 86400s(defa'
                              + 'ult:600s).'
                                ;
                  }
                }
                units s ;
                default 600 ;
              }
              leaf report-interval {
                description "The report interval of the DM test result,the defa"
                          + "ult value is 0s which means don't upsend results u"
                          + "ntil the test stopped."
                            ;
                type uint32 {
                  range 0..86400 {
                    description 'This parameter ranges from 0 to 86400(default:'
                              + '0).'
                                ;
                  }
                }
                units s ;
                default 0 ;
              }
              leaf serial-number {
                description 'The serial number of DM.'
                            ;
                type ncd:terminal-based-uint32 ;
              }
            }
            case disable {
              description 'Turn off the DM function.'
                          ;
              leaf disable {
                description 'Turn off the DM function.'
                            ;
                type empty ;
              }
            }
          }
        }
      }
    }
  }
  notification dm-event {
    list dm-result {
      description 'The test result is reported periodically according to the co'
                + 'nfigured reporting interval in the DM test.'
                  ;
      key index ;
      leaf index {
        config false ;
        description 'OAM index.'
                    ;
        type uint16 {
          range 1..65535 {
            description 'This oam index ranges from 1 to 65535.'
                        ;
          }
        }
        mandatory true ;
      }
      leaf delay {
        description 'The delay data of DM test(units: ns).'
                    ;
        type uint64 ;
        units ns ;
      }
      leaf delay-variation {
        description 'The delay variation of DM test(units: ns).'
                    ;
        type uint64 ;
        units ns ;
      }
      leaf average-delay {
        description 'The average delay of DM test(units: ns).'
                    ;
        type uint64 ;
        units ns ;
      }
      leaf average-delay-variation {
        description 'The average delay variation of DM test(units: ns).'
                    ;
        type uint64 ;
        units ns ;
      }
      leaf min-delay {
        description 'The minimal delay of DM test(units: ns).'
                    ;
        type uint64 ;
        units ns ;
      }
      leaf max-delay {
        description 'The maximal delay of DM test(units: ns).'
                    ;
        type uint64 ;
        units ns ;
      }
      leaf min-delay-variation {
        description 'The manimal delay of DM test(units: ns).'
                    ;
        type uint64 ;
        units ns ;
      }
      leaf max-delay-variation {
        description 'The maximal delay of DM test(units: ns).'
                    ;
        type uint64 ;
        units ns ;
      }
    }
  }
}
