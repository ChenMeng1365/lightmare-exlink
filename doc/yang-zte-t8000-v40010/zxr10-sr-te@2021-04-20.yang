module zxr10-sr-te {
  namespace 'http://www.zte.com.cn/zxr10/netconf/schema/rosng/sr-te'
            ;
  prefix sr ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf model for sr-te.'
              ;
  revision 2021-04-20 {
    description '1.Add the leaf configuration/segment-routing/traffic-eng/stati'
              + 'c-sr/static-tunnel/color.'
                ;
  }
  revision 2021-03-17 {
    description '1.Add the leaf /configuration/segment-routing/traffic-eng/glob'
              + 'al-config/policy-sl-sbfd/echo'+"\n"
              + '2.Add the leaf /configuration/segment-routing/traffic-eng/sr-p'
              + 'olicy/policy/segment-list-sbfd/sbfd-conf/enable/echo'+"\n"
              + '3.Add the container /configuration/segment-routing/traffic-eng'
              + '/sr-policy/policy/candidate-path/cp/segment-list/sl/srv6-bindi'
              + 'ng-sid'+"\n"
              + '4.Add the container /configuration/segment-routing/traffic-eng'
              + '/sr-policy/policy/candidate-path/cp/segment-list/sl/reverse-pa'
              + 'th'
                ;
  }
  revision 2021-03-16 {
    description '1.Add enumeration value configuration/segment-routing/traffic-'
              + 'eng/load-sharing.'+"\n"
              + '2.Add enumeration value configuration/segment-routing/traffic-'
              + 'eng/sr-policy/policy/load-sharing.'
                ;
  }
  revision 2021-03-01 {
    description '1.Add value configuration/segment-routing/traffic-eng/color-te'
              + 'mplates/color-template/policy/path-setup-type.'+"\n"
              + '2.Add container /configuration/segment-routing/traffic-eng/sr-'
              + 'policy/policy/candidate-path/cp/cspf-force-igp.'+"\n"
              + '3.Add container /configuration/segment-routing/traffic-eng/col'
              + 'or-templates/color-template/policy/candidate-path/cp/cspf-forc'
              + 'e-igp.'
                ;
  }
  revision 2021-01-21 {
    description '1.Add leaf /configuration/segment-routing/traffic-eng/sr-polic'
              + 'y/policy/path-verification'+"\n"
              + '2.Add leaf /configuration/segment-routing/traffic-eng/path-ver'
              + 'ification'+"\n"
              + '3.Add leaf configuration/segment-routing/traffic-eng/color-tem'
              + 'plates/color-template/path-verification'+"\n"
              + '4.Add the leaf configuration/segment-routing/traffic-eng/sr-tu'
              + 'nnel/tunnel/path-verification'+"\n"
              + '5.Add container /configuration/segment-routing/traffic-eng/sr-'
              + 'policy/policy/candidate-path/cp/pce-delegate.'+"\n"
              + '6.Add container /configuration/segment-routing/traffic-eng/col'
              + 'or-templates/color-template/policy/candidate-path/cp/pce-deleg'
              + 'ate.'+"\n"
              + '7.Add type value /configuration/segment-routing/traffic-eng/sr'
              + '-policy/policy/candidate-path/cp/metric-type.'+"\n"
              + '8.Add type value /configuration/segment-routing/traffic-eng/sr'
              + '-tunnel/tunnel/metric-type.'+"\n"
              + '9.Add leaf configuration/segment-routing/traffic-eng/sr-policy'
              + '/policy/sid-algo.'+"\n"
              + '10.Add the leaf configuration/segment-routing/traffic-eng/stat'
              + 'ic-sr/static-tunnel/path-verification.'
                ;
  }
  revision 2021-01-13 {
    description '1.Modify the default value /configuration/segment-routing/traf'
              + 'fic-eng/path-uninterrupt-time.'
                ;
  }
  revision 2020-12-21 {
    description '1.Modify the container /configuration/segment-routing/traffic-'
              + 'eng/sr-policy/policy/ipv6-diffserv-mode.'
                ;
  }
  revision 2020-12-16 {
    description '1.Add leaf configuration/segment-routing/traffic-eng/color-tem'
              + 'plates/color-template/template-type'+"\n"
              + '2.Add container configuration/segment-routing/traffic-eng/colo'
              + 'r-templates/color-template/policy'
                ;
  }
  revision 2020-12-03 {
    description '1.Add the leaf /state/sr-policy/traffic-statistics/policy/e-bi'
              + 't-rate.'+"\n"
              + '2.Add the leaf /state/sr-policy/traffic-statistics/policy/e-pa'
              + 'cket-rate.'
                ;
  }
  revision 2020-11-27 {
    description '1.Add the choice /configuration/segment-routing/traffic-eng/sr'
              + '-policy/policy/sbfd/sbfd-conf/reverse-path/path-type.'
                ;
  }
  revision 2020-11-23 {
    description 'Add the container /configuration/segment-routing/traffic-eng/s'
              + 'r-policy/policy/ipv6-diffserv-mode.'
                ;
  }
  revision 2020-11-17 {
    description 'Add case /configuration/segment-routing/traffic-eng/sr-policy/'
              + 'policy/srv6-binding-sid/dynamic.'
                ;
  }
  revision 2020-11-13 {
    description '1.Modify the max-elements of /configuration/segment-routing/tr'
              + 'affic-eng/sr-path/name-based.'+"\n"
              + '2.Modify the max-elements of /configuration/segment-routing/tr'
              + 'affic-eng/sr-path/id-based.'+"\n"
              + '3.Modify the max-elements of /configuration/segment-routing/tr'
              + 'affic-eng/srv6-path/name-based.'
                ;
  }
  revision 2020-10-20 {
    description '1.Add the container configuration/segment-routing/traffic-eng/'
              + 'sr-tunnel/tunnel/pce/slave-name.'+"\n"
              + '2.Add the leaf configuration/segment-routing/traffic-eng/sr-tu'
              + 'nnel/tunnel/hsb-enable'
                ;
  }
  revision 2020-10-13 {
    description 'Add leaf /configuration/segment-routing/traffic-eng/global-con'
              + 'fig/cspf-ex-overload'
                ;
  }
  revision 2020-10-07 {
    description '1.Add the container /configuration/segment-routing/traffic-eng'
              + '/global-config/pcep-auto-init'
                ;
  }
  revision 2020-09-27 {
    description '1.Add the choice /configuration/segment-routing/traffic-eng/sr'
              + '-path/name-based/path-paras/path-para/sr-path/sr-path-type/adj'
              + 'acency-ipv6-link-local.'+"\n"
              + '2.Add the choice /configuration/segment-routing/traffic-eng/sr'
              + '-path/id-based/path-paras/path-para/sr-path/sr-path-type/adjac'
              + 'ency-ipv6-link-local.'
                ;
  }
  revision 2020-09-21 {
    description '1.Add leaf /configuration/segment-routing/traffic-eng/sr-tunne'
              + 'l/tunnel/link-limit/srv6-link-limit-num.'
                ;
  }
  revision 2020-09-18 {
    description '1.Add leaf /configuration/segment-routing/traffic-eng/sr-tunne'
              + 'l/tunnel/drop-upon-invalid'
                ;
  }
  revision 2020-09-17 {
    description '1.Add the leaf /configuration/segment-routing/traffic-eng/stat'
              + 'ic-sr/static-tunnel/compress-num.'
                ;
  }
  revision 2020-09-11 {
    description '1.Add leaf state/sr-tunnel/tunnel/v6-ingress-id and v6-egress-'
              + 'id.'+"\n"
              + '2.Add leaf state/sr-tunnel/tunnel-sr-path/sr-path-hop/srv6-sid'
              + ' and v6-node-ip and v6-adj-local-ip and v6-local-id and v6-adj'
              + '-peer-ip and v6-peer-id.'+"\n"
              + '3.Add enumeration value state/sr-tunnel/tunnel-sr-path/sr-path'
              + '-hop/sid-type.'+"\n"
              + '4.Add the notification sr-tunnel/tunnel/v6-ingress-id and v6-e'
              + 'gress-id.'+"\n"
              + '5.Add the notification sr-tunnel/tunnel-path/srv6-sid and v6-n'
              + 'ode-ip and v6-adj-local-ip and v6-local-id and v6-adj-peer-ip '
              + 'and v6-peer-id.'+"\n"
              + '6.Add enumeration value notification sr-tunnel/tunnel-path/sid'
              + '-type.'
                ;
  }
  revision 2020-09-01 {
    description '1.Add the container /state/sr-policy/traffic-statistics.'
                ;
  }
  revision 2020-07-31 {
    description 'Add leaf /configuration/segment-routing/traffic-eng/global-con'
              + 'fig/srv6-locator-name'
                ;
  }
  revision 2020-06-28 {
    description '1.Add leaf /configuration/segment-routing/traffic-eng/sr-polic'
              + 'y/policy/candidate-path/cp/path-type'+"\n"
              + '2.Add leaf /configuration/segment-routing/traffic-eng/sr-polic'
              + 'y/policy/candidate-path/cp/metric-type'+"\n"
              + '3.Add container /configuration/segment-routing/traffic-eng/sr-'
              + 'policy/policy/candidate-path/cp/affinity'
                ;
  }
  revision 2020-06-25 {
    description 'obsolete /configuration/segment-routing/traffic-eng/sr-tunnel/'
              + 'tunnel/srv6-binding-sid/auto'+"\n"
              + 'obsolete /configuration/segment-routing/traffic-eng/sr-policy/'
              + 'policy/srv6-binding-sid/auto'
                ;
  }
  revision 2020-06-06 {
    description '1.Add the container /configuration/segment-routing/traffic-eng'
              + '/sr-policy/policy/sbfd/sbfd-conf/enable/reverse-path'
                ;
  }
  revision 2020-06-01 {
    description '1.Add the container /configuration/segment-routing/traffic-eng'
              + '/policy-group.'
                ;
  }
  revision 2020-05-28 {
    description '1.Add the container configuration/segment-routing/traffic-eng/'
              + 'sr-policy/srv6-binding-sid'+"\n"
              + '2.Add the choice of configuration/segment-routing/traffic-eng/'
              + 'sr-policy/srv6-binding-sid/srv6-bsid-type'+"\n"
              + '3.Add the leaf configuration/segment-routing/traffic-eng/load-'
              + 'sharing.'+"\n"
              + '4.Add the leaf configuration/segment-routing/traffic-eng/sr-po'
              + 'licy/policy/load-sharing.'
                ;
  }
  revision 2020-05-18 {
    description '1.Add the container /configuration/segment-routing/traffic-eng'
              + '/global-config/policy-sbfd'+"\n"
              + '2.Add the container /configuration/segment-routing/traffic-eng'
              + '/sr-policy/policy/sbfd'
                ;
  }
  revision 2020-04-18 {
    description '1.Add the leaf configuration/segment-routing/traffic-eng/path-'
              + 'uninterrupt-time'+"\n"
              + '2.Add the choice of configuration/segment-routing/traffic-eng/'
              + 'sr-tunnel/tunnel/bfd/tunnel-bfd/detect-param'+"\n"
              + '3.Add the choice of configuration/segment-routing/traffic-eng/'
              + 'sr-tunnel/tunnel/sbfd/tunnel-sbfd/detect-param'
                ;
  }
  revision 2020-04-10 {
    description '1.Add the container state/static-sr/static-tunnel.'+"\n"
              + '2.Add the notification static-sr.'
                ;
  }
  revision 2020-04-07 {
    description '1.Add the container /configuration/segment-routing/traffic-eng'
              + '/global-config/policy-sl-sbfd'+"\n"
              + '2.Add the container /configuration/segment-routing/traffic-eng'
              + '/sr-policy/policy/segment-list-sbfd'
                ;
  }
  revision 2020-03-28 {
    description '1.Add the leaf configuration/segment-routing/traffic-eng/sr-tu'
              + 'nnel/tunnel/metric-type'+"\n"
              + '2.Add the leaf configuration/segment-routing/traffic-eng/reopt'
              + 'imize/delay-decrease'
                ;
  }
  revision 2020-03-27 {
    description '1.Add the container configuration/segment-routing/traffic-eng/'
              + 'bpg-ls'
                ;
  }
  revision 2020-03-26 {
    description '1.Add the leaf configuration/segment-routing/traffic-eng/polic'
              + 'y-traffic-statistics.'+"\n"
              + '2.Add the leaf configuration/segment-routing/traffic-eng/sr-po'
              + 'licy/policy/traffic-statistics.'
                ;
  }
  revision 2020-03-19 {
    description '1.Add leaf /configuration/segment-routing/traffic-eng/sr-polic'
              + 'y/policy/hsb-policy'+"\n"
              + '2.Add leaf /configuration/segment-routing/traffic-eng/hsb-poli'
              + 'cy'
                ;
  }
  revision 2020-03-04 {
    description '1. Add container /configuration/segment-routing/traffic-eng/sr'
              + '-tunnel/tunnel/escape-path/sr-path'
                ;
  }
  revision 2020-02-14 {
    description '1.Modify status deprecated configuration/segment-routing/traff'
              + 'ic-eng/sr-tunnel/tunnel/pce-init.'+"\n"
              + '2.Modify status deprecated configuration/segment-routing/traff'
              + 'ic-eng/sr-tunnel/tunnel/pce-control.'+"\n"
              + '3.Add choice configuration/segment-routing/traffic-eng/sr-tunn'
              + 'el/tunnel/pce-type.'
                ;
  }
  revision 2020-02-13 {
    description '1.Add enumeration value in the leaf configuration/segment-rout'
              + 'ing/traffic-eng/flex-algo-define/flex-algo/metric-type'
                ;
  }
  revision 2020-02-06 {
    description '1.Modify leaf /configuration/segment-routing/traffic-eng/tnnl-'
              + 'rate-limit/tunnel/cir.'
                ;
  }
  revision 2019-12-20 {
    description '1.Add the container configuration/segment-routing/traffic-eng/'
              + 'color-maps'+"\n"
              + '2.Add the container configuration/segment-routing/traffic-eng/'
              + 'flex-algo-define'+"\n"
              + '3.Add the leaf configuration/segment-routing/traffic-eng/sr-tu'
              + 'nnel/tunnel/sid-algo'
                ;
  }
  revision 2019-11-01 {
    description '1.Add leaf /configuration/segment-routing/traffic-eng/sr-polic'
              + 'y/policy/path-setup-type'+"\n"
              + '2.Add choice /configuration/segment-routing/traffic-eng/sr-pol'
              + 'icy/policy/candidate-path/cp/segment-list/sl/sl-path-type'+"\n"
              + '3.Increase the maximum of configuration/segment-routing/traffi'
              + 'c-eng/delay/delay_linkup'
                ;
  }
  revision 2019-10-12 {
    description '1. Add container /configuration/segment-routing/traffic-eng/sr'
              + '-tunnel/tunnel/affinity'
                ;
  }
  revision 2019-09-05 {
    description '1.Modify leaf /configuration/segment-routing/traffic-eng/stati'
              + 'c-sr/static-tunnel/triple/ingress-tunnel-id.'
                ;
  }
  revision 2019-08-09 {
    description '1.Add leaf /configuration/segment-routing/traffic-eng/sr-tunne'
              + 'l/tunnel/entropy-label'
                ;
  }
  revision 2019-08-07 {
    description '1.Add the choice of configuration/segment-routing/traffic-eng/'
              + 'sr-tunnel/tunnel/bfd/tunnel-bfd/reverse-path'
                ;
  }
  revision 2019-07-29 {
    description '1.Add leaf sr-tunnel/tunnel-path/adj-local-id'+"\n"
              + '2.Add leaf sr-tunnel/tunnel-path/adj-peer-id'
                ;
  }
  revision 2019-07-19 {
    description '1.Add the container configuration/segment-routing/traffic-eng/'
              + 'sr-tunnel/tunnel/bandwidth.'
                ;
  }
  revision 2019-07-16 {
    description '1.Add node-label-value leaf to /configuration/segment-routing/'
              + 'traffic-eng/sr-path/name-based/path-paras/path-para/sr-path/sr'
              + '-path-type/node'+"\n"
              + '2.Add adjacency-label-value leaf to /configuration/segment-rou'
              + 'ting/traffic-eng/sr-path/name-based/path-paras/path-para/sr-pa'
              + 'th/sr-path-type/adjacency'+"\n"
              + '3.Add node-ipv6-label-value leaf to /configuration/segment-rou'
              + 'ting/traffic-eng/sr-path/name-based/path-paras/path-para/sr-pa'
              + 'th/sr-path-type/node-ipv6'+"\n"
              + '4.Add adjacency-ipv6-label-value leaf to /configuration/segmen'
              + 't-routing/traffic-eng/sr-path/name-based/path-paras/path-para/'
              + 'sr-path/sr-path-type/adjacency-ipv6'+"\n"
              + '5.Add node-label-value leaf to /configuration/segment-routing/'
              + 'traffic-eng/sr-path/id-based/path-paras/path-para/sr-path/sr-p'
              + 'ath-type/node'+"\n"
              + '6.Add adjacency-label-value leaf to /configuration/segment-rou'
              + 'ting/traffic-eng/sr-path/id-based/path-paras/path-para/sr-path'
              + '/sr-path-type/adjacency'+"\n"
              + '7.Add node-ipv6-label-value leaf to /configuration/segment-rou'
              + 'ting/traffic-eng/sr-path/id-based/path-paras/path-para/sr-path'
              + '/sr-path-type/node-ipv6'+"\n"
              + '8.Add adjacency-ipv6-label-value leaf to /configuration/segmen'
              + 't-routing/traffic-eng/sr-path/id-based/path-paras/path-para/sr'
              + '-path/sr-path-type/adjacency-ipv6'
                ;
  }
  revision 2019-07-09 {
    description '1.Add leaf sr-tunnel/tunnel-sr-path/sr-path-hop/state/adj-loca'
              + 'l-id'+"\n"
              + '2.Add leaf sr-tunnel/tunnel-sr-path/sr-path-hop/state/adj-peer'
              + '-id'
                ;
  }
  revision 2019-07-08 {
    description '1.Modify leaf /configuration/segment-routing/traffic-eng/stati'
              + 'c-sr/static-tunnel/role-type/direction-type.'
                ;
  }
  revision 2019-06-22 {
    description '1.Add container /configuration/segment-routing/traffic-eng/sr-'
              + 'policy'
                ;
  }
  revision 2019-06-13 {
    description '1.Add flow-statistics leaf to /configuration/segment-routing/t'
              + 'raffic-eng/sr-tunnel/tunnel'+"\n"
              + '2.Add flow-statistics leaf to /configuration/segment-routing/t'
              + 'raffic-eng/static-sr/static-tunnel'
                ;
  }
  revision 2019-05-22 {
    description '1.Add container configuration/segment-routing/traffic-eng/sr-t'
              + 'unnel/tunnel/sbfd'
                ;
  }
  revision 2019-04-19 {
    description '1.Add container configuration/segment-routing/traffic-eng/glob'
              + 'al-config'+"\n"
              + '2.Add leaf configuration/segment-routing/traffic-eng/global-co'
              + 'nfig/bgp-auto-del-delay-time'
                ;
  }
  revision 2019-03-14 {
    description '1.Modify leaf /configuration/segment-routing/traffic-eng/tnnl-'
              + 'rate-limit/tunnel/cir.'+"\n"
              + '2.Modify leaf /configuration/segment-routing/traffic-eng/tnnl-'
              + 'rate-limit/tunnel/cbs.'+"\n"
              + '3.Modify leaf /configuration/segment-routing/traffic-eng/tnnl-'
              + 'rate-limit/tunnel/pir.'+"\n"
              + '4.Modify leaf /configuration/segment-routing/traffic-eng/tnnl-'
              + 'rate-limit/tunnel/pbs.'
                ;
  }
  revision 2019-02-15 {
    description '1.Add the leaf of /operation/manual-reopt/tunnel-id and  /oper'
              + 'ation/manual-reopt/all.'+"\n"
              + '2.Add container /configuration/segment-routing/traffic-eng/del'
              + 'ay'+"\n"
              + '3.Add container /configuration/segment-routing/traffic-eng/reo'
              + 'ptimize'+"\n"
              + '4.Add leaf /configuration/segment-routing/traffic-eng/sr-tunne'
              + 'l/tunnel/reoptimize'+"\n"
              + '5.Add leaf /configuration/segment-routing/traffic-eng/sr-tunne'
              + 'l/tunnel/reopt-hsb-lsp'
                ;
  }
  revision 2019-01-15 {
    description '1.Add container configuration/segment-routing/traffic-eng/colo'
              + 'r-templates'
                ;
  }
  revision 2019-01-02 {
    description '1.Add ipv6 choice to /configuration/segment-routing/traffic-en'
              + 'g/static-sr/static-tunnel/triple'
                ;
  }
  revision 2018-12-28 {
    description '1.Add pce-control container to /configuration/segment-routing/'
              + 'traffic-eng/static-sr/static-tunnel'
                ;
  }
  revision 2018-12-17 {
    description '1.Add tnnl-rate-limit container to /configuration/segment-rout'
              + 'ing/traffic-eng'
                ;
  }
  revision 2018-11-27 {
    description '1.Modify configuration/segment-routing/traffic-eng/sr-tunnel/t'
              + 'unnel/auto-route/ar-relative-metric'
                ;
  }
  revision 2018-11-23 {
    description '1.Add /configuration/segment-routing/traffic-eng/sr-path/name-'
              + 'based/path-paras/path-para/sr-path/node-ipv6'+"\n"
              + '2.Add /configuration/segment-routing/traffic-eng/sr-path/name-'
              + 'based/path-paras/path-para/sr-path/adjacency-ipv6'+"\n"
              + '3.Add /configuration/segment-routing/traffic-eng/sr-path/id-ba'
              + 'sed/path-paras/path-para/sr-path/node-ipv6'+"\n"
              + '4.Add /configuration/segment-routing/traffic-eng/sr-path/id-ba'
              + 'sed/path-paras/path-para/sr-path/adjacency-ipv6'+"\n"
              + '5.Add /configuration/segment-routing/traffic-eng/sr-tunnel/tun'
              + 'nel/pce-control/pce-control-addr-ipv6'
                ;
  }
  revision 2018-11-19 {
    description '1.Add leaf configuration/segment-routing/traffic-eng/bfd-affec'
              + 't-enable'+"\n"
              + '2.Add leaf configuration/segment-routing/traffic-eng/bfd-creat'
              + 'e-timeout'
                ;
  }
  revision 2018-11-14 {
    description '1.Add track-name leaf to /configuration/segment-routing/traffi'
              + 'c-eng/static-sr'
                ;
  }
  revision 2018-11-02 {
    description '1.Add configuration/segment-routing/traffic-eng/sr-tunnel/tunn'
              + 'el/auto-route/ar-include-ipv6'
                ;
  }
  revision 2018-10-29 {
    description '1.Add configuration/segment-routing/traffic-eng/sr-tunnel/tunn'
              + 'el/bfd/tunnel-bfd/bfd-enable enumeration type of slave'
                ;
  }
  revision 2018-10-15 {
    description '1.Add configuration/segment-routing/traffic-eng/sr-tunnel/tunn'
              + 'el/auto-route'
                ;
  }
  revision 2018-09-25 {
    description 'add /configuration/segment-routing/traffic-eng/policy-class.'
                ;
  }
  revision 2018-08-29 {
    description '1.Add configuration/segment-routing/traffic-eng/sr-tunnel/tunn'
              + 'el/pce-control/pce-control-addr'
                ;
  }
  revision 2018-08-27 {
    description '1.Add configuration/segment-routing/traffic-eng/sr-tunnel/tunn'
              + 'el/escape-path/escape-path-enable'
                ;
  }
  revision 2018-07-02 {
    description '1.Add configuration/segment-routing/traffic-eng/mbb/cleanup-de'
              + 'lay-time'+"\n"
              + '2.Add configuration/segment-routing/traffic-eng/mbb/installaio'
              + 'n-delay-time'
                ;
  }
  revision 2018-05-14 {
    description '1.Add configuration/segment-routing/traffic-eng/srv6-path'+"\n"
              + '2.Add configuration/segment-routing/traffic-eng/sr-tunnel/tunn'
              + 'el/path-setup-type'+"\n"
              + '3.Add configuration/segment-routing/traffic-eng/sr-tunnel/tunn'
              + 'el/color'+"\n"
              + '4.Add configuration/segment-routing/traffic-eng/sr-tunnel/tunn'
              + 'el/destination-ipv6'+"\n"
              + '5.Add configuration/segment-routing/traffic-eng/sr-tunnel/tunn'
              + 'el/srv6-path'+"\n"
              + '6.Add configuration/segment-routing/traffic-eng/sr-tunnel/tunn'
              + 'el/srv6-binding-sid'
                ;
  }
  revision 2018-03-26 {
    description '1.Add activation leaf to /configuration/segment-routing/traffi'
              + 'c-eng/static-sr'+"\n"
              + '2.Add performance-switch leaf to /configuration/segment-routin'
              + 'g/traffic-eng/static-sr'+"\n"
              + '3.Add state/static-sr/resource/tunnel-perf-switch'
                ;
  }
  revision 2018-02-13 {
    description '1.Add configuration/segment-routing/traffic-eng/static-sr'
                ;
  }
  revision 2017-10-25 {
    description '1.Adjust the order of container configuration/segment-routing/'
              + 'traffic-eng/sr-tunnel and configuration/segment-routing/traffi'
              + 'c-eng/sr-path'
                ;
  }
  revision 2017-10-16 {
    description '1.Add configuration/segment-routing/traffic-eng/sr-tunnel/tunn'
              + 'el/bfd/tunnel-bfd/reverse-tunnelid'
                ;
  }
  revision 2017-10-13 {
    description '1.Add configuration/segment-routing/traffic-eng/sr-tunnel/tunn'
              + 'el/activation'
                ;
  }
  revision 2017-09-14 {
    description 'Initial version.'
                ;
  }
  feature static-sr-tunnel-compress-num {
    description 'The number of compressed static SR tunnels.'
                ;
  }
  container state {
    config false ;
    description 'The branch of SR tunnel data model.'
                ;
    container sr-tunnel {
      description 'The SR tunnel information.'
                  ;
      list tunnel {
        description 'The SR tunnel list.'
                    ;
        key tunnel-id ;
        leaf tunnel-id {
          description 'The tunnel ID.'
                      ;
          type uint16 ;
        }
        leaf ingress-id {
          description 'The ingress LSR ID.'
                      ;
          type ncd:ipv4-address ;
        }
        leaf egress-id {
          description 'The egress LSR ID.'
                      ;
          type ncd:ipv4-address ;
        }
        leaf v6-ingress-id {
          description 'The ingress v6 LSR ID.'
                      ;
          type ncd:ipv6-address ;
          ncd:revise-date 2020-09-11 ;
        }
        leaf v6-egress-id {
          description 'The egress v6 LSR ID.'
                      ;
          type ncd:ipv6-address ;
          ncd:revise-date 2020-09-11 ;
        }
        leaf oper-status {
          description 'The operation status of tunnel.'
                      ;
          type enumeration {
            enum unknown {
              value 0 ;
            }
            enum up {
              value 1 ;
            }
            enum down {
              value 2 ;
            }
            enum wtr {
              value 4 ;
            }
          }
        }
        leaf master-lsp-id {
          description 'The master lsp identifier.'
                      ;
          type uint16 ;
        }
        leaf slave-lsp-id {
          description 'The lsp identifier of slave.'
                      ;
          type uint16 ;
        }
        leaf hsb-status {
          description 'The hsb status of tunnel.'
                      ;
          type enumeration {
            enum none {
              value 0 ;
            }
            enum ready {
              value 1 ;
            }
            enum active {
              value 2 ;
            }
          }
        }
        leaf master-splice-label {
          description 'The master splice label.'
                      ;
          type uint32 ;
        }
        leaf slave-splice-label {
          description 'The splice label of slave.'
                      ;
          type uint32 ;
        }
      }
      container tunnel-sr-path {
        description 'The path of segment-routing tunnel LSP.'
                    ;
        list sr-path-hop {
          description 'The hop of segment routing path.'
                      ;
          key 'tunnel-id lsp-role hop-index'
              ;
          leaf tunnel-id {
            description 'The tunnel ID.'
                        ;
            type uint16 ;
          }
          leaf lsp-role {
            description "The lsp role of tunnel,it's behalf of master while the"
                      + " value is 1 ,it's behalf of backup while the value is "
                      + "2."
                        ;
            type enumeration {
              enum master {
                value 1 ;
              }
              enum slave {
                value 2 ;
              }
            }
          }
          leaf hop-index {
            description 'The index of sr-path hop.'
                        ;
            type uint16 ;
          }
          leaf lsp-id {
            description 'The lsp identifier.'
                        ;
            type uint16 ;
          }
          leaf sid-type {
            description 'The sid type.'
                        ;
            type enumeration {
              enum default {
                value 0 ;
              }
              enum node-id-v4 {
                value 1 ;
              }
              enum node-id-v6 {
                value 2 ;
              }
              enum adj-id-v4 {
                value 3 ;
              }
              enum adj-id-v6 {
                value 4 ;
              }
              enum unnum-adj-id-v4 {
                value 5 ;
              }
              enum srv6-sid {
                value 14 ;
              }
              enum srv6-node-id {
                value 18 ;
              }
              enum srv6-adj-id {
                value 19 ;
              }
              enum srv6-link-local {
                value 20 ;
              }
            }
          }
          leaf sid-val {
            description 'The sid value.'
                        ;
            type uint32 ;
          }
          leaf node-ip {
            description 'The node IP.'
                        ;
            type ncd:ipv4-address ;
          }
          leaf adj-local-rid {
            description 'The local router id of adjacency.'
                        ;
            type ncd:ipv4-address ;
          }
          leaf adj-local-ip {
            description 'The local ip of adjacency.'
                        ;
            type ncd:ipv4-address ;
          }
          leaf adj-local-id {
            description 'The local ID of adjacency.'
                        ;
            type uint32 ;
            ncd:revise-date 2019-07-09 ;
          }
          leaf adj-peer-rid {
            description 'The peer router id of adjacency.'
                        ;
            type ncd:ipv4-address ;
          }
          leaf adj-peer-ip {
            description 'The peer ip of adjacency.'
                        ;
            type ncd:ipv4-address ;
          }
          leaf adj-peer-id {
            description 'The peer ID of adjacency.'
                        ;
            type uint32 ;
            ncd:revise-date 2019-07-09 ;
          }
          leaf srv6-sid {
            description 'The SRv6 sid value.'
                        ;
            type ncd:ipv6-address ;
            ncd:revise-date 2020-09-11 ;
          }
          leaf v6-node-ip {
            description 'The node IPv6 address.'
                        ;
            type ncd:ipv6-address ;
            ncd:revise-date 2020-09-11 ;
          }
          leaf v6-adj-local-ip {
            description 'The local IPv6 address of adjacency.'
                        ;
            type ncd:ipv6-address ;
            ncd:revise-date 2020-09-11 ;
          }
          leaf v6-local-id {
            description 'The local ID of v6 adjacency.'
                        ;
            type uint32 ;
            ncd:revise-date 2020-09-11 ;
          }
          leaf v6-adj-peer-ip {
            description 'The peer IPv6 address of adjacency.'
                        ;
            type ncd:ipv6-address ;
            ncd:revise-date 2020-09-11 ;
          }
          leaf v6-peer-id {
            description 'The peer ID of v6 adjacency.'
                        ;
            type uint32 ;
            ncd:revise-date 2020-09-11 ;
          }
        }
      }
    }
    container static-sr {
      description 'The static SR tunnels information.'
                  ;
      container resource {
        description 'The resource statistics of static SR tunnels.'
                    ;
        container tunnel-perf-switch {
          description 'The number of static SR tunnels which can be turned on p'
                    + 'erformance statistics switch.'
                      ;
          leaf configured {
            description 'The number of static SR tunnels which have turned on p'
                      + 'erformance statistics switch.'
                        ;
            type uint32 ;
          }
          leaf remainder-sum {
            description 'The number of remainder static SR tunnels which can be'
                      + ' turned on performance statistics switch.'
                        ;
            type uint32 ;
          }
          ncd:revise-date 2018-03-26 ;
        }
        ncd:revise-date 2018-03-26 ;
      }
      container static-tunnel {
        description 'The static SR tunnels information.'
                    ;
        list tunnel {
          description 'The static SR tunnel list.'
                      ;
          key tunnel-id ;
          leaf tunnel-id {
            description 'The tunnel ID.'
                        ;
            type uint32 ;
          }
          leaf associated-status {
            description 'The associated status of tunnel.'
                        ;
            type enumeration {
              enum disabled {
                value 1 ;
              }
              enum unbound {
                value 2 ;
              }
              enum bound {
                value 3 ;
              }
            }
          }
        }
        ncd:revise-date 2020-04-10 ;
      }
      ncd:revise-date 2018-03-26 ;
    }
    container sr-policy {
      description 'The SR policy information.'
                  ;
      container traffic-statistics {
        description 'The traffic statistics information of SR policy.'
                    ;
        list policy {
          description 'The SR policy list.'
                      ;
          key 'color end-point'
              ;
          leaf color {
            description 'The color.'
                        ;
            type uint32 ;
          }
          leaf end-point {
            description 'The address of end-point.'
                        ;
            type string {
              length 1..45 ;
            }
          }
          leaf in-bytes {
            description 'The number of inbound bytes.'
                        ;
            type uint64 ;
          }
          leaf in-packets {
            description 'The number of inbound packets.'
                        ;
            type uint64 ;
          }
          leaf e-bytes {
            description 'The number of exporting bytes.'
                        ;
            type uint64 ;
          }
          leaf e-packets {
            description 'The number of exporting packets.'
                        ;
            type uint64 ;
          }
          leaf e-bit-rate {
            description 'The rate of exporting bits.'
                        ;
            type uint64 ;
            ncd:revise-date 2020-12-03 ;
          }
          leaf e-packet-rate {
            description 'The rate of exporting packets.'
                        ;
            type uint64 ;
            ncd:revise-date 2020-12-03 ;
          }
        }
      }
      ncd:revise-date 2020-09-01 ;
    }
  }
  container configuration {
    description 'The branch of configuration model.'
                ;
    container segment-routing {
      description 'The configuration of segment-routing.'
                  ;
      container traffic-eng {
        description 'Traffic engineering.'
                    ;
        leaf te-enable {
          description 'The global switch of segment-routing traffic-eng.'
                      ;
          type enumeration {
            enum disabled {
              value 0 ;
            }
            enum enabled {
              value 1 ;
            }
          }
          default disabled ;
        }
        leaf bfd-affect-enable {
          description 'Enable BFD status affect tunnel creation.'
                      ;
          type enumeration {
            enum disabled {
              value 0 ;
            }
            enum enabled {
              value 1 ;
            }
          }
          default disabled ;
          ncd:revise-date 2018-11-19 ;
        }
        leaf bfd-create-timeout {
          description 'Configure BFD creation timeout in seconds.'
                      ;
          type uint16 {
            range 10..3600 ;
          }
          units second ;
          ncd:revise-date 2018-11-19 ;
        }
        leaf hsb-policy {
          description 'The configuration of policy hot-standby.'
                      ;
          type enumeration {
            enum disabled {
              value 0 ;
            }
            enum enabled {
              value 1 ;
            }
          }
          default disabled ;
          ncd:revise-date 2020-03-19 ;
        }
        leaf path-verification {
          description 'The configuration of global path-verification.'
                      ;
          type enumeration {
            enum disabled {
              value 0 ;
            }
            enum enabled {
              value 1 ;
            }
          }
          default disabled ;
          ncd:revise-date 2021-01-21 ;
        }
        leaf policy-traffic-statistics {
          description 'Enable or disable SR policy traffic statistics.'
                      ;
          type enumeration {
            enum disabled {
              value 0 ;
            }
            enum enabled {
              value 1 ;
            }
          }
          default disabled ;
          ncd:revise-date 2020-03-26 ;
        }
        leaf path-uninterrupt-time {
          description 'Configure uninterrupted time for path change.'
                      ;
          type uint16 {
            range 0..3600 ;
          }
          units second ;
          default 2 ;
          ncd:revise-date 2020-04-18 ;
        }
        leaf load-sharing {
          description 'Load sharing.'
                      ;
          type enumeration {
            enum per-stream {
              value 1 ;
            }
            enum per-packet {
              value 2 ;
            }
            enum dlb {
              value 3 ;
            }
          }
          default per-stream ;
          ncd:revise-date 2020-05-28 ;
        }
        leaf cspf-ex-overload {
          description 'Config CSPF exclude overload nodes.'
                      ;
          type enumeration {
            enum disabled {
              value 0 ;
            }
            enum enabled {
              value 1 ;
            }
          }
          default disabled ;
          ncd:revise-date 2020-10-13 ;
        }
        container global-config {
          description 'SR TE global common configuration.'
                      ;
          leaf bgp-auto-del-delay-time {
            description 'Configure the delay time to delete bgp auto tunnel.'
                        ;
            type uint16 {
              range 0..60 ;
            }
            units minute ;
            default 30 ;
          }
          leaf srv6-locator-name {
            description 'SRv6 locator name.'
                        ;
            type string {
              length 1..31 ;
            }
            ncd:revise-date 2020-07-31 ;
          }
          container policy-sbfd {
            description 'The global configuration of SR policy sbfd.When there '
                      + 'is no sbfd configuration under the SR policy instance,'
                      + ' use the global configuration.'
                        ;
            leaf template-name {
              description 'The template name of SR policy sbfd.'
                          ;
              type string {
                length 1..31 ;
              }
            }
            ncd:revise-date 2020-05-18 ;
          }
          container policy-sl-sbfd {
            description 'The global configuration of SR policy segment list sbf'
                      + 'd.When there is no segment list sbfd configuration und'
                      + 'er the SR policy instance, use the global configuratio'
                      + 'n.'
                        ;
            leaf template-name {
              description 'The template name of SR policy segment list sbfd.'
                          ;
              type string {
                length 1..31 ;
              }
            }
            leaf echo {
              description 'The echo configuration of SR policy segment list sbf'
                        + 'd.'
                          ;
              type enumeration {
                enum disabled {
                  value 0 ;
                }
                enum enabled {
                  value 1 ;
                }
              }
              default disabled ;
              ncd:revise-date 2021-03-17 ;
            }
            ncd:revise-date 2020-04-07 ;
          }
          container pcep-auto-init {
            description 'The configuration parameters of PCEP automatically est'
                      + 'ablishes tunnel.'
                        ;
            leaf tunnel-sbfd-template {
              description 'The template name of tunnel sbfd.'
                          ;
              type string {
                length 1..31 ;
              }
            }
            leaf master-sbfd-template {
              description 'The template name of master path sbfd.'
                          ;
              type string {
                length 1..31 ;
              }
            }
            leaf slave-sbfd-template {
              description 'The template name of slave path sbfd.'
                          ;
              type string {
                length 1..31 ;
              }
            }
            ncd:revise-date 2020-10-07 ;
          }
          ncd:revise-date 2019-04-19 ;
        }
        container bgp-ls {
          description 'BGP link-state information.'
                      ;
          leaf bgp-link-state {
            description 'Distribute link-state data using BGP.'
                        ;
            type enumeration {
              enum disabled {
                value 0 ;
              }
              enum enabled {
                value 1 ;
              }
            }
            default disabled ;
          }
          ncd:revise-date 2020-03-27 ;
        }
        container sr-path {
          description 'Configuration of sr path.'
                      ;
          presence 'Configuration of sr path'
                   ;
          list name-based {
            description 'The explicit path name list.'
                        ;
            max-elements 32768 ;
            key name ;
            leaf name {
              description 'The sr path name.'
                          ;
              type string {
                length 1..64 ;
              }
            }
            container path-paras {
              description 'Every sr explicit-path contains 16 hops.'
                          ;
              list path-para {
                description 'Explicit path address information.'
                            ;
                max-elements 131072 ;
                key index ;
                leaf index {
                  description 'The explicit path index.'
                              ;
                  type uint8 {
                    range 1..255 ;
                  }
                }
                container sr-path {
                  choice sr-path-type {
                    description 'SR path type.'
                                ;
                    mandatory true ;
                    case node {
                      description 'node type'
                                  ;
                      leaf node-router-id {
                        description 'The router id of node.'
                                    ;
                        type ncd:ipv4-address ;
                        mandatory true ;
                      }
                      leaf node-label-value {
                        description 'The value of label.'
                                    ;
                        type uint32 {
                          range 16..1048575 ;
                        }
                        ncd:revise-date 2019-07-16 ;
                      }
                    }
                    case adjacency {
                      description 'adjacency type.'
                                  ;
                      leaf router-id {
                        description 'The router id of local node.'
                                    ;
                        type ncd:ipv4-address ;
                        mandatory true ;
                      }
                      leaf interface-ip {
                        description 'The interface ip of local node.'
                                    ;
                        type ncd:ipv4-address ;
                        mandatory true ;
                      }
                      leaf peer-router-id {
                        description 'The router id of peer node.'
                                    ;
                        type ncd:ipv4-address ;
                        mandatory true ;
                      }
                      leaf peer-interface-ip {
                        description 'The interface ip of peer node.'
                                    ;
                        type ncd:ipv4-address ;
                        mandatory true ;
                      }
                      leaf adjacency-label-value {
                        description 'The value of label.'
                                    ;
                        type uint32 {
                          range 16..1048575 ;
                        }
                        ncd:revise-date 2019-07-16 ;
                      }
                    }
                    case label {
                      description 'label type.'
                                  ;
                      leaf label-value {
                        description 'The value of label.'
                                    ;
                        type uint32 {
                          range 16..1048575 ;
                        }
                        mandatory true ;
                      }
                    }
                    case node-ipv6 {
                      description 'node-ipv6 type'
                                  ;
                      leaf node-router-id-ipv6 {
                        description 'The IPv6 router id of node.'
                                    ;
                        type ncd:ipv6-address ;
                        mandatory true ;
                      }
                      leaf node-ipv6-label-value {
                        description 'The value of label.'
                                    ;
                        type uint32 {
                          range 16..1048575 ;
                        }
                        ncd:revise-date 2019-07-16 ;
                      }
                      ncd:revise-date 2018-11-23 ;
                    }
                    case adjacency-ipv6 {
                      description 'adjacency-ipv6 type.'
                                  ;
                      leaf interface-ipv6 {
                        description 'The interface IPv6 address of local node.'
                                    ;
                        type ncd:ipv6-address ;
                        mandatory true ;
                      }
                      leaf peer-interface-ipv6 {
                        description 'The interface ip of peer node.'
                                    ;
                        type ncd:ipv6-address ;
                        mandatory true ;
                      }
                      leaf adjacency-ipv6-label-value {
                        description 'The value of label.'
                                    ;
                        type uint32 {
                          range 16..1048575 ;
                        }
                        ncd:revise-date 2019-07-16 ;
                      }
                      ncd:revise-date 2018-11-23 ;
                    }
                    case adjacency-ipv6-link-local {
                      description 'adjacency-ipv6-link-local type.'
                                  ;
                      leaf local-interface-ipv6-addr {
                        description 'The interface IPv6 address of local node.'
                                    ;
                        type ncd:ipv6-address ;
                        mandatory true ;
                      }
                      leaf local-interface-id {
                        description 'The interface ID of local node.'
                                    ;
                        type uint32 {
                          range 1..4294967294 ;
                        }
                        mandatory true ;
                      }
                      leaf peer-interface-ipv6-addr {
                        description 'The interface IPv6 address of peer node.'
                                    ;
                        type ncd:ipv6-address ;
                        mandatory true ;
                      }
                      leaf peer-interface-id {
                        description 'The interface ID of remote node.'
                                    ;
                        type uint32 {
                          range 1..4294967294 ;
                        }
                        mandatory true ;
                      }
                      leaf adjacency-ipv6-link-local-label-value {
                        description 'The value of label.'
                                    ;
                        type uint32 {
                          range 16..1048575 ;
                        }
                      }
                      ncd:revise-date 2020-09-27 ;
                    }
                  }
                }
              }
            }
          }
          list id-based {
            description 'The explicit path ID list.'
                        ;
            max-elements 32768 ;
            key id ;
            leaf id {
              description 'The explicit path ID.'
                          ;
              type uint16 {
                range 1..65535 ;
              }
            }
            container path-paras {
              description 'Every explicit-path contains 16 hops.'
                          ;
              list path-para {
                description 'Explicit path address information.'
                            ;
                max-elements 131072 ;
                key index ;
                leaf index {
                  description 'Explicit path index.'
                              ;
                  type uint8 {
                    range 1..255 ;
                  }
                }
                container sr-path {
                  description 'SR path'
                              ;
                  choice sr-path-type {
                    description 'SR path type.'
                                ;
                    mandatory true ;
                    case node {
                      description 'node type.'
                                  ;
                      leaf node-router-id {
                        description 'The router id of node.'
                                    ;
                        type ncd:ipv4-address ;
                        mandatory true ;
                      }
                      leaf node-label-value {
                        description 'The value of label.'
                                    ;
                        type uint32 {
                          range 16..1048575 ;
                        }
                        ncd:revise-date 2019-07-16 ;
                      }
                    }
                    case adjacency {
                      description 'adjacency type.'
                                  ;
                      leaf router-id {
                        description 'The router id of local node.'
                                    ;
                        type ncd:ipv4-address ;
                        mandatory true ;
                      }
                      leaf interface-ip {
                        description 'The interface ip of local node.'
                                    ;
                        type ncd:ipv4-address ;
                        mandatory true ;
                      }
                      leaf peer-router-id {
                        description 'The router id of peer node.'
                                    ;
                        type ncd:ipv4-address ;
                        mandatory true ;
                      }
                      leaf peer-interface-ip {
                        description 'The interface ip of peer node.'
                                    ;
                        type ncd:ipv4-address ;
                        mandatory true ;
                      }
                      leaf adjacency-label-value {
                        description 'The value of label.'
                                    ;
                        type uint32 {
                          range 16..1048575 ;
                        }
                        ncd:revise-date 2019-07-16 ;
                      }
                    }
                    case label {
                      description 'label type.'
                                  ;
                      leaf label-value {
                        description 'The value of label.'
                                    ;
                        type uint32 {
                          range 16..1048575 ;
                        }
                        mandatory true ;
                      }
                    }
                    case node-ipv6 {
                      description 'node-ipv6 type'
                                  ;
                      leaf node-router-id-ipv6 {
                        description 'The IPv6 router id of node.'
                                    ;
                        type ncd:ipv6-address ;
                        mandatory true ;
                      }
                      leaf node-ipv6-label-value {
                        description 'The value of label.'
                                    ;
                        type uint32 {
                          range 16..1048575 ;
                        }
                        ncd:revise-date 2019-07-16 ;
                      }
                      ncd:revise-date 2018-11-23 ;
                    }
                    case adjacency-ipv6 {
                      description 'adjacency-ipv6 type.'
                                  ;
                      leaf interface-ipv6 {
                        description 'The interface IPv6 address of local node.'
                                    ;
                        type ncd:ipv6-address ;
                        mandatory true ;
                      }
                      leaf peer-interface-ipv6 {
                        description 'The interface ip of peer node.'
                                    ;
                        type ncd:ipv6-address ;
                        mandatory true ;
                      }
                      leaf adjacency-ipv6-label-value {
                        description 'The value of label.'
                                    ;
                        type uint32 {
                          range 16..1048575 ;
                        }
                        ncd:revise-date 2019-07-16 ;
                      }
                      ncd:revise-date 2018-11-23 ;
                    }
                    case adjacency-ipv6-link-local {
                      description 'adjacency-ipv6-link-local type.'
                                  ;
                      leaf local-interface-ipv6-addr {
                        description 'The interface IPv6 address of local node.'
                                    ;
                        type ncd:ipv6-address ;
                        mandatory true ;
                      }
                      leaf local-interface-id {
                        description 'The interface ID of local node.'
                                    ;
                        type uint32 {
                          range 1..4294967294 ;
                        }
                        mandatory true ;
                      }
                      leaf peer-interface-ipv6-addr {
                        description 'The interface IPv6 address of peer node.'
                                    ;
                        type ncd:ipv6-address ;
                        mandatory true ;
                      }
                      leaf peer-interface-id {
                        description 'The interface ID of remote node.'
                                    ;
                        type uint32 {
                          range 1..4294967294 ;
                        }
                        mandatory true ;
                      }
                      leaf adjacency-ipv6-link-local-label-value {
                        description 'The value of label.'
                                    ;
                        type uint32 {
                          range 16..1048575 ;
                        }
                      }
                      ncd:revise-date 2020-09-27 ;
                    }
                  }
                }
              }
            }
          }
          ncd:revise-date 2017-10-25 ;
        }
        container srv6-path {
          description 'Configuration of SRv6 path.'
                      ;
          list name-based {
            description 'The explicit path name list.'
                        ;
            max-elements 32768 ;
            key name ;
            leaf name {
              description 'The SRv6 path name.'
                          ;
              type string {
                length 1..64 ;
              }
            }
            container path-paras {
              list path-para {
                description 'Explicit path address information.'
                            ;
                max-elements 131072 ;
                key index ;
                leaf index {
                  description 'The explicit path index.'
                              ;
                  type int8 {
                    range 1..127 ;
                  }
                }
                container srv6-path {
                  choice srv6-path-type {
                    description 'SRv6 path type.'
                                ;
                    mandatory true ;
                    case srv6-sid {
                      description 'srv6-sid type.'
                                  ;
                      leaf srv6-sid-value {
                        description 'The value of srv6-sid.'
                                    ;
                        type ncd:ipv6-address ;
                        mandatory true ;
                      }
                    }
                  }
                }
              }
            }
          }
          ncd:revise-date 2018-05-14 ;
        }
        container sr-tunnel {
          list tunnel {
            description 'The sr tunnel configuration list.'
                        ;
            max-elements 131070 ;
            key tunnel-name ;
            leaf tunnel-name {
              description 'The tunnel name.'
                          ;
              type string {
                length 10..31 ;
                pattern 'te_tunnel[0-9]{1,22}'
                        ;
              }
            }
            leaf activation {
              description 'The activation of tunnel.'
                          ;
              type enumeration {
                enum disabled {
                  value 0 ;
                }
                enum enabled {
                  value 1 ;
                }
              }
              default enabled ;
              ncd:revise-date 2017-10-13 ;
            }
            leaf hsb-enable {
              description 'Enable hot-standby for tunnel.'
                          ;
              type enumeration {
                enum disabled {
                  value 0 ;
                }
                enum enabled {
                  value 1 ;
                }
              }
              default disabled ;
              ncd:revise-date 2020-10-20 ;
            }
            leaf entropy-label {
              description 'Configure whether the tunnel uses entropy labels.'
                          ;
              type empty ;
              ncd:revise-date 2019-08-09 ;
            }
            leaf destination {
              description 'The destination of tunnel.'
                          ;
              type ncd:ipv4-address {
                pattern '([1-9]|[1-9][0-9]|1[0-9][0-9]|2[0-4][0-9]|25[0-5])(.(['
                      + '0-9]|[1-9][0-9]|1[0-9][0-9]|2[0-4][0-9]|25[0-5])){3}'
                        ;
              }
            }
            leaf track-name {
              description 'The track name.'
                          ;
              type string {
                length 1..31 ;
              }
            }
            leaf alias-name {
              description 'Configuration of tunnel alias name.'
                          ;
              type string {
                length 1..63 ;
              }
            }
            leaf path-setup-type {
              description 'The path setup type of tunnel.'
                          ;
              type enumeration {
                enum sr-mpls {
                  value 0 ;
                }
                enum srv6 {
                  value 1 ;
                }
              }
              default sr-mpls ;
              ncd:revise-date 2018-05-14 ;
            }
            leaf path-verification {
              description 'The configuration of tunnel path-verification.'
                          ;
              type enumeration {
                enum none {
                  value 0 ;
                }
                enum enabled {
                  value 1 ;
                }
                enum disabled {
                  value 2 ;
                }
              }
              default none ;
              ncd:revise-date 2021-01-21 ;
            }
            leaf color {
              description 'The color of tunnel.'
                          ;
              type uint32 {
                range 1..4294967295 ;
              }
              ncd:revise-date 2018-05-14 ;
            }
            leaf sid-algo {
              description 'The SID algorithm definition number for SR tunnel.'
                          ;
              type uint8 {
                range 128..255 ;
              }
              ncd:revise-date 2019-12-20 ;
            }
            leaf metric-type {
              description 'The metric type of tunnel.'
                          ;
              type enumeration {
                enum igp {
                  value 0 ;
                }
                enum delay {
                  value 1 ;
                }
                enum te {
                  value 2 ;
                }
              }
              default igp ;
              ncd:revise-date 2020-03-28 ;
            }
            leaf drop-upon-invalid {
              description 'The drop-upon-invalid of tunnel.'
                          ;
              type enumeration {
                enum disabled {
                  value 0 ;
                }
                enum enabled {
                  value 1 ;
                }
              }
              default disabled ;
              ncd:revise-date 2020-09-18 ;
            }
            container destination-ipv6 {
              description 'The ipv6 destination of tunnel.'
                          ;
              leaf destination-ipv6 {
                description 'The ipv6 destination of tunnel.'
                            ;
                type ncd:ipv6-address {
                  pattern '((:|[0-9a-fA-F]{0,4}):)([0-9a-fA-F]{0,4}:){0,5}((([0'
                        + '-9a-fA-F]{0,4}:)?(:|[0-9a-fA-F]{0,4}))|(((25[0-5]|2['
                        + '0-4][0-9]|[01]?[0-9]?[0-9])\.){3}(25[0-5]|2[0-4][0-9'
                        + ']|[01]?[0-9]?[0-9])))(%[\p{N}\p{L}]+)?'
                          ;
                  pattern '(([^:]+:){6}(([^:]+:[^:]+)|(.*\..*)))|((([^:]+:)*[^:'
                        + ']+)?::(([^:]+:)*[^:]+)?)(%.+)?'
                          ;
                }
              }
              ncd:revise-date 2018-05-14 ;
            }
            container affinity {
              container main-affinity {
                description "The affinity function configuration of tunnel's ma"
                          + "ster lsp."
                            ;
                container bit-positions {
                  description 'The configuration of affinity bit position.The a'
                            + 'ffinity of bit and name types is mutually exclus'
                            + 'ive.'
                              ;
                  list bit-position {
                    description 'The configuration of affinity bit position.The'
                              + ' affinity of bit and name types is mutually ex'
                              + 'clusive.'
                                ;
                    max-elements 32 ;
                    key position ;
                    leaf affinity-type {
                      description 'The tunnel configuration of affinity type,ex'
                                + 'clude-any(1)/include-any(2)/include-all(3).'
                                  ;
                      type enumeration {
                        enum exclude-any {
                          value 1 ;
                          description 'Configure the exclude-any affinity.'
                                      ;
                        }
                        enum include-any {
                          value 2 ;
                          description 'Configure the include-any affinity.'
                                      ;
                        }
                        enum include-all {
                          value 3 ;
                          description 'Configure the include-all affinity.'
                                      ;
                        }
                      }
                      mandatory true ;
                    }
                    leaf position {
                      description 'The tunnel configuration of affinity bit pos'
                                + 'ition.'
                                  ;
                      type uint8 {
                        range 0..31 ;
                      }
                    }
                  }
                }
                container bit-names {
                  description 'The configuration of affinity name.The affinity '
                            + 'of bit and name types is mutually exclusive.'
                              ;
                  list bit-name {
                    description 'The configuration of affinity name.The affinit'
                              + 'y of bit and name types is mutually exclusive.'
                                ;
                    max-elements 32 ;
                    key name ;
                    leaf affinity-type {
                      description 'The tunnel configuration of affinity type,ex'
                                + 'clude-any(1)/include-any(2)/include-all(3).'
                                  ;
                      type enumeration {
                        enum exclude-any {
                          value 1 ;
                          description 'Configure the exclude-any affinity.'
                                      ;
                        }
                        enum include-any {
                          value 2 ;
                          description 'Configure the include-any affinity.'
                                      ;
                        }
                        enum include-all {
                          value 3 ;
                          description 'Configure the include-all affinity.'
                                      ;
                        }
                      }
                      mandatory true ;
                    }
                    leaf name {
                      description 'The configuration of affinity bit name.'
                                  ;
                      type string {
                        length 1..32 ;
                      }
                    }
                  }
                }
              }
              ncd:revise-date 2019-10-12 ;
            }
            container escape-path {
              description 'configuration of escape path.'
                          ;
              presence 'configuration of escape path.'
                       ;
              leaf escape-path-enable {
                description 'Enable escape path function of the tunnel.'
                            ;
                type enumeration {
                  enum disabled {
                    value 0 ;
                  }
                  enum enabled {
                    value 1 ;
                  }
                }
                default disabled ;
              }
              container sr-path {
                description 'The escape path of SR tunnel.'
                            ;
                choice path-type {
                  description 'Path Selection Type.'
                              ;
                  case name-based {
                    description 'Based on the name of the sr path selection.'
                                ;
                    leaf name {
                      description 'The sr path name.'
                                  ;
                      type string {
                        length 1..64 ;
                      }
                      mandatory true ;
                    }
                  }
                  case id-based {
                    description 'Based on the id of the sr path selection.'
                                ;
                    leaf id {
                      description 'The sr path ID.'
                                  ;
                      type uint16 {
                        range 1..65535 ;
                      }
                      mandatory true ;
                    }
                  }
                }
                ncd:revise-date 2020-03-04 ;
              }
              ncd:revise-date 2018-08-27 ;
            }
            container ref-hsb {
              description 'Enable backup path of a tunnel.'
                          ;
              presence 'configuration of ref-hsb'
                       ;
              leaf ref_hsb_enable {
                description 'The tunnel setup reference to hsb enable.'
                            ;
                type enumeration {
                  enum disabled {
                    value 0 ;
                  }
                  enum enabled {
                    value 1 ;
                  }
                }
                default disabled ;
              }
            }
            container sr-path {
              description 'The path of SR tunnel.'
                          ;
              presence 'The path of SR tunnel'
                       ;
              list tunnel-sr-path {
                description 'The path of SR tunnel.'
                            ;
                max-elements 262140 ;
                key path-role ;
                leaf path-role {
                  description 'The role of sr path.'
                              ;
                  type enumeration {
                    enum master {
                      value 1 ;
                    }
                    enum slave {
                      value 2 ;
                    }
                  }
                }
                choice path-type {
                  description 'Path Selection Type.'
                              ;
                  mandatory true ;
                  case name-based {
                    description 'Based on the name of the sr path selection.'
                                ;
                    leaf name {
                      description 'The sr path name.'
                                  ;
                      type string {
                        length 1..64 ;
                      }
                      mandatory true ;
                    }
                  }
                  case id-based {
                    description 'Based on the id of the sr path selection.'
                                ;
                    leaf id {
                      description 'The sr path ID.'
                                  ;
                      type uint16 {
                        range 1..65535 ;
                      }
                      mandatory true ;
                    }
                  }
                }
              }
            }
            container srv6-path {
              description 'The path of SRv6 tunnel.'
                          ;
              list tunnel-srv6-path {
                description 'The path of SRv6 tunnel.'
                            ;
                max-elements 262140 ;
                key path-role ;
                leaf path-role {
                  description 'The role of SRv6 path.'
                              ;
                  type enumeration {
                    enum master {
                      value 1 ;
                    }
                    enum slave {
                      value 2 ;
                    }
                  }
                }
                leaf path-name {
                  description 'The name of SRv6 path.'
                              ;
                  type string {
                    length 1..64 ;
                  }
                  mandatory true ;
                }
              }
              ncd:revise-date 2018-05-14 ;
            }
            container bfd {
              description 'configuration of bfd'
                          ;
              presence 'configuration of bfd'
                       ;
              list tunnel-bfd {
                description 'BFD is set in a tunnel.'
                            ;
                max-elements 100 ;
                key bfd-enable ;
                leaf bfd-enable {
                  description 'The tunnel BFD enable.'
                              ;
                  type enumeration {
                    enum master {
                      value 1 ;
                    }
                    enum slave {
                      value 2 ;
                    }
                  }
                }
                choice detect-param {
                  description 'Detect param.'
                              ;
                  mandatory true ;
                  case template {
                    description 'Bfd template name.'
                                ;
                    leaf template-name {
                      description 'The tunnel bfd template name.'
                                  ;
                      type string {
                        length 1..31 ;
                      }
                      mandatory true ;
                    }
                    ncd:revise-date 2020-04-18 ;
                  }
                  case detect-params {
                    description 'Detect params.'
                                ;
                    leaf min-tx-interval {
                      description 'The tunnel BFD min transmit interval.'
                                  ;
                      type uint32 {
                        range 10..990 ;
                      }
                      units ms ;
                      mandatory true ;
                    }
                    leaf min-rx-interval {
                      description 'The tunnel BFD min receive interval.'
                                  ;
                      type uint32 {
                        range 10..990 ;
                      }
                      units ms ;
                      mandatory true ;
                    }
                    leaf detect-multiple {
                      description 'The tunnel BFD detecting multiple.'
                                  ;
                      type uint16 {
                        range 3..50 ;
                      }
                      mandatory true ;
                    }
                  }
                }
                choice reverse-path {
                  description 'Reverse path.'
                              ;
                  case reverse-tunnel {
                    description 'Selection reverse tunnel.'
                                ;
                    leaf reverse-tunnelid {
                      description 'The tunnel bfd associatd reverse tunnelid.'
                                  ;
                      type uint16 {
                        range 1..65535 {
                          description 'The tunnel bfd reverse tunnel id range'
                                      ;
                        }
                      }
                    }
                    ncd:revise-date 2017-10-16 ;
                  }
                  case ld-rd {
                    description 'Local and Remote discriminator for BFD.'
                                ;
                    container ld-rd {
                      description 'Local and Remote discriminator for BFD.'
                                  ;
                      presence 'Local and Remote discriminator for BFD.'
                               ;
                      leaf ld {
                        description 'Local discriminator for BFD.'
                                    ;
                        type uint32 {
                          range 1..2048 ;
                        }
                        mandatory true ;
                      }
                      leaf rd {
                        description 'Remote discriminator for BFD.'
                                    ;
                        type uint32 {
                          range 1..4294967295 ;
                        }
                        mandatory true ;
                      }
                    }
                    ncd:revise-date 2019-08-07 ;
                  }
                  ncd:revise-date 2017-10-16 ;
                }
              }
            }
            container sbfd {
              description 'configuration of sbfd'
                          ;
              list tunnel-sbfd {
                description 'S-BFD is set in a tunnel.'
                            ;
                max-elements 100 ;
                key sbfd-enable ;
                leaf sbfd-enable {
                  description 'The tunnel S-BFD enable.'
                              ;
                  type enumeration {
                    enum master {
                      value 3 ;
                    }
                    enum slave {
                      value 4 ;
                    }
                  }
                }
                choice detect-param {
                  description 'Detect param.'
                              ;
                  mandatory true ;
                  case template {
                    description 'Bfd template name.'
                                ;
                    leaf template-name {
                      description 'The tunnel bfd template name.'
                                  ;
                      type string {
                        length 1..31 ;
                      }
                      mandatory true ;
                    }
                    ncd:revise-date 2020-04-18 ;
                  }
                  case detect-params {
                    description 'Detect params.'
                                ;
                    leaf min-tx-interval {
                      description 'The tunnel S-BFD min transmit interval.'
                                  ;
                      type uint32 {
                        range 10..990 ;
                      }
                      units ms ;
                      mandatory true ;
                    }
                    leaf detect-multiple {
                      description 'The tunnel S-BFD detecting multiple.'
                                  ;
                      type uint16 {
                        range 3..50 ;
                      }
                      mandatory true ;
                    }
                  }
                }
                container reverse-path {
                  description 'The tunnel S-BFD associatd reverse path.'
                              ;
                  choice path-type {
                    description 'Path Selection Type.'
                                ;
                    case label-based {
                      description 'Based on the label path selection.'
                                  ;
                      leaf mpls-label {
                        description 'The tunnel S-BFD associatd reverse mpls la'
                                  + 'bel.'
                                    ;
                        type uint32 {
                          range 16..1048575 ;
                        }
                      }
                    }
                    case sr-path-id-based {
                      description 'Based on the id of the sr path selection.'
                                  ;
                      leaf sr-path-id {
                        description 'The sr path ID.'
                                    ;
                        type uint16 {
                          range 1..65535 ;
                        }
                      }
                    }
                    case sr-path-name-based {
                      description 'Based on the name of the sr path selection.'
                                  ;
                      leaf sr-path-name {
                        description 'The sr path name.'
                                    ;
                        type string {
                          length 1..64 ;
                        }
                      }
                    }
                  }
                }
              }
              ncd:revise-date 2019-05-22 ;
            }
            container path-option {
              description 'Tunnel path option configuration.'
                          ;
              presence 'Tunnel path option configuration.'
                       ;
              list tunnel-path-option {
                description 'Tunnel path option configuration.'
                            ;
                max-elements 786420 ;
                key option-id ;
                leaf option-id {
                  description 'The number of path-option.'
                              ;
                  type uint8 {
                    range 1..16 ;
                  }
                }
                choice path-type {
                  description 'Path Selection Type.'
                              ;
                  mandatory true ;
                  case dynamic {
                    description 'SR Path Selection.'
                                ;
                    leaf dynamic {
                      description 'The path type is dynamic.'
                                  ;
                      type empty ;
                      mandatory true ;
                    }
                  }
                  case explicit-name {
                    description 'Based on the name of the explicit path selecti'
                              + 'on.'
                                ;
                    leaf explicit-path-name {
                      description 'The related explicit path name.'
                                  ;
                      type string {
                        length 1..64 ;
                      }
                      mandatory true ;
                    }
                  }
                  case explicit-id {
                    description 'Id-based explicit path selection.'
                                ;
                    leaf explicit-path-id {
                      description 'The related explicit path ID.'
                                  ;
                      type uint16 {
                        range 1..65535 ;
                      }
                      mandatory true ;
                    }
                  }
                }
              }
            }
            container hotstandby {
              description 'The configuration of hotstandby.'
                          ;
              presence 'The configuration of hotstandby.'
                       ;
              list tunnel-hotstandby {
                description 'The configuration of hotstandby.'
                            ;
                max-elements 786420 ;
                key path-option-id ;
                leaf path-option-id {
                  description 'The attribute is the path-option which is protec'
                            + 'ted.'
                              ;
                  type uint8 {
                    range 1..16 ;
                  }
                }
                choice path-type {
                  description 'To assign path type of backup lsp. Three types.'
                              ;
                  mandatory true ;
                  case dynamic {
                    description 'Dynamic Path Selection.'
                                ;
                    leaf dynamic {
                      description 'The path type is dynamic.'
                                  ;
                      type empty ;
                      mandatory true ;
                    }
                    leaf prefer {
                      description "If this attribute is configured, the backup "
                                + "path only can't be completely duplicated wit"
                                + "h primary path, otherwise the backup path mu"
                                + "st be different from primary path."
                                  ;
                      type boolean ;
                      default false ;
                    }
                  }
                  case explicit-id {
                    description 'Id-based explicit path selection.'
                                ;
                    leaf explicit-path-id {
                      description 'The configured explicit path ID.'
                                  ;
                      type uint16 {
                        range 1..65535 ;
                      }
                      mandatory true ;
                    }
                    leaf id-exclude {
                      description 'This attribute can be used to indicate wheth'
                                + 'er backup path need exclude primary path str'
                                + 'ictly.'
                                  ;
                      type boolean ;
                      default false ;
                    }
                  }
                  case explicit-name {
                    description 'Based on the name of the explicit path selecti'
                              + 'on.'
                                ;
                    leaf explicit-path-name {
                      description 'The configured explicit path name.'
                                  ;
                      type string {
                        length 1..64 ;
                      }
                      mandatory true ;
                    }
                    leaf name-exclude {
                      description 'This attribute can be used to indicate wheth'
                                + 'er backup path need exclude primary path str'
                                + 'ictly.'
                                  ;
                      type boolean ;
                      default false ;
                    }
                  }
                }
              }
            }
            container link-limit {
              description 'The maxixmum of link.'
                          ;
              presence 'configuration of hop-limit'
                       ;
              leaf link-limit-num {
                description 'The maxixmum of hop.'
                            ;
                type uint8 {
                  range 1..32 ;
                }
              }
              leaf srv6-link-limit-num {
                description 'The maxixmum of hop for SRv6 tunnel.'
                            ;
                type uint8 {
                  range 1..32 ;
                }
                ncd:revise-date 2020-09-21 ;
              }
            }
            container pce-init {
              status deprecated ;
              description 'The pce initiate function of dynamic tunnel.'
                          ;
              presence 'pce initiate of dynamic tunnel'
                       ;
              leaf pce-init-enable {
                status deprecated ;
                description 'Enable PCE init of a tunnel.'
                            ;
                type enumeration {
                  enum disabled {
                    value 0 ;
                  }
                  enum enabled {
                    value 1 ;
                  }
                }
                default disabled ;
              }
            }
            container pce-control {
              status deprecated ;
              description 'The pce control function of dynamic tunnel.'
                          ;
              presence 'pce control of dynamic tunnel'
                       ;
              leaf pce-control-enable {
                status deprecated ;
                description 'Enable PCE control of a tunnel.'
                            ;
                type enumeration {
                  enum disabled {
                    value 0 ;
                  }
                  enum enabled {
                    value 1 ;
                  }
                }
                default disabled ;
              }
              leaf pce-control-addr {
                status deprecated ;
                description 'Pce control address.'
                            ;
                type ncd:ipv4-address {
                  pattern '([1-9]|[1-9][0-9]|1[0-9][0-9]|2[0-4][0-9]|25[0-5])(.'
                        + '([0-9]|[1-9][0-9]|1[0-9][0-9]|2[0-4][0-9]|25[0-5])){'
                        + '3}'
                          ;
                }
                ncd:revise-date 2018-08-29 ;
              }
              leaf pce-control-addr-ipv6 {
                status deprecated ;
                description 'IPv6 pce control address.'
                            ;
                type ncd:ipv6-address {
                  pattern '([0-9a-fA-F]{1,4}:){7}([0-9a-fA-F]{0,4})$|^([0-9a-fA'
                        + '-F]{1,4}:){1,6}(:[0-9a-fA-F]{0,4}){1,6}$|^([:]{2})(('
                        + '[0-9a-fA-F]{1,4}:){0,6})([0-9a-fA-F]{1,4})$|^([0-9a-'
                        + 'fA-F]{1,4}:){6}([0-9]{1,3}.){3}([0-9]{1,3})$|^([0-9a'
                        + '-fA-F]{1,4}:){1,5}(:[0-9a-fA-F]{0,4}){1,5}([0-9]{1,3'
                        + '}.){3}([0-9]{1,3})$|^([:]{2})(([0-9a-fA-F]{1,4}:){0,'
                        + '5})([0-9]{1,3}.){3}([0-9]{1,3})'
                          ;
                }
                ncd:revise-date 2018-11-23 ;
              }
            }
            container pce {
              description 'configuration of pce.'
                          ;
              container slave-name {
                description 'Configuration of tunnel slave name.'
                            ;
                leaf slave-name {
                  description 'Configuration of tunnel slave name.'
                              ;
                  type string {
                    length 1..63 ;
                  }
                }
                ncd:revise-date 2020-10-20 ;
              }
              choice pce-type {
                description 'Pce Selection Type.'
                            ;
                case pce-init {
                  description 'The pce initiate function of dynamic tunnel.'
                              ;
                  container pce-init-cfg {
                    description 'The pce init function of dynamic tunnel.'
                                ;
                    leaf pce-init-enable {
                      description 'Enable PCE init of a tunnel.'
                                  ;
                      type empty ;
                    }
                  }
                }
                case pce-control {
                  description 'The pce control function of dynamic tunnel.'
                              ;
                  container pce-control-cfg {
                    description 'The pce control function of dynamic tunnel.'
                                ;
                    presence 'pce control of dynamic tunnel'
                             ;
                    leaf pce-control-enable {
                      description 'Enable PCE control of a tunnel.'
                                  ;
                      type empty ;
                    }
                    container control-addr {
                      description 'the PCE control address.'
                                  ;
                      choice addr-type {
                        description 'Specify the PCE control address type.'
                                    ;
                        case ipv4 {
                          description 'IPv4 address type.'
                                      ;
                          leaf pce-control-addr {
                            description 'Pce control address.'
                                        ;
                            type ncd:ipv4-address {
                              pattern '([1-9]|[1-9][0-9]|1[0-9][0-9]|2[0-4][0-9'
                                    + ']|25[0-5])(.([0-9]|[1-9][0-9]|1[0-9][0-9'
                                    + ']|2[0-4][0-9]|25[0-5])){3}'
                                      ;
                            }
                          }
                        }
                        case ipv6 {
                          description 'IPv6 address type.'
                                      ;
                          leaf pce-control-addr-ipv6 {
                            description 'IPv6 pce control address.'
                                        ;
                            type ncd:ipv6-address {
                              pattern '([0-9a-fA-F]{1,4}:){7}([0-9a-fA-F]{0,4})'
                                    + '$|^([0-9a-fA-F]{1,4}:){1,6}(:[0-9a-fA-F]'
                                    + '{0,4}){1,6}$|^([:]{2})(([0-9a-fA-F]{1,4}'
                                    + ':){0,6})([0-9a-fA-F]{1,4})$|^([0-9a-fA-F'
                                    + ']{1,4}:){6}([0-9]{1,3}.){3}([0-9]{1,3})$'
                                    + '|^([0-9a-fA-F]{1,4}:){1,5}(:[0-9a-fA-F]{'
                                    + '0,4}){1,5}([0-9]{1,3}.){3}([0-9]{1,3})$|'
                                    + '^([:]{2})(([0-9a-fA-F]{1,4}:){0,5})([0-9'
                                    + ']{1,3}.){3}([0-9]{1,3})'
                                      ;
                            }
                          }
                        }
                      }
                    }
                  }
                }
              }
              ncd:revise-date 2020-02-14 ;
            }
            container srv6-binding-sid {
              description 'The configuration of SRv6 binding sid.'
                          ;
              choice srv6-bsid-type {
                description 'To assign the type of SRv6 binding sid. Two types.'
                            ;
                case auto {
                  status obsolete {
                    ncd:revise-date 2020-06-25 ;
                  }
                  description 'Auto SRv6 binding sid.'
                              ;
                  leaf auto {
                    status obsolete {
                      ncd:revise-date 2020-06-25 ;
                    }
                    description 'The type is auto.'
                                ;
                    type empty ;
                  }
                }
                case static {
                  description 'static SRv6 binding sid.'
                              ;
                  leaf static_srv6_bsid {
                    description 'The type is static.'
                                ;
                    type ncd:ipv6-address ;
                  }
                }
              }
              ncd:revise-date 2018-05-14 ;
            }
            container auto-route {
              description 'configuration of auto-route.'
                          ;
              presence 'configuration of auto-route'
                       ;
              leaf ar-enable {
                description 'The tunnel auto route switch.'
                            ;
                type enumeration {
                  enum disabled {
                    value 0 ;
                  }
                  enum enabled {
                    value 1 ;
                  }
                }
                default disabled ;
              }
              leaf ar-metric-type {
                description 'Auto route metric type.'
                            ;
                type enumeration {
                  enum igp {
                    value 0 ;
                  }
                  enum absolute {
                    value 2 ;
                  }
                  enum relative {
                    value 3 ;
                  }
                }
                default igp ;
              }
              leaf ar-relative-metric {
                description 'The relative metric of AR,it is relative to IGP me'
                          + 'tric.'
                            ;
                type int32 {
                  range -10..10 ;
                }
                default 0 ;
              }
              leaf ar-absolute-metric {
                description 'The absolute metric of AR.'
                            ;
                type uint32 {
                  range 0..4294967295 ;
                }
                default 0 ;
              }
              leaf ar-include-ipv6 {
                description 'The tunnel auto route ipv6 enable.'
                            ;
                type enumeration {
                  enum disabled {
                    value 0 ;
                  }
                  enum enabled {
                    value 1 ;
                  }
                }
                default disabled ;
                ncd:revise-date 2018-11-02 ;
              }
              ncd:revise-date 2018-10-15 ;
            }
            leaf reoptimize {
              description 'Specify SR tunnel whether to open the timing re-opti'
                        + 'mization.'
                          ;
              type empty ;
              ncd:revise-date 2019-02-15 ;
            }
            leaf reopt-hsb-lsp {
              description 'Enable hsb-lsp auto-reoptimize.'
                          ;
              type empty ;
              ncd:revise-date 2019-02-15 ;
            }
            leaf flow-statistics {
              description 'The switch of SR tunnel flow statistics.'
                          ;
              type enumeration {
                enum disabled {
                  value 0 ;
                }
                enum enabled {
                  value 1 ;
                }
              }
              default disabled ;
              ncd:revise-date 2019-06-13 ;
            }
            container bandwidth {
              description 'The SR tunnel bandwidth.'
                          ;
              presence 'SR tunnel bandwidth allocation.'
                       ;
              leaf bandwidth {
                description 'The SR tunnel bandwidth configuration.'
                            ;
                type uint32 {
                  range 1..4294967295 ;
                }
                units kbps ;
                mandatory true ;
              }
              ncd:revise-date 2019-07-19 ;
            }
          }
        }
        container static-sr {
          description 'The static SR tunnel configuration.'
                      ;
          list static-tunnel {
            description 'The static SR tunnel configuration list.'
                        ;
            max-elements 131070 ;
            key tunnel-name ;
            leaf tunnel-name {
              description 'The tunnel name.'
                          ;
              type string {
                length 10..31 ;
                pattern 'te_tunnel[0-9]{1,22}'
                        ;
              }
            }
            leaf activation {
              description 'The activation of tunnel.'
                          ;
              type enumeration {
                enum disabled {
                  value 0 ;
                }
                enum enabled {
                  value 1 ;
                }
              }
              default enabled ;
              ncd:revise-date 2018-03-26 ;
            }
            leaf color {
              description 'The color of tunnel.'
                          ;
              type uint32 {
                range 1..4294967295 ;
              }
              ncd:revise-date 2021-04-20 ;
            }
            leaf compress-num {
              if-feature static-sr-tunnel-compress-num ;
              description 'The number of compressed tunnels.'
                          ;
              type uint16 {
                range 1..32768 ;
              }
              ncd:revise-date 2020-09-17 ;
            }
            leaf path-verification {
              description 'The configuration of tunnel path-verification.'
                          ;
              type enumeration {
                enum none {
                  value 0 ;
                }
                enum enabled {
                  value 1 ;
                }
                enum disabled {
                  value 2 ;
                }
              }
              default none ;
              ncd:revise-date 2021-01-21 ;
            }
            leaf performance-switch {
              description 'The switch of tunnel performance statistics.'
                          ;
              type enumeration {
                enum off {
                  value 0 ;
                }
                enum on {
                  value 1 ;
                }
              }
              default off ;
              ncd:revise-date 2018-03-26 ;
            }
            leaf track-name {
              description 'The track name.'
                          ;
              type string {
                length 1..31 ;
              }
              ncd:revise-date 2018-11-14 ;
            }
            container role-type {
              description 'The tunnel role and direction type.'
                          ;
              presence 'Configure tunnel role and type.'
                       ;
              leaf role {
                description 'The static SR tunnel role including ingress,transi'
                          + 't and egress.'
                            ;
                type enumeration {
                  enum ingressNode {
                    value 1 ;
                  }
                  enum transitNode {
                    value 2 ;
                  }
                  enum egressNode {
                    value 3 ;
                  }
                }
                mandatory true ;
              }
              leaf direction-type {
                description 'The static SR tunnel direction type including unid'
                          + 'irectional and bidirectional.'
                            ;
                type enumeration {
                  enum bidirectional {
                    value 2 ;
                  }
                  enum unidirectional {
                    value 1 ;
                  }
                }
                mandatory true ;
              }
            }
            container triple {
              description 'The tunnel triple elements.'
                          ;
              presence 'Configure tunnel triple.'
                       ;
              leaf ingress-tunnel-id {
                description 'The ingress tunnel ID,it is used to locate ingress'
                          + ' tunnel. This attribute is determined by product.'
                            ;
                type uint32 {
                  range 1..264192 ;
                }
                mandatory true ;
              }
              choice ip-type {
                description 'The type of triple elements address.'
                            ;
                mandatory true ;
                case ipv4 {
                  description 'IPv4 address.'
                              ;
                  leaf ingress-id {
                    description 'The ingress route ID.'
                                ;
                    type ncd:ipv4-address ;
                    mandatory true ;
                  }
                  leaf egress-id {
                    description 'The egress route ID.'
                                ;
                    type ncd:ipv4-address ;
                    mandatory true ;
                  }
                }
                case ipv6 {
                  description 'IPv6 address.'
                              ;
                  leaf ingress-ipv6-id {
                    description 'The ingress IPv6 route ID.'
                                ;
                    type ncd:ipv6-address ;
                    mandatory true ;
                  }
                  leaf egress-ipv6-id {
                    description 'The egress IPv6 route ID.'
                                ;
                    type ncd:ipv6-address ;
                    mandatory true ;
                  }
                  ncd:revise-date 2019-01-02 ;
                }
              }
            }
            container pce-control {
              description 'The tunnel pce control function.'
                          ;
              leaf pce-control-enable {
                description 'Enable tunnel PCE control.'
                            ;
                type enumeration {
                  enum enabled {
                    value 1 ;
                  }
                  enum disabled {
                    value 0 ;
                  }
                }
                default disabled ;
              }
              ncd:revise-date 2018-12-28 ;
            }
            container lsps {
              description 'The configured lsp of static SR tunnel.'
                          ;
              list lsp {
                description 'Lsp list.'
                            ;
                max-elements 1 ;
                key lsp-id ;
                leaf lsp-id {
                  description "The tunnel's lsp ID."
                              ;
                  type uint16 {
                    range 1 ;
                  }
                }
                container positive-in-label {
                  description 'The positive in-label of static SR tunnel.'
                              ;
                  presence 'Configure positive in-label'
                           ;
                  leaf in-label {
                    description 'The positive in-label.'
                                ;
                    type uint32 {
                      range 16..1048575 ;
                    }
                    mandatory true ;
                  }
                }
                container positive-out-label {
                  description 'The positive out-label of static SR tunnel.'
                              ;
                  presence 'Configure positive out-label'
                           ;
                  leaf out-label {
                    description 'The positive out-label.'
                                ;
                    type uint32 {
                      range 16..1048575 ;
                    }
                    mandatory true ;
                  }
                }
                container reverse-in-label {
                  description 'The reverse in-label of static SR tunnel.'
                              ;
                  presence 'Configure reverse in-label'
                           ;
                  leaf rvs-in-label {
                    description 'The reverse in-label.'
                                ;
                    type uint32 {
                      range 16..1048575 ;
                    }
                    mandatory true ;
                  }
                }
                container reverse-out-label {
                  description 'The reverse out-label of static SR tunnel.'
                              ;
                  presence 'Configure reverse out-label'
                           ;
                  leaf rvs-out-label {
                    description 'The reverse out-label.'
                                ;
                    type uint32 {
                      range 16..1048575 ;
                    }
                    mandatory true ;
                  }
                }
                container positive-sr-path {
                  description 'The positive path of static SR tunnel.'
                              ;
                  presence 'Configure positive path'
                           ;
                  choice sr-path {
                    description 'The positive path type of static SR tunnel.'
                                ;
                    mandatory true ;
                    case id {
                      description 'The positive path ID of static SR tunnel.'
                                  ;
                      leaf path-id {
                        description 'The ID of path.'
                                    ;
                        type uint16 {
                          range 1..65535 ;
                        }
                        mandatory true ;
                      }
                    }
                    case name {
                      description 'The positive path name of static SR tunnel.'
                                  ;
                      leaf path-name {
                        description 'The name of path.'
                                    ;
                        type string {
                          length 1..64 ;
                        }
                        mandatory true ;
                      }
                    }
                  }
                }
                container reserve-sr-path {
                  description 'The reserve path of static SR tunnel.'
                              ;
                  presence 'Configure reserve path'
                           ;
                  choice rvs-sr-path {
                    description 'The reserve path type of static SR tunnel.'
                                ;
                    mandatory true ;
                    case rvs-id {
                      description 'The reserve path ID of static SR tunnel.'
                                  ;
                      leaf rvs-path-id {
                        description 'The ID of reserve path.'
                                    ;
                        type uint16 {
                          range 1..65535 ;
                        }
                        mandatory true ;
                      }
                    }
                    case rvs-name {
                      description 'The reserve path name of static SR tunnel.'
                                  ;
                      leaf rvs-path-name {
                        description 'The name of reserve path.'
                                    ;
                        type string {
                          length 1..64 ;
                        }
                        mandatory true ;
                      }
                    }
                  }
                }
              }
            }
            leaf flow-statistics {
              description 'The switch of static SR tunnel flow statistics.'
                          ;
              type enumeration {
                enum disabled {
                  value 0 ;
                }
                enum enabled {
                  value 1 ;
                }
              }
              default disabled ;
              ncd:revise-date 2019-06-13 ;
            }
          }
          ncd:revise-date 2018-02-13 ;
        }
        container sr-policy {
          description 'Configuration of sr policy.'
                      ;
          presence 'Configuration of sr policy'
                   ;
          list policy {
            description 'The SR policy configuration list.'
                        ;
            max-elements 16384 ;
            key policy-name ;
            leaf policy-name {
              description 'The policy name.'
                          ;
              type string {
                length 1..63 ;
              }
            }
            leaf path-setup-type {
              description 'The path setup type of policy.'
                          ;
              type enumeration {
                enum sr-mpls {
                  value 0 ;
                }
                enum srv6 {
                  value 1 ;
                }
              }
              default sr-mpls ;
              ncd:revise-date 2019-11-01 ;
            }
            leaf drop-upon-invalid {
              description 'The drop-upon-invalid of policy.'
                          ;
              type enumeration {
                enum disabled {
                  value 0 ;
                }
                enum enabled {
                  value 1 ;
                }
              }
              default disabled ;
            }
            leaf hsb-policy {
              description 'The configuration of policy hot-standby.'
                          ;
              type enumeration {
                enum none {
                  value 0 ;
                }
                enum enabled {
                  value 1 ;
                }
                enum disabled {
                  value 2 ;
                }
              }
              default none ;
              ncd:revise-date 2020-03-19 ;
            }
            leaf path-verification {
              description 'The configuration of policy path-verification.'
                          ;
              type enumeration {
                enum none {
                  value 0 ;
                }
                enum enabled {
                  value 1 ;
                }
                enum disabled {
                  value 2 ;
                }
              }
              default none ;
              ncd:revise-date 2021-01-21 ;
            }
            leaf traffic-statistics {
              description 'The traffic statistics of policy.'
                          ;
              type enumeration {
                enum enabled {
                  value 1 ;
                }
                enum disabled {
                  value 2 ;
                }
              }
              ncd:revise-date 2020-03-26 ;
            }
            leaf load-sharing {
              description 'Load sharing of SR policy.'
                          ;
              type enumeration {
                enum null {
                  value 0 ;
                }
                enum per-stream {
                  value 1 ;
                }
                enum per-packet {
                  value 2 ;
                }
                enum dlb {
                  value 3 ;
                }
              }
              ncd:revise-date 2020-05-28 ;
            }
            leaf sid-algo {
              description 'The SID algorithm definition number for SR policy.'
                          ;
              type uint8 {
                range 128..255 ;
              }
              ncd:revise-date 2021-01-21 ;
            }
            container end-point {
              description 'Configuration of policy color and end-point.'
                          ;
              presence 'Configuration of policy color and end-point.'
                       ;
              leaf color {
                description 'The color of policy.'
                            ;
                type uint32 {
                  range 1..4294967295 ;
                }
                mandatory true ;
              }
              choice address-type {
                description 'Address Selection Type.'
                            ;
                mandatory true ;
                case ipv4 {
                  description 'Configration ipv4 type of the end-point.'
                              ;
                  leaf end-point-v4 {
                    description 'The ipv4 address of end-point.'
                                ;
                    type ncd:ipv4-address {
                      pattern '([1-9]|[1-9][0-9]|1[0-9][0-9]|2[0-4][0-9]|25[0-5'
                            + '])(.([0-9]|[1-9][0-9]|1[0-9][0-9]|2[0-4][0-9]|25'
                            + '[0-5])){3}'
                              ;
                    }
                    mandatory true ;
                  }
                }
                case ipv6 {
                  description 'Configration ipv6 type of the end-point.'
                              ;
                  leaf end-point-v6 {
                    description 'The ipv6 address of end-point.'
                                ;
                    type ncd:ipv6-address {
                      pattern '((:|[0-9a-fA-F]{0,4}):)([0-9a-fA-F]{0,4}:){0,5}('
                            + '(([0-9a-fA-F]{0,4}:)?(:|[0-9a-fA-F]{0,4}))|(((25'
                            + '[0-5]|2[0-4][0-9]|[01]?[0-9]?[0-9])\.){3}(25[0-5'
                            + ']|2[0-4][0-9]|[01]?[0-9]?[0-9])))(%[\p{N}\p{L}]+'
                            + ')?'
                              ;
                      pattern '(([^:]+:){6}(([^:]+:[^:]+)|(.*\..*)))|((([^:]+:)'
                            + '*[^:]+)?::(([^:]+:)*[^:]+)?)(%.+)?'
                              ;
                    }
                    mandatory true ;
                  }
                }
              }
            }
            container srv6-binding-sid {
              description 'The configuration of SRv6 binding sid.'
                          ;
              choice srv6-bsid-type {
                description 'To assign the type of SRv6 binding sid. Two types.'
                            ;
                case auto {
                  status obsolete {
                    ncd:revise-date 2020-06-25 ;
                  }
                  description 'Auto SRv6 binding sid.'
                              ;
                  leaf auto {
                    status obsolete {
                      ncd:revise-date 2020-06-25 ;
                    }
                    description 'The type is auto.'
                                ;
                    type empty ;
                  }
                }
                case static {
                  description 'static SRv6 binding sid.'
                              ;
                  leaf static_srv6_bsid {
                    description 'The type is static.'
                                ;
                    type ncd:ipv6-address ;
                  }
                }
                case dynamic {
                  description 'Automatic generation of SRv6 binding sid.'
                              ;
                  leaf dynamic {
                    description 'Automatic generation of SRv6 binding sid.'
                                ;
                    type enumeration {
                      enum auto {
                        value 1 ;
                        description 'Automatic generation of SRv6 binding sid.'
                                    ;
                      }
                    }
                  }
                  ncd:revise-date 2020-11-17 ;
                }
              }
              ncd:revise-date 2020-05-28 ;
            }
            container ipv6-diffserv-mode {
              description 'The configuration of SRv6 policy differentiated serv'
                        + 'ice mode.'
                          ;
              choice mode {
                description 'The mode, including uniform-phb, uniform-non-phb a'
                          + 'nd pipe.'
                            ;
                case uniform-phb-mode {
                  description 'The uniform PHB mode.'
                              ;
                  leaf uniform-phb {
                    description 'The uniform PHB mode, inheriting PHB.'
                                ;
                    type empty ;
                    mandatory true ;
                  }
                  ncd:revise-date 2020-12-21 ;
                }
                case uniform-non-phb-mode {
                  description 'The uniform non-PHB mode.'
                              ;
                  leaf uniform-non-phb {
                    description 'The uniform non-PHB mode, L2VPN inherits 802.1'
                              + 'P and L3VPN inherits DSCP.'
                                ;
                    type empty ;
                    mandatory true ;
                  }
                  ncd:revise-date 2020-12-21 ;
                }
                case pipe-mode {
                  description 'The pipe mode.'
                              ;
                  leaf pipe {
                    description 'The pipe mode.'
                                ;
                    type empty ;
                    mandatory true ;
                  }
                  leaf dscp-value {
                    description 'DSCP value.'
                                ;
                    type uint8 {
                      range 0..63 ;
                    }
                    mandatory true ;
                  }
                }
              }
              ncd:revise-date 2020-11-23 ;
            }
            container sbfd {
              description 'Configuration of policy sbfd.'
                          ;
              choice sbfd-conf {
                description 'Whether to enable segment list sbfd.'
                            ;
                case enable {
                  description 'Enable policy sbfd.'
                              ;
                  leaf template-name {
                    description 'The template name of sbfd.'
                                ;
                    type string {
                      length 1..31 ;
                    }
                    mandatory true ;
                  }
                  container reverse-path {
                    description 'The S-BFD associatd reverse path.'
                                ;
                    choice path-type {
                      description 'Path Selection Type.'
                                  ;
                      case mpls-label {
                        description 'The S-BFD associatd reverse mpls label.'
                                    ;
                        leaf mpls-label {
                          description 'The S-BFD associatd reverse mpls label.'
                                      ;
                          type uint32 {
                            range 16..1048575 ;
                          }
                        }
                      }
                      case srv6-sid {
                        description 'The S-BFD associatd reverse SRv6 SID.'
                                    ;
                        leaf srv6-sid {
                          description 'The S-BFD associatd reverse SRv6 SID.'
                                      ;
                          type ncd:ipv6-address ;
                        }
                        ncd:revise-date 2020-11-27 ;
                      }
                    }
                    ncd:revise-date 2020-06-06 ;
                  }
                }
                case disable {
                  description 'Disable policy sbfd.'
                              ;
                  leaf disable {
                    description 'Disable policy sbfd.'
                                ;
                    type empty ;
                    mandatory true ;
                  }
                }
              }
              ncd:revise-date 2020-05-18 ;
            }
            container segment-list-sbfd {
              description 'Configuration of policy segment list sbfd.'
                          ;
              choice sbfd-conf {
                description 'Whether to enable segment list sbfd.'
                            ;
                case enable {
                  description 'Enable policy segment list sbfd.'
                              ;
                  leaf template-name {
                    description 'The template name of sbfd.'
                                ;
                    type string {
                      length 1..31 ;
                    }
                    mandatory true ;
                  }
                  leaf echo {
                    description 'The echo configuration of SR policy segment li'
                              + 'st sbfd.'
                                ;
                    type enumeration {
                      enum disabled {
                        value 0 ;
                      }
                      enum enabled {
                        value 1 ;
                      }
                    }
                    default disabled ;
                    ncd:revise-date 2021-03-17 ;
                  }
                }
                case disable {
                  description 'Disable policy segment list sbfd.'
                              ;
                  leaf disable {
                    description 'Disable policy segment list sbfd.'
                                ;
                    type empty ;
                    mandatory true ;
                  }
                }
              }
              ncd:revise-date 2020-04-07 ;
            }
            container candidate-path {
              description 'The configuration of policy candidate-path.'
                          ;
              list cp {
                description 'The configuration list of SR policy candidate-path.'
                            ;
                max-elements 16 ;
                key preference ;
                leaf preference {
                  description 'The candidate-path preference.'
                              ;
                  type uint32 {
                    range 0..4294967295 ;
                  }
                }
                leaf path-type {
                  description 'The path type of candidate-path.'
                              ;
                  type enumeration {
                    enum explicit {
                      value 0 ;
                    }
                    enum dynamic {
                      value 1 ;
                    }
                  }
                  default explicit ;
                  ncd:revise-date 2020-06-28 ;
                }
                leaf metric-type {
                  description 'The metric type of candidate-path.'
                              ;
                  type enumeration {
                    enum igp {
                      value 0 ;
                    }
                    enum delay {
                      value 1 ;
                    }
                    enum te {
                      value 2 ;
                    }
                  }
                  default igp ;
                  ncd:revise-date 2020-06-28 ;
                }
                container pce-delegate {
                  description 'The pce delegate function of candidate path.'
                              ;
                  leaf enable {
                    description 'Delegate candidate path to PCE.'
                                ;
                    type empty ;
                  }
                  container pce-addr {
                    description 'The PCE delegate address.'
                                ;
                    choice addr-type {
                      description 'Specify the PCE address type.'
                                  ;
                      case ipv4 {
                        description 'IPv4 address type.'
                                    ;
                        leaf pce-addr-ipv4 {
                          description 'PCE IPv4 address.'
                                      ;
                          type ncd:ipv4-address {
                            pattern '([1-9]|[1-9][0-9]|1[0-9][0-9]|2[0-4][0-9]|'
                                  + '25[0-5])(.([0-9]|[1-9][0-9]|1[0-9][0-9]|2['
                                  + '0-4][0-9]|25[0-5])){3}'
                                    ;
                          }
                        }
                      }
                      case ipv6 {
                        description 'IPv6 address type.'
                                    ;
                        leaf pce-addr-ipv6 {
                          description 'PCE IPv6 address.'
                                      ;
                          type ncd:ipv6-address {
                            pattern '([0-9a-fA-F]{1,4}:){7}([0-9a-fA-F]{0,4})$|'
                                  + '^([0-9a-fA-F]{1,4}:){1,6}(:[0-9a-fA-F]{0,4'
                                  + '}){1,6}$|^([:]{2})(([0-9a-fA-F]{1,4}:){0,6'
                                  + '})([0-9a-fA-F]{1,4})$|^([0-9a-fA-F]{1,4}:)'
                                  + '{6}([0-9]{1,3}.){3}([0-9]{1,3})$|^([0-9a-f'
                                  + 'A-F]{1,4}:){1,5}(:[0-9a-fA-F]{0,4}){1,5}(['
                                  + '0-9]{1,3}.){3}([0-9]{1,3})$|^([:]{2})(([0-'
                                  + '9a-fA-F]{1,4}:){0,5})([0-9]{1,3}.){3}([0-9'
                                  + ']{1,3})'
                                    ;
                          }
                        }
                      }
                    }
                  }
                  ncd:revise-date 2021-01-21 ;
                }
                container segment-list {
                  description 'The configuration of policy segment-list.'
                              ;
                  list sl {
                    description 'The configuration list of SR policy segment-li'
                              + 'st.'
                                ;
                    max-elements 16384 ;
                    key index ;
                    leaf index {
                      description 'The segment-list index.'
                                  ;
                      type uint8 {
                        range 1..255 ;
                      }
                    }
                    leaf weight {
                      description 'The segment-list weight.'
                                  ;
                      type uint32 {
                        range 1..4294967295 ;
                      }
                      default 1 ;
                    }
                    choice sl-path-type {
                      description 'Path Selection Type.'
                                  ;
                      case sr-path {
                        description 'The segment-list type is sr-path.'
                                    ;
                        container sr-path {
                          description 'The segment-list sr-path.'
                                      ;
                          choice path-type {
                            description 'Path Selection Type.'
                                        ;
                            case name-based {
                              description 'Based on the name of the sr path selection.'
                                          ;
                              leaf sr-path-name {
                                description 'The sr path name.'
                                            ;
                                type string {
                                  length 1..64 ;
                                }
                                mandatory true ;
                              }
                            }
                            case id-based {
                              description 'Based on the id of the sr path selection.'
                                          ;
                              leaf sr-path-id {
                                description 'The sr path ID.'
                                            ;
                                type uint16 {
                                  range 1..65535 ;
                                }
                                mandatory true ;
                              }
                            }
                          }
                        }
                        ncd:revise-date 2019-06-22 ;
                      }
                      case srv6-path {
                        description 'The segment-list type is srv6-path.'
                                    ;
                        container srv6-path {
                          description 'The segment-list srv6-path.'
                                      ;
                          presence srv6-path ;
                          leaf srv6-path-name {
                            description 'The srv6 path name.'
                                        ;
                            type string {
                              length 1..64 ;
                            }
                            mandatory true ;
                          }
                        }
                        ncd:revise-date 2019-11-01 ;
                      }
                      ncd:revise-date 2019-06-22 ;
                    }
                    container srv6-binding-sid {
                      description 'The configuration of SRv6 binding SID.'
                                  ;
                      choice srv6-bsid-type {
                        description 'To assign the type of SRv6 binding SID.'
                                    ;
                        case static {
                          description 'Static type of SRv6 binding SID.'
                                      ;
                          leaf static_srv6_bsid {
                            description 'The configuration of static SRv6 binding SID.'
                                        ;
                            type ncd:ipv6-address ;
                          }
                        }
                      }
                      ncd:revise-date 2021-03-17 ;
                    }
                    container reverse-path {
                      description 'The sbfd associatd reverse path.'
                                  ;
                      choice path-type {
                        description 'Path Selection Type.'
                                    ;
                        case srv6-sid {
                          description 'The sbfd associatd reverse SRv6 SID.'
                                      ;
                          leaf srv6-sid {
                            description 'The sbfd associatd reverse SRv6 SID.'
                                        ;
                            type ncd:ipv6-address ;
                          }
                        }
                      }
                      ncd:revise-date 2021-03-17 ;
                    }
                  }
                }
                container affinity {
                  description 'The affinity function configuration of candidate'
                            + '-path.'
                              ;
                  list bit-position {
                    description 'The configuration of affinity bit position.'
                                ;
                    max-elements 32 ;
                    key position ;
                    leaf affinity-type {
                      description 'The configuration of affinity type,exclude-a'
                                + 'ny(1)/include-any(2)/include-all(3).'
                                  ;
                      type enumeration {
                        enum exclude-any {
                          value 1 ;
                          description 'Configure the exclude-any affinity.'
                                      ;
                        }
                        enum include-any {
                          value 2 ;
                          description 'Configure the include-any affinity.'
                                      ;
                        }
                        enum include-all {
                          value 3 ;
                          description 'Configure the include-all affinity.'
                                      ;
                        }
                      }
                      mandatory true ;
                    }
                    leaf position {
                      description 'The configuration of affinity bit position.'
                                  ;
                      type uint16 {
                        range 0..31 ;
                      }
                    }
                  }
                  ncd:revise-date 2020-06-28 ;
                }
                container cspf-force-igp {
                  description 'Force IGP of the candidate path.'
                              ;
                  presence 'cspf force igp'
                           ;
                  choice igp-type {
                    description 'IGP type.'
                                ;
                    case force-ospf {
                      description 'Force OSPF.'
                                  ;
                      leaf ospf {
                        description 'Force OSPF.'
                                    ;
                        type empty ;
                        mandatory true ;
                      }
                      container ospf-process {
                        description 'Force OSPF process.'
                                    ;
                        presence 'force ospf process'
                                 ;
                        leaf process-id {
                          description 'Force OSPF process ID.'
                                      ;
                          type uint32 ;
                          mandatory true ;
                        }
                        container ospf-area {
                          description 'Force OSPF area.'
                                      ;
                          presence 'force ospf area'
                                   ;
                          leaf area-id {
                            description 'Force OSPF area ID.'
                                        ;
                            type ncd:ipv4-address ;
                            mandatory true ;
                          }
                        }
                      }
                    }
                    case force-isis {
                      description 'Force ISIS.'
                                  ;
                      leaf isis {
                        description 'Force ISIS.'
                                    ;
                        type empty ;
                        mandatory true ;
                      }
                      container isis-process {
                        description 'Force ISIS process.'
                                    ;
                        presence 'force isis process'
                                 ;
                        leaf process-id {
                          description 'Force ISIS process ID.'
                                      ;
                          type uint32 ;
                          mandatory true ;
                        }
                        container isis-level {
                          description 'Force ISIS level.'
                                      ;
                          presence 'force isis level'
                                   ;
                          leaf isis-level {
                            description 'Force ISIS level.'
                                        ;
                            type enumeration {
                              enum level-1 {
                                value 1 ;
                              }
                              enum level-2 {
                                value 2 ;
                              }
                            }
                            mandatory true ;
                          }
                        }
                      }
                    }
                  }
                  ncd:revise-date 2021-03-01 ;
                }
              }
            }
          }
          ncd:revise-date 2019-06-22 ;
        }
        container mbb {
          leaf cleanup-delay-time {
            description 'Configure cleanup delay time.'
                        ;
            type uint16 {
              range 0..600 ;
            }
            units second ;
            default 15 ;
          }
          leaf installation-delay-time {
            description 'Configure installation delay time.'
                        ;
            type uint16 {
              range 0..3600 ;
            }
            units second ;
            default 10 ;
          }
          ncd:revise-date 2018-07-02 ;
        }
        container policy-class {
          description "The configuration of SR tunnel's policy class."
                      ;
          list classes {
            description 'The value of policy-class(<0-7> and 255).'+"\n"
                      + 'The default value of policy-class is 255.'+"\n"
                      + '                  '+"\n"
                      + 'The policy-class range of 0 and 7 and 255 cannot be ex'
                      + 'isted the same time.'+"\n"
                      + 'For example 1, if we set the value 0 and 255 at the sa'
                      + 'me time (255 behind), the final value is 255.'+"\n"
                      + 'For example 2, if we set the value 255 and 0 at the sa'
                      + 'me time (0 behind ), the final value is 0.'+"\n"
                      + 'For example 3, if we set the value 0, 255, 1 and 3 at '
                      + 'the same time the final value is 1 and 3.'
                        ;
            key 'tnnl-name class'
                ;
            leaf tnnl-name {
              description 'The tunnel name.'
                          ;
              type ncd:ifname ;
            }
            leaf class {
              description 'The value of policy class.'
                          ;
              type uint8 ;
            }
          }
          ncd:revise-date 2018-09-25 ;
        }
        container tnnl-rate-limit {
          description 'The configuration of tunnel rate limit.'
                      ;
          presence 'configuration of tnnl-rate-limit'
                   ;
          list tunnel {
            description 'The configuration list of tunnel rate limit.'
                        ;
            max-elements 131072 ;
            key tunnel-name ;
            leaf tunnel-name {
              description 'The tunnel name'
                          ;
              type ncd:ifname ;
            }
            leaf mode {
              description 'The tunnel rate limit mode.'
                          ;
              type enumeration {
                enum blind {
                  value 1 ;
                }
                enum aware {
                  value 2 ;
                }
              }
              mandatory true ;
            }
            leaf cir {
              description CIR. ;
              type uint32 {
                range 0..4294967295 {
                  description 'The minimum value may be greater than 0, and the'
                            + ' maximum value may be less than 4294967295, depe'
                            + 'nding on the system.'
                              ;
                }
              }
              units kbps ;
              mandatory true ;
            }
            leaf cbs {
              description CBS. ;
              type uint32 {
                range 1..4294967295 {
                  description 'The minimum value may be greater than 1, and the'
                            + ' maximum value may be less than 4294967295, depe'
                            + 'nding on the system.'
                              ;
                }
              }
              units KB ;
              mandatory true ;
            }
            leaf pir {
              description PIR. ;
              type uint32 {
                range 1..4294967295 {
                  description 'The minimum value may be greater than 1, and the'
                            + ' maximum value may be less than 4294967295, depe'
                            + 'nding on the system.'
                              ;
                }
              }
              units kbps ;
              mandatory true ;
            }
            leaf pbs {
              description PBS. ;
              type uint32 {
                range 1..4294967295 {
                  description 'The minimum value may be greater than 1, and the'
                            + ' maximum value may be less than 4294967295, depe'
                            + 'nding on the system.'
                              ;
                }
              }
              units KB ;
              mandatory true ;
            }
          }
          ncd:revise-date 2018-12-17 ;
        }
        container color-templates {
          description 'The configuration of SR color template.'
                      ;
          list color-template {
            description 'The color template.'
                        ;
            key color ;
            leaf color {
              description 'The color value.'
                          ;
              type uint32 {
                range 1..4294967295 ;
              }
            }
            leaf template-type {
              description 'Configuration of odn template type.'
                          ;
              type enumeration {
                enum tunnel {
                  value 0 ;
                }
                enum policy {
                  value 1 ;
                }
              }
              default tunnel ;
              ncd:revise-date 2020-12-16 ;
            }
            leaf path-verification {
              description 'The configuration of template path-verification.'
                          ;
              type enumeration {
                enum none {
                  value 0 ;
                }
                enum enabled {
                  value 1 ;
                }
                enum disabled {
                  value 2 ;
                }
              }
              default none ;
              ncd:revise-date 2021-01-21 ;
            }
            container path-options {
              description 'The configuration of path option.'
                          ;
              list path-option {
                description 'The path option configuration of template.'
                            ;
                key option-id ;
                leaf option-id {
                  description 'The number of path-option.'
                              ;
                  type uint8 {
                    range 1 ;
                  }
                }
                choice path-type {
                  description 'Path Selection Type.'
                              ;
                  mandatory true ;
                  case dynamic {
                    description 'Dynamic path Selection Type.'
                                ;
                    leaf dynamic {
                      description 'The path type is dynamic.'
                                  ;
                      type empty ;
                      mandatory true ;
                    }
                  }
                }
              }
            }
            container pce-path-compute {
              description 'The configuration of PCE compute path.'
                          ;
              presence 'pce path compute.'
                       ;
              leaf enable {
                description 'Enable the configuration of PCE compute path.'
                            ;
                type empty ;
                mandatory true ;
              }
            }
            container pce-delegate {
              description 'The configuration of PCE delegate.'
                          ;
              presence 'pce delegate.'
                       ;
              leaf enable {
                description 'Enable the configuration of PCE delegate.'
                            ;
                type empty ;
                mandatory true ;
              }
            }
            container policy {
              description 'Configuration of sr policy color-template.'
                          ;
              leaf path-setup-type {
                description 'The path setup type of policy template.'
                            ;
                type enumeration {
                  enum sr-mpls {
                    value 0 ;
                  }
                  enum srv6 {
                    value 1 ;
                  }
                  enum auto {
                    value 2 ;
                  }
                }
              }
              leaf drop-upon-invalid {
                description 'The drop-upon-invalid of policy template.'
                            ;
                type enumeration {
                  enum disabled {
                    value 0 ;
                  }
                  enum enabled {
                    value 1 ;
                  }
                }
              }
              leaf traffic-statistics {
                description 'The traffic statistics of policy template.'
                            ;
                type enumeration {
                  enum enabled {
                    value 1 ;
                  }
                  enum disabled {
                    value 2 ;
                  }
                }
              }
              container sbfd {
                description 'Configuration of policy template sbfd.'
                            ;
                choice sbfd-conf {
                  description 'Whether to enable segment list sbfd.'
                              ;
                  case enable {
                    description 'Enable policy template sbfd.'
                                ;
                    leaf template-name {
                      description 'The template name of sbfd.'
                                  ;
                      type string {
                        length 1..31 ;
                      }
                      mandatory true ;
                    }
                  }
                  case disable {
                    description 'Disable policy template sbfd.'
                                ;
                    leaf disable {
                      description 'Disable policy template sbfd.'
                                  ;
                      type empty ;
                      mandatory true ;
                    }
                  }
                }
              }
              container segment-list-sbfd {
                description 'Configuration of policy template segment list sbfd.'
                            ;
                choice sbfd-conf {
                  description 'Whether to enable segment list sbfd.'
                              ;
                  case enable {
                    description 'Enable policy template segment list sbfd.'
                                ;
                    leaf template-name {
                      description 'The template name of sbfd.'
                                  ;
                      type string {
                        length 1..31 ;
                      }
                      mandatory true ;
                    }
                  }
                  case disable {
                    description 'Disable policy template segment list sbfd.'
                                ;
                    leaf disable {
                      description 'Disable policy template segment list sbfd.'
                                  ;
                      type empty ;
                      mandatory true ;
                    }
                  }
                }
              }
              container candidate-path {
                description 'The configuration of policy template candidate-pat'
                          + 'h.'
                            ;
                list cp {
                  description 'The configuration list of policy template candid'
                            + 'ate-path.'
                              ;
                  max-elements 16 ;
                  key preference ;
                  leaf preference {
                    description 'The candidate-path preference.'
                                ;
                    type uint32 {
                      range 0..4294967295 ;
                    }
                  }
                  leaf metric-type {
                    description 'The metric type of candidate-path.'
                                ;
                    type enumeration {
                      enum igp {
                        value 0 ;
                      }
                      enum delay {
                        value 1 ;
                      }
                      enum te {
                        value 2 ;
                      }
                    }
                    default igp ;
                  }
                  container affinity {
                    description 'The affinity function configuration of candida'
                              + 'te-path.'
                                ;
                    list bit-position {
                      description 'The configuration of affinity bit position.'
                                  ;
                      max-elements 32 ;
                      key position ;
                      leaf affinity-type {
                        description 'The configuration of affinity type,exclude'
                                  + '-any(1)/include-any(2)/include-all(3).'
                                    ;
                        type enumeration {
                          enum exclude-any {
                            value 1 ;
                            description 'Configure the exclude-any affinity.'
                                        ;
                          }
                          enum include-any {
                            value 2 ;
                            description 'Configure the include-any affinity.'
                                        ;
                          }
                          enum include-all {
                            value 3 ;
                            description 'Configure the include-all affinity.'
                                        ;
                          }
                        }
                        mandatory true ;
                      }
                      leaf position {
                        description 'The configuration of affinity bit position.'
                                    ;
                        type uint16 {
                          range 0..31 ;
                        }
                      }
                    }
                  }
                  container pce-delegate {
                    description 'The pce delegate function of candidate path.'
                                ;
                    leaf enable {
                      description 'Delegate candidate path to PCE.'
                                  ;
                      type empty ;
                    }
                    container pce-addr {
                      description 'The PCE address.'
                                  ;
                      choice addr-type {
                        description 'Specify the PCE address type.'
                                    ;
                        case ipv4 {
                          description 'IPv4 address type.'
                                      ;
                          leaf pce-addr-ipv4 {
                            description 'PCE IPv4 address.'
                                        ;
                            type ncd:ipv4-address {
                              pattern '([1-9]|[1-9][0-9]|1[0-9][0-9]|2[0-4][0-9'
                                    + ']|25[0-5])(.([0-9]|[1-9][0-9]|1[0-9][0-9'
                                    + ']|2[0-4][0-9]|25[0-5])){3}'
                                      ;
                            }
                          }
                        }
                        case ipv6 {
                          description 'IPv6 address type.'
                                      ;
                          leaf pce-addr-ipv6 {
                            description 'PCE IPv6 address.'
                                        ;
                            type ncd:ipv6-address {
                              pattern '([0-9a-fA-F]{1,4}:){7}([0-9a-fA-F]{0,4})'
                                    + '$|^([0-9a-fA-F]{1,4}:){1,6}(:[0-9a-fA-F]'
                                    + '{0,4}){1,6}$|^([:]{2})(([0-9a-fA-F]{1,4}'
                                    + ':){0,6})([0-9a-fA-F]{1,4})$|^([0-9a-fA-F'
                                    + ']{1,4}:){6}([0-9]{1,3}.){3}([0-9]{1,3})$'
                                    + '|^([0-9a-fA-F]{1,4}:){1,5}(:[0-9a-fA-F]{'
                                    + '0,4}){1,5}([0-9]{1,3}.){3}([0-9]{1,3})$|'
                                    + '^([:]{2})(([0-9a-fA-F]{1,4}:){0,5})([0-9'
                                    + ']{1,3}.){3}([0-9]{1,3})'
                                      ;
                            }
                          }
                        }
                      }
                    }
                    ncd:revise-date 2021-01-21 ;
                  }
                  container cspf-force-igp {
                    description 'Force IGP of the candidate path.'
                                ;
                    presence 'cspf force igp'
                             ;
                    choice igp-type {
                      description 'IGP type.'
                                  ;
                      case force-ospf {
                        description 'Force OSPF.'
                                    ;
                        leaf ospf {
                          description 'Force OSPF.'
                                      ;
                          type empty ;
                          mandatory true ;
                        }
                        container ospf-process {
                          description 'Force OSPF process.'
                                      ;
                          presence 'force ospf process'
                                   ;
                          leaf process-id {
                            description 'Force OSPF process ID.'
                                        ;
                            type uint32 ;
                            mandatory true ;
                          }
                          container ospf-area {
                            description 'Force OSPF area.'
                                        ;
                            presence 'force ospf area'
                                     ;
                            leaf area-id {
                              description 'Force OSPF area ID.'
                                          ;
                              type ncd:ipv4-address ;
                              mandatory true ;
                            }
                          }
                        }
                      }
                      case force-isis {
                        description 'Force ISIS.'
                                    ;
                        leaf isis {
                          description 'Force ISIS.'
                                      ;
                          type empty ;
                          mandatory true ;
                        }
                        container isis-process {
                          description 'Force ISIS process.'
                                      ;
                          presence 'force isis process'
                                   ;
                          leaf process-id {
                            description 'Force ISIS process ID.'
                                        ;
                            type uint32 ;
                            mandatory true ;
                          }
                          container isis-level {
                            description 'Force ISIS level.'
                                        ;
                            presence 'force isis level'
                                     ;
                            leaf isis-level {
                              description 'Force ISIS level.'
                                          ;
                              type enumeration {
                                enum level-1 {
                                  value 1 ;
                                }
                                enum level-2 {
                                  value 2 ;
                                }
                              }
                              mandatory true ;
                            }
                          }
                        }
                      }
                    }
                    ncd:revise-date 2021-03-01 ;
                  }
                }
              }
              ncd:revise-date 2020-12-16 ;
            }
          }
          ncd:revise-date 2019-01-15 ;
        }
        container delay {
          description 'SR TE delay function of management object'
                      ;
          leaf delay_linkup {
            description 'The linkup of time delay response.'
                        ;
            type uint8 {
              range 0..120 ;
            }
            units second ;
            default 0 ;
          }
          ncd:revise-date 2019-02-15 ;
        }
        container reoptimize {
          description 'The global configuration of reoptimization.'
                      ;
          leaf frequency {
            description 'The tunnels reoptimize timer frequency in global mode.'
                      + ' Configure tnnl-reoptimize enable node to specify whic'
                      + 'h tunnel uses reoptimize function.'
                        ;
            type int32 {
              range 30..604800 ;
            }
            units second ;
          }
          leaf delay-decrease {
            description 'Specify delay decrease event can triger reoptimize.'
                        ;
            type empty ;
            ncd:revise-date 2020-03-28 ;
          }
          leaf link-up {
            description 'Specify link-up event can triger reoptimize.'
                        ;
            type empty ;
          }
          ncd:revise-date 2019-02-15 ;
        }
        container color-maps {
          description 'The configuration of SR color mapping relation.'
                      ;
          list color-map {
            description 'The SR color mapping.'
                        ;
            key color ;
            leaf color {
              description 'The color value.'
                          ;
              type uint32 {
                range 1..4294967295 ;
              }
            }
            leaf sid-algo {
              description 'The SR SID algorithm definition number.'
                          ;
              type uint8 {
                range 128..255 ;
              }
            }
          }
          ncd:revise-date 2019-12-20 ;
        }
        container flex-algo-define {
          description 'The configuration of SR flexible algorithm definition.'
                      ;
          list flex-algo {
            description 'The SR flexible algorithm definition.'
                        ;
            key number ;
            leaf number {
              description 'The SR flexible algorithm definition number.'
                          ;
              type uint8 {
                range 128..255 ;
              }
            }
            leaf advertise-def {
              description 'Advertise SR flexible algorithm definition.'
                          ;
              type empty ;
            }
            leaf metric-type {
              description 'Metric type.'
                          ;
              type enumeration {
                enum igp {
                  value 0 ;
                }
                enum te {
                  value 1 ;
                }
                enum delay {
                  value 2 ;
                }
              }
              default igp ;
            }
            leaf priority {
              description Priority. ;
              type uint8 {
                range 0..255 ;
              }
              default 0 ;
            }
            container affinity {
              description 'The affinity configuration.'
                          ;
              container bit-positions {
                description 'The configuration of affinity bit position.The aff'
                          + 'inity of bit and name types is mutually exclusive.'
                            ;
                list bit-position {
                  description 'The configuration of affinity bit position.The a'
                            + 'ffinity of bit and name types is mutually exclus'
                            + 'ive.'
                              ;
                  key position ;
                  leaf affinity-type {
                    description 'The configuration of affinity type,exclude-any'
                              + '(1)/include-any(2)/include-all(3).'
                                ;
                    type enumeration {
                      enum exclude-any {
                        value 1 ;
                        description 'Configure the exclude-any affinity.'
                                    ;
                      }
                      enum include-any {
                        value 2 ;
                        description 'Configure the include-any affinity.'
                                    ;
                      }
                      enum include-all {
                        value 3 ;
                        description 'Configure the include-all affinity.'
                                    ;
                      }
                    }
                    mandatory true ;
                  }
                  leaf position {
                    description 'The configuration of affinity bit position.'
                                ;
                    type uint8 {
                      range 0..31 ;
                    }
                  }
                }
              }
              container bit-names {
                description 'The configuration of affinity name.The affinity of'
                          + ' bit and name types is mutually exclusive.'
                            ;
                list bit-name {
                  description 'The configuration of affinity name.The affinity '
                            + 'of bit and name types is mutually exclusive.'
                              ;
                  key name ;
                  leaf affinity-type {
                    description 'The configuration of affinity type,exclude-any'
                              + '(1)/include-any(2)/include-all(3).'
                                ;
                    type enumeration {
                      enum exclude-any {
                        value 1 ;
                        description 'Configure the exclude-any affinity.'
                                    ;
                      }
                      enum include-any {
                        value 2 ;
                        description 'Configure the include-any affinity.'
                                    ;
                      }
                      enum include-all {
                        value 3 ;
                        description 'Configure the include-all affinity.'
                                    ;
                      }
                    }
                    mandatory true ;
                  }
                  leaf name {
                    description 'The configuration of affinity bit name.'
                                ;
                    type string {
                      length 1..32 ;
                    }
                  }
                }
              }
            }
          }
          ncd:revise-date 2019-12-20 ;
        }
        container policy-group {
          description 'The configuration of SR policy group.'
                      ;
          presence 'The configuration of SR policy group.'
                   ;
          list group {
            description 'The SR policy group configuration list.'
                        ;
            max-elements 65535 ;
            key group-id ;
            leaf group-id {
              description 'The policy group ID.'
                          ;
              type uint16 {
                range 1..65535 ;
              }
            }
            container end-point {
              description 'The configuration of policy group end-point.'
                          ;
              presence 'The configuration of policy group end-point.'
                       ;
              choice address-type {
                description 'The address type of end-point.'
                            ;
                mandatory true ;
                case ipv4 {
                  description 'The IPv4 address type of end-point.'
                              ;
                  leaf end-point-v4 {
                    description 'The IPv4 address of end-point.'
                                ;
                    type ncd:ipv4-address ;
                    mandatory true ;
                  }
                }
                case ipv6 {
                  description 'The IPv6 address type of the end-point.'
                              ;
                  leaf end-point-v6 {
                    description 'The IPv6 address of end-point.'
                                ;
                    type ncd:ipv6-address ;
                    mandatory true ;
                  }
                }
              }
            }
            container color {
              description 'The configuration of policy group color.'
                          ;
              presence 'The configuration of policy group color.'
                       ;
              list colors {
                description 'The color configuration list.'
                            ;
                max-elements 130 ;
                key 'color dscp-address-type'
                    ;
                leaf color {
                  description 'The color value.'
                              ;
                  type uint32 {
                    range 1..4294967295 ;
                  }
                }
                leaf dscp-address-type {
                  description 'The DSCP address type including IPv4 and IPv6.'
                              ;
                  type enumeration {
                    enum ipv4 {
                      value 1 ;
                    }
                    enum ipv6 {
                      value 2 ;
                    }
                  }
                }
                choice dscp-type {
                  description 'The type of DSCP.'
                              ;
                  mandatory true ;
                  case dscp-value {
                    description 'Configure DSCP value.'
                                ;
                    leaf value {
                      description 'Configure DSCP value in range mode, support '
                                + 'single DSCP value or range(max num:32;spacin'
                                + 'g mark:,) in <0-63>. For example,"1,3-5,10,2'
                                + '0-30",etc.The DSCP values of different color'
                                + ' in the same policy group cannot overlap.'
                                  ;
                      type ncd:range {
                        pattern '(((([0-9]|[1-5][0-9]|6[0-3])-([0-9]|[1-5][0-9]'
                              + '|6[0-3]))|([0-9]|[1-5][0-9]|6[0-3]))(,((([0-9]'
                              + '|[1-5][0-9]|6[0-3])-([0-9]|[1-5][0-9]|6[0-3]))'
                              + '|([0-9]|[1-5][0-9]|6[0-3]))){0,31})'
                                ;
                      }
                      mandatory true ;
                    }
                  }
                  case dscp-default {
                    description 'Configure default SR policy.'
                                ;
                    leaf default {
                      description 'The default SR policy. For the same address '
                                + 'type in the same policy group, only one colo'
                                + 'r can be configured with default.'
                                  ;
                      type empty ;
                      mandatory true ;
                    }
                  }
                }
              }
            }
          }
          ncd:revise-date 2020-06-01 ;
        }
      }
    }
  }
  container operation {
    config false ;
    container manual-reopt {
      description 'Operation about manual-reopt.'
                  ;
      leaf tunnel-id {
        description 'Specify the tunnel(s) to be reoptimized.'
                    ;
        type uint32 {
          range 1..65535 ;
        }
      }
      leaf all {
        description 'Configure all tunnels to be reoptimized.'
                    ;
        type empty ;
      }
    }
    ncd:revise-date 2019-02-15 ;
  }
  notification sr-tunnel {
    description 'The SR tunnel information.'
                ;
    list tunnel {
      config false ;
      description 'The SR tunnel list.'
                  ;
      key tunnel-id ;
      leaf tunnel-id {
        description 'The tunnel ID.'
                    ;
        type uint16 ;
      }
      leaf ingress-id {
        description 'The ingress LSR ID.'
                    ;
        type ncd:ipv4-address ;
      }
      leaf egress-id {
        description 'The egress LSR ID.'
                    ;
        type ncd:ipv4-address ;
      }
      leaf v6-ingress-id {
        description 'The ingress v6 LSR ID.'
                    ;
        type ncd:ipv6-address ;
        ncd:revise-date 2020-09-11 ;
      }
      leaf v6-egress-id {
        description 'The egress v6 LSR ID.'
                    ;
        type ncd:ipv6-address ;
        ncd:revise-date 2020-09-11 ;
      }
      leaf oper-status {
        description 'The operation status of tunnel.'
                    ;
        type enumeration {
          enum unknown {
            value 0 ;
          }
          enum up {
            value 1 ;
          }
          enum down {
            value 2 ;
          }
          enum wtr {
            value 4 ;
          }
        }
      }
      leaf master-lsp-id {
        description 'The master lsp identifier.'
                    ;
        type uint16 ;
      }
      leaf slave-lsp-id {
        description 'The lsp identifier of slave.'
                    ;
        type uint16 ;
      }
      leaf hsb-status {
        description 'The hsb status of tunnel.'
                    ;
        type enumeration {
          enum none {
            value 0 ;
          }
          enum ready {
            value 1 ;
          }
          enum active {
            value 2 ;
          }
        }
      }
      leaf master-splice-label {
        description 'The master splice label.'
                    ;
        type uint32 ;
      }
      leaf slave-splice-label {
        description 'The splice label of slave.'
                    ;
        type uint32 ;
      }
      leaf report-reason {
        description 'The reason of report.'
                    ;
        type enumeration {
          enum creat_succ {
            value 1 ;
          }
          enum creat_err {
            value 2 ;
          }
          enum delete_succ {
            value 3 ;
          }
          enum delete_err {
            value 4 ;
          }
          enum chg_succ {
            value 5 ;
          }
          enum chg_err {
            value 6 ;
          }
          enum state_chg {
            value 7 ;
          }
          enum hsb_binding_succ {
            value 8 ;
          }
          enum hsb_delete {
            value 9 ;
          }
          enum hsb_switch {
            value 10 ;
          }
          enum hsb_unswitch {
            value 11 ;
          }
        }
      }
    }
    list tunnel-path {
      config false ;
      description 'The path of segment-routing tunnel LSP.'
                  ;
      key 'tunnel-id lsp-role hop-index'
          ;
      leaf tunnel-id {
        description 'The tunnel ID.'
                    ;
        type uint16 ;
      }
      leaf lsp-role {
        description "The lsp role of tunnel,it's behalf of master while the val"
                  + "ue is 1 ,it's behalf of backup while the value is 2."
                    ;
        type enumeration {
          enum master {
            value 1 ;
          }
          enum slave {
            value 2 ;
          }
        }
      }
      leaf hop-index {
        description 'The index of sr-path hop.'
                    ;
        type uint16 ;
      }
      leaf lsp-id {
        description 'The lsp identifier.'
                    ;
        type uint16 ;
      }
      leaf sid-type {
        description 'The sid type.'
                    ;
        type enumeration {
          enum default {
            value 0 ;
          }
          enum node-id-v4 {
            value 1 ;
          }
          enum node-id-v6 {
            value 2 ;
          }
          enum adj-id-v4 {
            value 3 ;
          }
          enum adj-id-v6 {
            value 4 ;
          }
          enum unnum-adj-id-v4 {
            value 5 ;
          }
          enum srv6-sid {
            value 14 ;
          }
          enum srv6-node-id {
            value 18 ;
          }
          enum srv6-adj-id {
            value 19 ;
          }
          enum srv6-link-local {
            value 20 ;
          }
        }
      }
      leaf sid-val {
        description 'The sid value.'
                    ;
        type uint32 ;
      }
      leaf node-ip {
        description 'The node IP.'
                    ;
        type ncd:ipv4-address ;
      }
      leaf adj-local-rid {
        description 'The local router id of adjacency.'
                    ;
        type ncd:ipv4-address ;
      }
      leaf adj-local-ip {
        description 'The local ip of adjacency.'
                    ;
        type ncd:ipv4-address ;
      }
      leaf adj-local-id {
        description 'The local ID of adjacency.'
                    ;
        type uint32 ;
        ncd:revise-date 2019-07-29 ;
      }
      leaf adj-peer-rid {
        description 'The peer router id of adjacency.'
                    ;
        type ncd:ipv4-address ;
      }
      leaf adj-peer-ip {
        description 'The peer ip of adjacency.'
                    ;
        type ncd:ipv4-address ;
      }
      leaf adj-peer-id {
        description 'The peer ID of adjacency.'
                    ;
        type uint32 ;
        ncd:revise-date 2019-07-29 ;
      }
      leaf srv6-sid {
        description 'The SRv6 sid value.'
                    ;
        type ncd:ipv6-address ;
        ncd:revise-date 2020-09-11 ;
      }
      leaf v6-node-ip {
        description 'The node IPv6 address.'
                    ;
        type ncd:ipv6-address ;
        ncd:revise-date 2020-09-11 ;
      }
      leaf v6-adj-local-ip {
        description 'The local IPv6 address of adjacency.'
                    ;
        type ncd:ipv6-address ;
        ncd:revise-date 2020-09-11 ;
      }
      leaf v6-local-id {
        description 'The local ID of v6 adjacency.'
                    ;
        type uint32 ;
        ncd:revise-date 2020-09-11 ;
      }
      leaf v6-adj-peer-ip {
        description 'The peer IPv6 address of adjacency.'
                    ;
        type ncd:ipv6-address ;
        ncd:revise-date 2020-09-11 ;
      }
      leaf v6-peer-id {
        description 'The peer ID of v6 adjacency.'
                    ;
        type uint32 ;
        ncd:revise-date 2020-09-11 ;
      }
    }
  }
  notification static-sr {
    description 'The static SR tunnel information.'
                ;
    list tunnel {
      config false ;
      description 'The staic SR tunnel list.'
                  ;
      key tunnel-id ;
      leaf tunnel-id {
        description 'The tunnel ID.'
                    ;
        type uint32 ;
      }
      leaf report-reason {
        description 'The reason of report.'
                    ;
        type enumeration {
          enum create {
            value 1 ;
          }
          enum delete {
            value 2 ;
          }
          enum associated-status-change {
            value 3 ;
          }
        }
      }
      leaf associated-status {
        description 'The associated status of tunnel.'
                    ;
        type enumeration {
          enum disabled {
            value 1 ;
          }
          enum unbound {
            value 2 ;
          }
          enum bound {
            value 3 ;
          }
        }
      }
    }
    ncd:revise-date 2020-04-10 ;
  }
}
