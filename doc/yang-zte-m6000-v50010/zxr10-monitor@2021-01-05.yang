module zxr10-monitor {
  namespace 'http://www.zte.com.cn/zxr10/netconf/schema/rosng/monitor'
            ;
  prefix monitor ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2021-01-05 {
    description '1 Add default-vxlans with feature default-vxlan-feature to sup'
              + 'port destination VXLAN:'+"\n"
              + '/configuration/monitor/sessions/session/default-vxlans;'+"\n"
              + '2 Add remote-monitor with feature remote-monitor-feature to su'
              + 'pport RSPAN:'+"\n"
              + '/configuration/monitor/sessions/session/default-interfaces/def'
              + 'ault-interface/remote-monitor;'+"\n"
              + '3 Add encap-remote-monitor with feature encap-remote-monitor-f'
              + 'eature to support ERSPAN:'+"\n"
              + '/configuration/monitor/sessions/session/default-gres/default-g'
              + 're/encap-remote-monitor;'+"\n"
              + '4 Add switchvlan-sources with feature switchvlan-source-featur'
              + 'e to support switchvlan as monitor source:'+"\n"
              + '/configuration/monitor/sessions/session/sources/switchvlan-sou'
              + 'rces.'+"\n"
              + '5 Add cpu-sources with feature cpu-source-feature to support C'
              + 'PU monitor source:'+"\n"
              + '/configuration/monitor/sessions/session/sources/cpu-sources.'
                ;
  }
  revision 2020-06-15 {
    description 'Support description for seesion:'+"\n"
              + '/configuration/monitor/sessions/session/description.'
                ;
  }
  revision 2020-04-13 {
    description '1. Support multi-acl-destinations with feature multi-acl-featu'
              + 're:'+"\n"
              + '/configuration/monitor/sessions/session/multi-acl-rules;'+"\n"
              + '2. Support default-interfaces with feature default-interface-f'
              + 'eature:'+"\n"
              + '/configuration/monitor/sessions/session/default-interfaces.'+"\n"
              + '3. Add enumeration value ipv4-mixed-acl:'+"\n"
              + '/configuration/monitor/sessions/session/acl-rules/acl-rule/acl'
              + '-type'
                ;
  }
  revision 2017-05-16 {
    description 'add destination of gre.'
                ;
  }
  revision 2017-04-14 {
    description '1.add vpws case to /configuration/monitor/sessions/session/acl'
              + '-rules/acl-rule/destination-type/.'+"\n"
              + '2.add default-vpwss container to /configuration/monitor/sessio'
              + 'ns/session/. '+"\n"
              + '3.add default-observers container to /configuration/monitor/se'
              + 'ssions/session/. '+"\n"
              + '4.add rule-observers container to /configuration/monitor/sessi'
              + 'ons/session/.'+"\n"
              + '5.add flow-type leaf to /configuration/monitor/sessions/sessio'
              + 'n/sources/interface-source/.'+"\n"
              + '6.add vpws-source list to /configuration/monitor/sessions/sess'
              + 'ion/sources/.'
                ;
  }
  revision 2015-07-13 {
    description 'Initial version'
                ;
  }
  feature multi-acl-feature {
    description 'Mark multiple ACL destination.'
                ;
  }
  feature default-interface-feature {
    description 'Mark multiple default destination.'
                ;
  }
  feature default-vxlan-feature {
    description 'Mark default destination VXLAN.'
                ;
  }
  feature switchvlan-source-feature {
    description 'Mark switchvlan source.'
                ;
  }
  feature remote-monitor-feature {
    description 'Mark remote monitor.'
                ;
  }
  feature encap-remote-monitor-feature {
    description 'Mark encapsulated remote monitor.'
                ;
  }
  feature cpu-source-feature {
    description 'Mark CPU source.'
                ;
  }
  typedef flow-type {
    type enumeration {
      enum default {
        value 0 ;
      }
      enum bgp-default {
        value 1 ;
      }
      enum bgp-config {
        value 2 ;
      }
      enum bgp-known {
        value 3 ;
      }
      enum ospf-default {
        value 4 ;
      }
      enum ospf-config {
        value 5 ;
      }
      enum ospf-known {
        value 6 ;
      }
      enum isis-default {
        value 7 ;
      }
      enum isis-known {
        value 8 ;
      }
      enum rip {
        value 9 ;
      }
      enum pim-suppress {
        value 10 ;
      }
      enum pim {
        value 11 ;
      }
      enum igmp-suppress {
        value 12 ;
      }
      enum igmp-default {
        value 13 ;
      }
      enum msdp-default {
        value 14 ;
      }
      enum msdp-known {
        value 15 ;
      }
      enum mld {
        value 16 ;
      }
      enum mvpn {
        value 17 ;
      }
      enum msdp-config {
        value 18 ;
      }
      enum ospf-hello {
        value 19 ;
      }
      enum isis-hello {
        value 20 ;
      }
      enum pim-hello {
        value 21 ;
      }
      enum pim-known {
        value 22 ;
      }
      enum ldp-default {
        value 25 ;
      }
      enum ldp-config {
        value 26 ;
      }
      enum ldp-known {
        value 27 ;
      }
      enum ldp-udp {
        value 28 ;
      }
      enum rsvp {
        value 29 ;
      }
      enum ldp-known-hello {
        value 30 ;
      }
      enum pcep-default {
        value 31 ;
      }
      enum pcep-known {
        value 32 ;
      }
      enum telnet-default {
        value 35 ;
      }
      enum telnet-known {
        value 36 ;
      }
      enum snmp-default {
        value 37 ;
      }
      enum snmp-known {
        value 38 ;
      }
      enum ssh-default {
        value 39 ;
      }
      enum ssh-known {
        value 40 ;
      }
      enum rta-default {
        value 41 ;
      }
      enum rta-known {
        value 42 ;
      }
      enum http-default {
        value 51 ;
      }
      enum tacacs+ {
        value 52 ;
      }
      enum radius {
        value 54 ;
      }
      enum dhcp {
        value 55 ;
      }
      enum ntp {
        value 56 ;
      }
      enum ftp-default {
        value 57 ;
      }
      enum ftp-known {
        value 58 ;
      }
      enum tftp {
        value 59 ;
      }
      enum lsp-ping {
        value 60 ;
      }
      enum mac-ping {
        value 61 ;
      }
      enum bfd-default {
        value 62 ;
      }
      enum bfd-known {
        value 63 ;
      }
      enum vrrp {
        value 64 ;
      }
      enum ipsec {
        value 65 ;
      }
      enum l2tp {
        value 66 ;
      }
      enum icmp-app {
        value 67 ;
      }
      enum portal {
        value 68 ;
      }
      enum eap-authentication {
        value 69 ;
      }
      enum dns {
        value 72 ;
      }
      enum http-known {
        value 74 ;
      }
      enum twamp-tcp-default {
        value 75 ;
      }
      enum twamp-tcp-known {
        value 76 ;
      }
      enum twamp-udp-default {
        value 77 ;
      }
      enum twamp-udp-known {
        value 78 ;
      }
      enum sibmgr-known {
        value 80 ;
      }
      enum radius-coa-dm {
        value 82 ;
      }
      enum dhcp-known {
        value 83 ;
      }
      enum sqa-general-flow {
        value 84 ;
      }
      enum meap-authentication {
        value 86 ;
      }
      enum nhrp {
        value 87 ;
      }
      enum openflow-default {
        value 88 ;
      }
      enum openflow-known {
        value 89 ;
      }
      enum pcp {
        value 90 ;
      }
      enum icmp-default {
        value 91 ;
      }
      enum icmp-control {
        value 92 ;
      }
      enum tcp-default {
        value 93 ;
      }
      enum udp-default {
        value 94 ;
      }
      enum nd {
        value 95 ;
      }
      enum ah {
        value 96 ;
      }
      enum esp {
        value 97 ;
      }
      enum gre {
        value 98 ;
      }
      enum sctp-default {
        value 99 ;
      }
      enum arp-suppress {
        value 101 ;
      }
      enum arp-default {
        value 102 ;
      }
      enum ppp-connect {
        value 103 ;
      }
      enum arp-known {
        value 104 ;
      }
      enum hdlc-control {
        value 105 ;
      }
      enum fr-control {
        value 107 ;
      }
      enum lacp {
        value 109 ;
      }
      enum udld {
        value 110 ;
      }
      enum lldp {
        value 111 ;
      }
      enum stp {
        value 112 ;
      }
      enum pppoe-disc {
        value 113 ;
      }
      enum pppoe-session {
        value 114 ;
      }
      enum efm {
        value 119 ;
      }
      enum slow-cfm {
        value 120 ;
      }
      enum mc-elam {
        value 121 ;
      }
      enum ssm {
        value 122 ;
      }
      enum evb {
        value 123 ;
      }
      enum nd-known {
        value 124 ;
      }
      enum pppoe-keepalive {
        value 127 ;
      }
      enum pppoe-padi {
        value 128 ;
      }
      enum noarp {
        value 142 ;
      }
      enum nosupervlan {
        value 143 ;
      }
      enum vplsmac {
        value 144 ;
      }
      enum netflow-up {
        value 146 ;
      }
      enum nond {
        value 147 ;
      }
      enum pmtu {
        value 148 ;
      }
      enum special-multidata {
        value 151 ;
      }
      enum ttl1 {
        value 152 ;
      }
      enum ipfrag {
        value 154 ;
      }
      enum ipoption {
        value 155 ;
      }
      enum ipv6-special {
        value 156 ;
      }
      enum netflow-down {
        value 159 ;
      }
      enum nosa {
        value 160 ;
      }
      enum unihttp {
        value 161 ;
      }
      enum special-multidata6 {
        value 163 ;
      }
      enum tunnel-special {
        value 165 ;
      }
      enum nat-alg {
        value 167 ;
      }
      enum nat-nonat {
        value 168 ;
      }
      enum nat-pcp {
        value 169 ;
      }
      enum nat-p2mp-local {
        value 170 ;
      }
      enum ptp-normal {
        value 174 ;
      }
      enum mpls-oam-cv {
        value 176 ;
      }
      enum ip-unreachable {
        value 177 ;
      }
      enum atm-oam {
        value 178 ;
      }
      enum slow-mpls-tp-oam {
        value 180 ;
      }
      enum mpls-tp-aps {
        value 182 ;
      }
      enum multi-hop-access {
        value 183 ;
      }
      enum up-slow-cfm {
        value 184 ;
      }
      enum sdc-access {
        value 185 ;
      }
      enum unihttp_syn {
        value 186 ;
      }
      enum down-fast-cfm {
        value 187 ;
      }
      enum up-fast-cfm {
        value 188 ;
      }
      enum radius-proxy-traffic {
        value 191 ;
      }
      enum ipv6-ah-or-esp {
        value 195 ;
      }
      enum openflow-controller {
        value 196 ;
      }
      enum openflow-normal {
        value 197 ;
      }
      enum cps-log {
        value 199 ;
      }
      enum no-nhrp {
        value 200 ;
      }
      enum fast-unihttp {
        value 202 ;
      }
      enum erps {
        value 203 ;
      }
      enum uni-arp-default {
        value 204 ;
      }
      enum uni-arp-known {
        value 205 ;
      }
      enum uni-nd {
        value 206 ;
      }
      enum uni-dhcp {
        value 208 ;
      }
      enum openflow-tblmissing {
        value 209 ;
      }
      enum arp-nni {
        value 210 ;
      }
      enum openflow-lldp {
        value 211 ;
      }
      enum openflow-arp {
        value 212 ;
      }
      enum openflow-dhcp {
        value 213 ;
      }
      enum openflow-bgp {
        value 214 ;
      }
      enum openflow-ospf {
        value 215 ;
      }
      enum openflow-icmp {
        value 216 ;
      }
      enum static-arp-trust {
        value 217 ;
      }
      enum vrrp-known {
        value 218 ;
      }
      enum arp-protect {
        value 223 ;
      }
      enum nd-protect {
        value 224 ;
      }
    }
  }
  container configuration {
    description 'MONITOR module configuration model'
                ;
    container monitor {
      description 'MONITOR module configuration root node'
                  ;
      container sessions {
        description 'MONITOR sessions'
                    ;
        list session {
          description 'MONITOR session'
                      ;
          key session-id ;
          leaf session-id {
            description 'MONITOR session ID'
                        ;
            type uint32 {
              range 1..64 ;
            }
          }
          leaf description {
            description 'Description for use.'
                        ;
            type ncd:string-with-blank {
              length 1..79 ;
            }
            ncd:revise-date 2020-06-15 ;
          }
          container acl-rules {
            description 'MONITOR destinations for acl rules'
                        ;
            list acl-rule {
              description 'MONITOR destination for one acl rule'
                          ;
              key 'acl-type acl-name'
                  ;
              leaf acl-type {
                description 'The ACL type'
                            ;
                type enumeration {
                  enum ipv4-acl {
                    value 1 ;
                    description 'The type of ACL is IPv4'
                                ;
                  }
                  enum ipv6-acl {
                    value 2 ;
                    description 'The type of ACL is IPv6'
                                ;
                  }
                  enum link-acl {
                    value 3 ;
                    description 'The type of ACL is LINK'
                                ;
                  }
                  enum ipv4-mixed-acl {
                    value 4 ;
                    description 'The type of ACL is IPv4 mixed'
                                ;
                  }
                }
              }
              leaf acl-name {
                description 'The ACL name'
                            ;
                type string {
                  length 1..31 ;
                }
              }
              choice destination-type {
                description 'The type of MONITOR destination'
                            ;
                mandatory true ;
                case interface {
                  description 'The type of MONITOR destination is interface'
                              ;
                  leaf interface-name {
                    description 'The interface name'
                                ;
                    type ncd:ifname ;
                  }
                }
                case vpws {
                  description 'The type of MONITOR destination is vpws.'
                              ;
                  leaf vpws-name {
                    description 'The vpws-for-monitor name'
                                ;
                    type string {
                      length 1..32 ;
                    }
                  }
                  ncd:revise-date 2017-04-14 ;
                }
              }
            }
          }
          container default {
            description 'The default MONITOR destination'
                        ;
            presence 'Default destination interface of mirror'
                     ;
            choice destination-type {
              description 'The type of MONITOR destination'
                          ;
              mandatory true ;
              case interface {
                description 'The type of MONITOR destination is interface'
                            ;
                leaf interface-name {
                  description 'The interface name of MONITOR destination'
                              ;
                  type ncd:ifname ;
                }
              }
            }
          }
          container default-vpwss {
            description 'Configuration port mirror of remote mirror by vpws.'
                        ;
            list default-vpws {
              description 'Configuration list of port mirror of remote mirror b'
                        + 'y vpws.'
                          ;
              key vpws-name ;
              leaf vpws-name {
                description 'The vpws name'
                            ;
                type string {
                  length 1..32 ;
                }
              }
            }
            ncd:revise-date 2017-04-14 ;
          }
          container sources {
            description 'The MONITOR sources'
                        ;
            list interface-source {
              description 'The MONITOR source whose type is interface'
                          ;
              key 'interface-name direction'
                  ;
              leaf interface-name {
                description 'The interface name of MONITOR source'
                            ;
                type ncd:ifname ;
              }
              leaf direction {
                description 'The direction for MONITOR source'
                            ;
                type enumeration {
                  enum rx {
                    value 2 ;
                    description 'The MONITOR direction is receive'
                                ;
                  }
                  enum tx {
                    value 3 ;
                    description 'The MONITOR direction is transmit'
                                ;
                  }
                }
              }
              leaf flow-type {
                description flow-type ;
                type enumeration {
                  enum bfd-default {
                    value 62 ;
                    description 'Packets from unknown BFD sessions'
                                ;
                  }
                }
                ncd:revise-date 2017-04-14 ;
              }
            }
            list vpws-source {
              description 'The MONITOR source whose type is vpws'
                          ;
              key 'vpws-name direction'
                  ;
              leaf vpws-name {
                description 'The vpws name of MONITOR source'
                            ;
                type string {
                  length 1..32 ;
                }
              }
              leaf direction {
                description 'The direction for MONITOR source'
                            ;
                type enumeration {
                  enum rx {
                    value 2 ;
                    description 'The MONITOR direction is receive'
                                ;
                  }
                }
              }
              ncd:revise-date 2017-04-14 ;
            }
            container switchvlan-sources {
              // if-feature switchvlan-source-feature ;
              description 'The switchvlan source.'
                          ;
              list switchvlan-source {
                description 'The switchvlan source.'
                            ;
                key 'switchvlan-id direction'
                    ;
                leaf switchvlan-id {
                  description 'The vlanid of switchvlan source.'
                              ;
                  type uint16 {
                    range 1..4094 ;
                  }
                }
                leaf direction {
                  description 'The direction for monitor source.'
                              ;
                  type enumeration {
                    enum rx {
                      value 2 ;
                      description 'The monitor source direction is receive'
                                  ;
                    }
                    enum tx {
                      value 3 ;
                      description 'The monitor source direction is transmit'
                                  ;
                    }
                    enum both {
                      value 1 ;
                      description 'Set direction to both rx and tx'
                                  ;
                    }
                  }
                }
              }
              ncd:revise-date 2021-01-05 ;
            }
            container cpu-sources {
              // if-feature cpu-source-feature ;
              description 'The CPU source.'
                          ;
              list cpu-source {
                description 'The CPU source.'
                            ;
                key 'interface-name direction flow-type'
                    ;
                leaf interface-name {
                  description 'The interface name of MONITOR source'
                              ;
                  type ncd:ifname ;
                }
                leaf direction {
                  description 'The direction for MONITOR source'
                              ;
                  type enumeration {
                    enum rx {
                      value 5 ;
                    }
                    enum tx {
                      value 6 ;
                    }
                  }
                }
                leaf flow-type {
                  description 'Flow type.'
                              ;
                  type flow-type ;
                }
              }
              ncd:revise-date 2021-01-05 ;
            }
          }
          container default-observers {
            description 'Specify the source address and destination address of '
                      + 'port mirror.'
                        ;
            list default-observer {
              description 'Specify the source address and destination address o'
                        + 'f port mirror.'
                          ;
              key 'source-ipv4-addr server-ipv4-addr'
                  ;
              leaf source-ipv4-addr {
                description 'Specify source IPv4 address.'
                            ;
                type ncd:ipv4-address ;
              }
              leaf server-ipv4-addr {
                description 'Specify server IPv4 address.'
                            ;
                type ncd:ipv4-address ;
              }
            }
            ncd:revise-date 2017-04-14 ;
          }
          container rule-observers {
            description 'Specify the source address and destination address of '
                      + 'acl mirror.'
                        ;
            list rule-observer {
              description 'Specify the source address and destination address o'
                        + 'f acl mirror.'
                          ;
              key 'acl-type acl-name source-ipv4-addr server-ipv4-addr'
                  ;
              leaf acl-type {
                description 'ACL type.'
                            ;
                type enumeration {
                  enum ipv4-acl {
                    value 1 ;
                    description 'The type of ACL is IPv4'
                                ;
                  }
                  enum ipv6-acl {
                    value 2 ;
                    description 'The type of ACL is IPv6'
                                ;
                  }
                  enum link-acl {
                    value 3 ;
                    description 'The type of ACL is LINK'
                                ;
                  }
                }
              }
              leaf acl-name {
                description 'acl name'
                            ;
                type string {
                  length 1..31 {
                    description 'The acl name'
                                ;
                  }
                }
              }
              leaf source-ipv4-addr {
                description 'Specify source IPv4 address.'
                            ;
                type ncd:ipv4-address ;
              }
              leaf server-ipv4-addr {
                description 'Specify server IPv4 address.'
                            ;
                type ncd:ipv4-address ;
              }
            }
            ncd:revise-date 2017-04-14 ;
          }
          container default-gres {
            description 'config destination of gre interface'
                        ;
            list default-gre {
              description 'destination of gre interface'
                          ;
              key gre-interface ;
              leaf gre-interface {
                description 'Gre_tunnel interface'
                            ;
                type ncd:ifname ;
              }
              container encap-remote-monitor {
                // if-feature encap-remote-monitor-feature ;
                description 'Configure the ERSPAN.'
                            ;
                leaf tpid {
                  description 'Configure the MAC header TPID of ERmonitor'
                              ;
                  type enumeration {
                    enum 0x8100 {
                      value 1 ;
                    }
                  }
                  default 0x8100 ;
                }
                leaf precedence {
                  description 'Configure the IP precedence value of ERmonitor.'
                              ;
                  type uint8 {
                    range 0..7 ;
                  }
                  default 0 ;
                }
                leaf flags {
                  description 'Configure the VLAN flags of ERmonitor traffic'
                              ;
                  type enumeration {
                    enum disable {
                      value 0 ;
                    }
                    enum enable {
                      value 1 ;
                    }
                  }
                  default disable ;
                }
                leaf ttl {
                  description 'Configure the IP time-to-live (TTL) value.'
                              ;
                  type uint8 {
                    range 1..255 ;
                  }
                  default 128 ;
                }
                leaf dscp {
                  description 'Configure the IP DSCP value.'
                              ;
                  type uint8 {
                    range 0..63 {
                      description 'dscp range'
                                  ;
                    }
                  }
                  default 0 ;
                }
                ncd:revise-date 2021-01-05 ;
              }
            }
            ncd:revise-date 2017-05-16 ;
          }
          container multi-acl-destinations {
            // if-feature multi-acl-feature ;
            description 'Specify multiply ACL destination.'
                        ;
            list multi-interface {
              description 'Specify interface destination.'
                          ;
              key 'acl-type acl-name interface-name'
                  ;
              leaf acl-type {
                description 'Specify ACL type.'
                            ;
                type enumeration {
                  enum ipv4-acl {
                    value 1 ;
                  }
                  enum ipv6-acl {
                    value 2 ;
                  }
                  enum link-acl {
                    value 3 ;
                  }
                  enum ipv4-mixed-acl {
                    value 4 ;
                  }
                }
              }
              leaf acl-name {
                description 'Specify ACL name.'
                            ;
                type string {
                  length 1..31 ;
                }
              }
              leaf interface-name {
                description 'Specify interface name.'
                            ;
                type ncd:ifname ;
              }
            }
            list multi-vpws {
              description 'Specify VPWS destination.'
                          ;
              key 'acl-type acl-name vpws-name'
                  ;
              leaf acl-type {
                description 'Specify ACL type.'
                            ;
                type enumeration {
                  enum ipv4-acl {
                    value 1 ;
                  }
                  enum ipv6-acl {
                    value 2 ;
                  }
                  enum link-acl {
                    value 3 ;
                  }
                  enum ipv4-mixed-acl {
                    value 4 ;
                  }
                }
              }
              leaf acl-name {
                description 'Specify ACL name.'
                            ;
                type string {
                  length 1..31 ;
                }
              }
              leaf vpws-name {
                description 'Specify VPWS name.'
                            ;
                type string {
                  length 1..32 ;
                }
              }
            }
            ncd:revise-date 2020-04-13 ;
          }
          container default-interfaces {
            // if-feature default-interface-feature ;
            description 'Specify interface destination.'
                        ;
            list default-interface {
              description 'Specify interface destination.'
                          ;
              key interface-name ;
              leaf interface-name {
                description 'Specify interface name.'
                            ;
                type ncd:ifname ;
              }
              container remote-monitor {
                // if-feature remote-monitor-feature ;
                description 'Configure remote monitor.'
                            ;
                presence 'Configuration rspan'
                         ;
                leaf vlan-id {
                  description 'Configure the RSPAN.'
                              ;
                  type uint16 {
                    range 1..4094 {
                      description 'RSPAN VLAN ID'
                                  ;
                    }
                  }
                  mandatory true ;
                }
                container tpid-priority {
                  description 'Configure the tpid and priority.'
                              ;
                  leaf tpid {
                    description 'Configure the MAC header TPID.'
                                ;
                    type enumeration {
                      enum 0x8100 {
                        value 1 ;
                      }
                      enum 0x88A8 {
                        value 2 ;
                      }
                      enum 0x9100 {
                        value 3 ;
                      }
                      enum 0x9200 {
                        value 4 ;
                      }
                    }
                    default 0x8100 ;
                  }
                  leaf priority {
                    description 'Configure the priority.'
                                ;
                    type uint8 {
                      range 0..7 ;
                    }
                    default 0 ;
                  }
                }
                ncd:revise-date 2021-01-05 ;
              }
            }
            ncd:revise-date 2020-04-13 ;
          }
          container default-vxlans {
            // if-feature default-vxlan-feature ;
            description 'The destination of VXLAN.'
                        ;
            container ipv4s {
              description 'Specify IPv4 address.'
                          ;
              list ipv4 {
                description 'Specify IPv4 address.'
                            ;
                key 'source-ipv4-addr server-ipv4-addr'
                    ;
                leaf source-ipv4-addr {
                  description 'Source IPv4 address.'
                              ;
                  type ncd:ipv4-address ;
                }
                leaf server-ipv4-addr {
                  description 'Server IPv4 address.'
                              ;
                  type ncd:ipv4-address ;
                }
                leaf vpls {
                  description 'VPLS instance.'
                              ;
                  type string {
                    length 1..32 ;
                  }
                  mandatory true ;
                }
              }
            }
            container ipv6s {
              description 'Specify IPv6 address.'
                          ;
              list ipv6 {
                description 'Specify IPv6 address.'
                            ;
                key 'source-ipv6-addr server-ipv6-addr'
                    ;
                leaf source-ipv6-addr {
                  description 'Source IPv6 address.'
                              ;
                  type ncd:ipv6-address ;
                }
                leaf server-ipv6-addr {
                  description 'Server IPv6 address.'
                              ;
                  type ncd:ipv6-address ;
                }
                leaf vpls {
                  description 'VPLS instance.'
                              ;
                  type string {
                    length 1..32 ;
                  }
                  mandatory true ;
                }
              }
            }
            ncd:revise-date 2021-01-05 ;
          }
        }
      }
      container rate-limits {
        description 'MONITOR rate limit configuration'
                    ;
        list rate-limit {
          description 'MONITOR rate limit configuration list'
                      ;
          key board-name ;
          leaf board-name {
            description 'The board name supported rate limit by monitor'
                        ;
            type ncd:board {
              length 1..19 ;
            }
          }
          leaf cir {
            description 'Configure Committed Information Rate value,Unit is Mbp'
                      + 's.'
                        ;
            type uint32 {
              range 1..30000 {
                description 'CIR value(Mbps)'
                            ;
              }
            }
            mandatory true ;
          }
          leaf cbs {
            description 'Configure Committed Burst Size value,Unit is MB.'
                        ;
            type uint32 {
              range 1..16 {
                description 'CBS value(MB)'
                            ;
              }
            }
            mandatory true ;
          }
          container pir-pbs {
            description 'Configure Peak Information Rate value and Peak Burst S'
                      + 'ize value.'
                        ;
            presence pir-pbs ;
            leaf pir {
              description 'Configure Peak Information Rate value,Unit is Mbps.'
                          ;
              type uint32 {
                range 1..30000 {
                  description 'PIR value(Mbps)'
                              ;
                }
              }
              mandatory true ;
            }
            leaf pbs {
              description 'Configure Peak Burst Size value,Unit is MB.'
                          ;
              type uint32 {
                range 1..16 {
                  description 'PBS value(MB)'
                              ;
                }
              }
              mandatory true ;
            }
          }
        }
        ncd:revise-date 2017-04-14 ;
      }
    }
  }
}
