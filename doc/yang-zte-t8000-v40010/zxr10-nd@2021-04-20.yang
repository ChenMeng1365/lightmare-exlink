module zxr10-nd {
  namespace 'http://www.zte.com.cn/zxr10/netconf/schema/rosng/nd'
            ;
  prefix nd ;
  yang-version 1 ;
  import zxr10-netconf-defs {
    prefix ncd ;
    revision-date 2015-11-09 ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe ND(Neighbor Discovery).'
              ;
  revision 2021-04-20 {
    description 'Add container /configuration/nd/inter-chassis-backup.'
                ;
  }
  revision 2020-12-02 {
    description 'Add state/nd/mclag-check-items node and son nodes.'
                ;
  }
  revision 2020-11-07 {
    description 'Add configuration/nd/ra-dns-servers node and son nodes.'+"\n"
              + 'Add configuration/nd/ra-dns-searches node and son nodes.'+"\n"
              + 'Modify the if_feature of configuration/nd/ra-route-information'
              + '.'
                ;
  }
  revision 2020-11-04 {
    description 'Modify the range of ra-linkmtu node.'
                ;
  }
  revision 2020-08-18 {
    description 'Delete the default value of ipv6 dad-attempts, and modify the '
              + 'description of the leaf /configuration/nd/ipv6-nd-attribute/da'
              + 'd-attempts.'
                ;
  }
  revision 2020-08-13 {
    description 'Delete the default value of ND anti-attack threshold, and modi'
              + 'fy the description of the leaf /configuration/nd/global/anti-a'
              + 'ttack/threshold.'
                ;
  }
  revision 2020-07-18 {
    description 'Add configuration about mac delete.'
                ;
  }
  revision 2020-07-08 {
    description 'Add configuration/nd/global/nud-fast-reply nodes.'+"\n"
              + 'Add the feature of nd-fast-reply.'
                ;
  }
  revision 2020-07-01 {
    description 'Add configuration/nd/ra-address-prefixs node and its son-nodes'
              + '.'+"\n"
              + 'Add the feature of ra-address-prefix.'
                ;
  }
  revision 2020-06-18 {
    description 'Add container:/configuration/nd/global/anti-attack and its son'
              + '-node.'
                ;
  }
  revision 2020-05-23 {
    description 'Add configuration/nd/vpls-evpns son nodes.'+"\n"
              + 'include:'+"\n"
              + '  nd description'
                ;
  }
  revision 2020-05-06 {
    description 'Add state/nd/l2-proxy-items/l2-proxy-item nodes and a feature '
              + 'about getting l2-proxy-item'
                ;
  }
  revision 2020-02-03 {
    description 'Add container:/configuration/nd/periodic-na-inteval and its so'
              + 'n-node.'
                ;
  }
  revision 2019-12-27 {
    description 'Add configuration/nd/vpls-evpns probe-delay nodes.'
                ;
  }
  revision 2019-12-05 {
    description 'Add container:/configuration/nd/nd-entry-limits.'
                ;
  }
  revision 2019-09-19 {
    description 'Add container:/configuration/nd/ipv6-nd-host-route.'
                ;
  }
  revision 2019-07-03 {
    description 'Add state\nd\nd-caches\nd-cache\type leaf node.'
                ;
  }
  revision 2019-04-02 {
    description 'Add max value (Perf-code)for /configuration/nd/nd-num-on-if/ma'
              + 'x-number.'
                ;
  }
  revision 2018-09-26 {
    description 'Change the status of ipv6-source-guards node to obsolete.'
                ;
  }
  revision 2018-08-23 {
    description 'Add configuration/nd/vpls-evpns son nodes.'+"\n"
              + 'Include:'+"\n"
              + '  nd broadcast'+"\n"
              + '  nd proxy-suppress'+"\n"
              + '  nd proxy'+"\n"
              + '  nd l3-proxy'
                ;
  }
  revision 2017-10-25 {
    description 'Add container:/configuration/nd/nd-global-proxys'
                ;
  }
  revision 2016-05-05 {
    description 'Delete the default values of nud-switch node and stale-switch '
              + 'node under nd-globle cantainer node.'
                ;
  }
  revision 2015-12-31 {
    description 'Modify the type of prefix leaf node under the ipv6-nd-prefix t'
              + 'able.'+"\n"
              + 'Delete the prefix-length leaf node under the ipv6-nd-prefix ta'
              + 'ble.'+"\n"
              + 'Modify the type of prefix leaf node under the ra-route-informa'
              + 'tion table.'+"\n"
              + 'Delete the prefix-length leaf node under the ra-route-informat'
              + 'ion table.'+"\n"
              + 'Modify the import submodule.'
                ;
  }
  revision 2015-11-16 {
    description 'Expand the range of the retransmit-time leaf node,and the rang'
              + 'e is from 1000 to 4294967295.'
                ;
  }
  revision 2015-10-13 {
    description 'Modify the son-nodes of the ipv6-nd-attribute container node.'+"\n"
              + 'Remove the reachable-times container node and its son-nodes.'+"\n"
              + 'Remove the retransmit-times container node and its son-nodes.'+"\n"
              + 'Add the ra-time container node and its son-nodes.'
                ;
  }
  revision 2015-09-14 {
    description 'Modify the name of list node from "link-loacl" to "link-local".'
                ;
  }
  revision 2015-07-28 {
    description 'Set the config of operation and state to false.'
                ;
  }
  revision 2015-06-09 {
    description 'Delete feature:switch-feature,feature-to-15K,feature-to-T8000.'
              + ''+"\n"
              + 'Add feature:nd-keepalive-feature,nd-if-number-defended-feature'
              + ',nd-whitelist-feature.'+"\n"
              + 'Add nd-whitelist-feature on container cps-trusts.'+"\n"
              + 'Add nd-keepalive-feature on container keepalive.'+"\n"
              + 'Add nd-if-number-defended-feature on container nd-num-on-if.'
                ;
  }
  revision 2015-04-08 {
    description 'Delete list:by-if.'+"\n"
              + 'Delete leaf:ifname.'+"\n"
              + 'Delete leaf:all.'+"\n"
              + 'Add choise:all-or-if.'+"\n"
              + 'Add case:all.'+"\n"
              + 'Add leaf:all-nd-cache.'+"\n"
              + 'Add case:by-if.'+"\n"
              + 'Add leaf:ifname.'+"\n"
              + 'Add feature-to-T8000 on container cps-trusts.'
                ;
  }
  revision 2014-11-19 {
    description 'Add container:nd-num-on-if.'+"\n"
              + 'Add leaf:max-number.'+"\n"
              + 'Add feature:feature-to-T8000.'+"\n"
              + 'Add feature-to-T8000 on container nd-num-on-if and container k'
              + 'eepalive.'
                ;
  }
  revision 2014-07-21 {
    description 'Add container:vlan-id.'+"\n"
              + 'Add container:external-vlan-id and internal-vlan-id.'
                ;
  }
  revision 2014-04-18 {
    description 'Add container:default-route,list:default-route-priority,leaf:i'
              + 'fname and priority;'+"\n"
              + 'Modify the name of container from "dad-proxys" to "dad-proxy";'
              + ''+"\n"
              + 'Modify the name of container from "dad-proxy" to "linklocal",a'
              + 'nd add mimaction;'+"\n"
              + 'Delete leaf:link-loacl;'+"\n"
              + 'Delete the OperationChangeType of global,keepalive and nd-glob'
              + 'al.'
                ;
  }
  revision 2014-03-31 {
    description 'Add a new feature and modily the if_features of some nodes.'
                ;
  }
  revision 2013-10-25 {
    description 'Initial version.'
                ;
  }
  feature route-feature {
    description 'Router feature.'
                ;
  }
  feature nd-keepalive-feature {
    description 'The feature for keepalive function.'
                ;
  }
  feature nd-if-number-defended-feature {
    description 'The feature for nd number on interface defended.'
                ;
  }
  feature nd-whitelist-feature {
    description 'The feature for whitelist function.'
                ;
  }
  feature global-proxy {
    description 'The feature for nd global proxy.'
                ;
  }
  feature nd-vpls-evpn {
    description 'ND configurations about VPLS-EVPN.'
                ;
  }
  feature ipv6-nd-host-route-feature {
    description 'The feature for IPv6 host route fuction.'
                ;
  }
  feature nd-entry-per-interface {
    description 'The feature for setting nd entry limit for an interface.'
                ;
  }
  feature vpls-evpn-probe-delay {
    description 'ND probe delay configuration in vpls evpn.'
                ;
  }
  feature periodic-na {
    description 'The feature for setting interval time of sending NA periodical'
              + 'ly.'
                ;
  }
  feature get-l2-proxy-item {
    description 'A feature about getting l2-proxy item'
                ;
  }
  feature nd-vpls-evpn-description {
    description 'Set the description of VPLS EVPN ND.'
                ;
  }
  feature nd-anti-attack {
    description 'The feature for nd anti-attack fuction.'
                ;
  }
  feature ra-address-prefix {
    description 'The feature for whether advertising IPv6 address prefix by RA '
              + 'function'
                ;
  }
  feature nd-fast-reply {
    description 'The feature for nd nud-fast-reply fuction.'
                ;
  }
  feature mac-delete-detect {
    description 'The feature for nd processing of associated MAC deletion.'
                ;
  }
  feature ra-route-information {
    description 'The feature for RA route information options.'
                ;
  }
  feature ra-dns {
    description 'The feature for RA DNS options.'
                ;
  }
  feature mclag-consistency-check {
    description 'The feature for getting the static ND information in MC-LAG co'
              + 'nsistency checking.'
                ;
  }
  feature delete-notify {
    description 'The feature about inter-chassis backup delete-notify.'
                ;
  }
  container configuration {
    description 'Configuration model info.'
                ;
    container nd {
      description 'Neighbor Discovery Protocol configuration.'
                  ;
      container ipv6-nd-attribute {
        description 'Configure IPv6 ND attributes.'
                    ;
        list nd-attribute {
          description 'Configure ND cache entry attributes.'
                      ;
          key ifname ;
          leaf ifname {
            description 'The name of the interface.'
                        ;
            type ncd:ifname ;
          }
          leaf dad-attempts {
            description 'Configure the DAD attempts number. Its default value w'
                      + 'hich is between 1-10 and generally 3, depends on produ'
                      + 'ct specification.'
                        ;
            type uint8 {
              range 0..10 ;
            }
          }
          leaf man-cfg-flag {
            description 'The flag denotes the hosts should use DHCP(Dynamic Hos'
                      + 't Configuration Protocol) for address configuration.'
                        ;
            type enumeration {
              enum reset {
                value 1 ;
                description 'Reset the flag.'
                            ;
              }
              enum set {
                value 2 ;
                description 'Set the flag.'
                            ;
              }
            }
            default reset ;
          }
          leaf other-cfg-flag {
            description 'The flag denotes the hosts should use DHCP for configu'
                      + 'ration except for address.'
                        ;
            type enumeration {
              enum reset {
                value 1 ;
                description 'Reset the flag.'
                            ;
              }
              enum set {
                value 2 ;
                description 'Set the flag.'
                            ;
              }
            }
            default reset ;
          }
          leaf nud-switch {
            description 'IPv6 ND NUD(Neighbour Unreachable Detect) switch.'
                        ;
            type enumeration {
              enum off {
                value 1 ;
                description 'Turn off the switch.'
                            ;
              }
              enum on {
                value 2 ;
                description 'Turn on the switch.'
                            ;
              }
            }
            default on ;
          }
          leaf stale-switch {
            description 'IPv6 ND stale switch.'
                        ;
            type enumeration {
              enum off {
                value 1 ;
                description 'Turn off the switch.'
                            ;
              }
              enum on {
                value 2 ;
                description 'Turn on the switch.'
                            ;
              }
            }
            default off ;
          }
          leaf ra-curhoplimit {
            description 'Set IPv6 router advertisement current hoplimit.'
                        ;
            type uint8 {
              range 0..255 ;
            }
            default 64 ;
          }
          leaf ra-interval {
            description 'Set IPv6 router advertisement interval(second).'
                        ;
            type uint16 {
              range 3..1800 ;
            }
            units second ;
            default 600 ;
          }
          leaf ra-lifetime {
            description 'Set IPv6 router advertisement lifetime(second).'
                        ;
            type uint16 {
              range 0..9000 ;
            }
            units second ;
            default 1800 ;
          }
          leaf na-parse {
            description 'Parse IPv6 multicast neighbor advertisements.'
                        ;
            type enumeration {
              enum off {
                value 1 ;
                description 'Turn off the switch.'
                            ;
              }
              enum on {
                value 2 ;
                description 'Turn on the switch.'
                            ;
              }
            }
            default off ;
          }
          leaf staled-time {
            description 'IPv6 ND entry staled time(minute).'
                        ;
            type uint32 {
              range 1..14400 ;
            }
            units minute ;
          }
          leaf redirect {
            description 'Control IPv6 router ND redirect.'
                        ;
            type enumeration {
              enum off {
                value 1 ;
                description 'Turn off the switch.'
                            ;
              }
              enum on {
                value 2 ;
                description 'Turn on the switch.'
                            ;
              }
            }
            default off ;
          }
          leaf ra-linkmtu {
            description 'Set IPv6 router advertisement linkmtu.Its maximum whic'
                      + 'h is between 1500-9586 and generally 1500, depends on '
                      + 'pruduct specification.'
                        ;
            type uint16 {
              range 0..9586 ;
            }
            units byte ;
            default 1500 ;
          }
          leaf proxy-switch {
            description 'The ND proxy switch between the interfaces.'
                        ;
            type enumeration {
              enum off {
                value 1 ;
                description 'Turn off the switch.'
                            ;
              }
              enum on {
                value 2 ;
                description 'Turn on the switch.'
                            ;
              }
            }
            default off ;
          }
          leaf innervlan-proxy-switch {
            description 'The ND proxy switch in the same vlan of the interface.'
                        ;
            type enumeration {
              enum off {
                value 1 ;
                description 'Turn off the switch.'
                            ;
              }
              enum on {
                value 2 ;
                description 'Turn on the switch.'
                            ;
              }
            }
            default off ;
          }
          leaf intervlan-proxy-switch {
            description 'The ND proxy switch in the different vlan of the inter'
                      + 'face.'
                        ;
            type enumeration {
              enum off {
                value 1 ;
                description 'Turn off the switch.'
                            ;
              }
              enum on {
                value 2 ;
                description 'Turn on the switch.'
                            ;
              }
            }
            default off ;
          }
          ncd:revise-date 2015-10-13 ;
        }
      }
      container ipv6-nd-prefix {
        description 'Configure IPv6 ND prefix.'
                    ;
        list prefix {
          description 'Configure IPv6 ND prefix.'
                      ;
          key 'ifname prefix'
              ;
          leaf ifname {
            description 'The name of the interface.'
                        ;
            type ncd:ifname ;
          }
          leaf prefix {
            description 'IPv6 ND prefix.'
                        ;
            type ncd:ipv6-prefix ;
            ncd:revise-date 2015-12-31 ;
          }
          container lifetime {
            description 'Set the lifetimes of the prefix.'
                        ;
            presence lifetime ;
            leaf valid-lifetime {
              description 'Set the valid lifetime of the prefix (second).'
                          ;
              type uint32 {
                range 0..4294967295 ;
              }
              units second ;
              mandatory true ;
            }
            leaf preferred-lifetime {
              description 'Set the preferred lifetime of the prefix(second).'
                          ;
              type uint32 {
                range 0..4294967295 ;
              }
              units second ;
              mandatory true ;
            }
          }
          leaf no-autoconfig {
            description "Set the flag indicates that can't generate automatical"
                      + "ly the address using the prefix."
                        ;
            type enumeration {
              enum reset {
                value 1 ;
                description 'Reset the flag.'
                            ;
              }
              enum set {
                value 2 ;
                description 'Set the flag.'
                            ;
              }
            }
            default reset ;
          }
          leaf off-link {
            description "Set the flag indicates that can't use prefix for onlin"
                      + "k determination."
                        ;
            type enumeration {
              enum reset {
                value 1 ;
                description 'Reset the flag.'
                            ;
              }
              enum set {
                value 2 ;
                description 'Set the flag.'
                            ;
              }
            }
            default reset ;
          }
        }
      }
      container static-nd {
        description 'Configure static ND cache entry.'
                    ;
        container no-supervlan {
          description 'Configure static ND cache entry on non-supervlan interfa'
                    + 'ce.'
                      ;
          list nd-config {
            description 'Configure  relevant attributes static ND cache entry.'
                        ;
            key 'ifname next-hop'
                ;
            leaf ifname {
              description 'The name of the interface.'
                          ;
              type ncd:ifname ;
            }
            leaf next-hop {
              description 'The next hop IPv6 address.'
                          ;
              type ncd:ipv6-address ;
            }
            leaf mac {
              description 'MAC(Media Access Control) address.'
                          ;
              type ncd:mac-address ;
              mandatory true ;
            }
            container vlan-id {
              if-feature route-feature ;
              description 'Configure VLAN ID.'
                          ;
              presence vlan-id ;
              leaf external-vlan-id {
                description 'External VLAN ID.'
                            ;
                type uint16 {
                  range 1..4094 ;
                }
                mandatory true ;
              }
              leaf internal-vlan-id {
                description 'Internal VLAN ID.'
                            ;
                type uint16 {
                  range 1..4094 ;
                }
              }
            }
          }
        }
        container supervlan {
          if-feature route-feature ;
          description 'Configure static ND cache entry on supervlan interface.'
                      ;
          list nd-config {
            description 'Configure relevant attributes static ND cache entry.'
                        ;
            key 'ifname next-hop'
                ;
            leaf ifname {
              description 'The name of the interface.'
                          ;
              type ncd:ifname ;
            }
            leaf next-hop {
              description 'The next hop IPv6 address.'
                          ;
              type ncd:ipv6-address ;
            }
            leaf mac {
              description 'Mac address.'
                          ;
              type ncd:mac-address ;
              mandatory true ;
            }
            leaf subvlan-ifname {
              description 'The subvlan interface name.'
                          ;
              type ncd:ifname ;
              mandatory true ;
            }
            container vlan-id {
              if-feature route-feature ;
              description 'Configure VLAN ID.'
                          ;
              presence vlan-id ;
              leaf external-vlan-id {
                description 'External VLAN ID.'
                            ;
                type uint16 {
                  range 1..4094 ;
                }
                mandatory true ;
              }
              leaf internal-vlan-id {
                description 'Internal VLAN ID.'
                            ;
                type uint16 {
                  range 1..4094 ;
                }
              }
            }
          }
        }
      }
      container cps-trusts {
        if-feature nd-whitelist-feature ;
        description 'Configure CPS(Control plane security)trust properties of t'
                  + 'he interface.'
                    ;
        list cps-trust {
          description 'Configure CPS(Control plane security)trust properties of'
                    + ' the interface.'
                      ;
          key ifname ;
          leaf ifname {
            description 'The name of the interface.'
                        ;
            type ncd:ifname ;
          }
        }
      }
      container ipv6-source-guards {
        status obsolete {
          ncd:revise-date 2018-09-26 ;
        }
        description 'Configure IPv6 source guard.'
                    ;
        list ipv6-source-guard {
          description 'Configure IPv6 source guard.'
                      ;
          key ifname ;
          leaf ifname {
            description 'The name of the interface.'
                        ;
            type ncd:ifname ;
          }
          choice if-need-vlan {
            description 'Whether need configure VLAN.'
                        ;
            case need {
              description 'Need configure VLAN.'
                          ;
              leaf mode-with-vlan {
                description 'Configure IPv6 source-guard mode.'
                            ;
                type enumeration {
                  enum mac-base {
                    value 1 ;
                    description 'Base on MAC.'
                                ;
                  }
                  enum ip-base {
                    value 2 ;
                    description 'Base on IP address.'
                                ;
                  }
                  enum mac-ip-base {
                    value 3 ;
                    description 'Base on MAC and IP address.'
                                ;
                  }
                }
                mandatory true ;
              }
              leaf vlan-id {
                description 'Configure VLAN ID,a value of 4095 indicates using '
                          + 'default values of project.'
                            ;
                type uint32 {
                  range 1..4095 ;
                }
                mandatory true ;
              }
            }
            case no-need {
              description "Needn't configure VLAN."
                          ;
              leaf mode-without-vlan {
                description 'Configure IPv6 source-guard mode.'
                            ;
                type enumeration {
                  enum mac-base {
                    value 1 ;
                    description 'Base on MAC.'
                                ;
                  }
                  enum ip-base {
                    value 2 ;
                    description 'Base on IP address.'
                                ;
                  }
                  enum mac-ip-base {
                    value 3 ;
                    description 'Base on MAC and IP address.'
                                ;
                  }
                }
                mandatory true ;
              }
            }
          }
        }
      }
      container ra-suppresses {
        description 'Configure the switch of suppressing IPv6 RA(Router Adverti'
                  + 'sement) packets to send.'
                    ;
        list ra-suppress {
          description 'Configure the switch of suppressing IPv6 RA packets to s'
                    + 'end.'
                      ;
          key ifname ;
          leaf ifname {
            description 'The name of the interface.'
                        ;
            type ncd:ifname ;
          }
          leaf switch {
            description 'The switch of suppressing IPv6 router advertisements t'
                      + 'o send.'
                        ;
            type enumeration {
              enum off {
                value 1 ;
                description 'Turn off the switch.'
                            ;
              }
              enum on {
                value 2 ;
                description 'Turn on the switch.'
                            ;
              }
            }
            mandatory true ;
          }
        }
      }
      container ra-time {
        list time {
          key ifname ;
          leaf ifname {
            description 'The name of the interface.'
                        ;
            type ncd:ifname {
              length 1..31 ;
            }
          }
          leaf reachable-time {
            description 'Reachability time in milliseconds.'
                        ;
            type uint32 {
              range 0..3600000 ;
            }
            units millisecond ;
            default 30000 ;
          }
          leaf retransmit-time {
            description 'Retransmit time(millisecond).'
                        ;
            type uint32 {
              range 1000..4294967295 ;
            }
            units millisecond ;
            default 1000 ;
          }
        }
        ncd:revise-date 2015-10-13 ;
      }
      container ra-route-information {
        if-feature ra-route-information ;
        description 'Configure route information option in RA.'
                    ;
        list ra-routeinfo {
          description 'Configure route information option in RA.'
                      ;
          key 'ifname prefix'
              ;
          leaf ifname {
            description 'The name of the interface.'
                        ;
            type ncd:ifname ;
          }
          leaf prefix {
            description 'IPv6 ND prefix.'
                        ;
            type ncd:ipv6-prefix ;
            ncd:revise-date 2015-12-31 ;
          }
          container relevant-attributes {
            description 'Set relevant attributes.'
                        ;
            presence relevant-attributes ;
            leaf route-lifetime {
              description 'Route lifetime(second).'
                          ;
              type uint32 {
                range 0..4294967295 ;
              }
              units second ;
              mandatory true ;
            }
            leaf preference {
              description 'Route preference.'
                          ;
              type uint8 {
                range 0..3 ;
              }
              default 0 ;
            }
          }
        }
      }
      container nd-host {
        if-feature route-feature ;
        description 'Enable IPv6 ND host specification.'
                    ;
        list enable {
          description 'Enable IPv6 ND host specification.'
                      ;
          key ifname ;
          leaf ifname {
            description 'The name of the interface.'
                        ;
            type ncd:ifname ;
          }
        }
      }
      container dad-proxy {
        if-feature route-feature ;
        description 'Set DAD proxy.'
                    ;
        list link-local {
          description 'Enable DAD proxy of the linklocal.'
                      ;
          key ifname ;
          leaf ifname {
            description 'The name of the interface.'
                        ;
            type ncd:ifname ;
          }
          ncd:revise-date 2015-09-14 ;
        }
      }
      container global {
        description 'Global configurations.'
                    ;
        container keepalive {
          if-feature nd-keepalive-feature ;
          description 'Configure ND keepalive interval.'
                      ;
          leaf periodic {
            description 'Configure ND keepalive interval(second).'
                        ;
            type uint16 {
              range 10..14400 ;
            }
            units second ;
            default 30 ;
          }
        }
        container nd-global {
          description 'Configure ND global information.'
                      ;
          leaf staled-time {
            description 'IPv6 ND entry staled time(minute).'
                        ;
            type uint32 {
              range 1..14400 ;
            }
            units minute ;
          }
          leaf nud-switch {
            description 'IPv6 ND NUD switch,and the different projects have dif'
                      + 'ferent default values.'
                        ;
            type enumeration {
              enum off {
                value 1 ;
                description 'Turn off the switch.'
                            ;
              }
              enum on {
                value 2 ;
                description 'Turn on the switch.'
                            ;
              }
            }
          }
          leaf stale-switch {
            description 'IPv6 ND stale switch,and the different projects can ha'
                      + 've different default values.'
                        ;
            type enumeration {
              enum off {
                value 1 ;
                description 'Turn off the switch.'
                            ;
              }
              enum on {
                value 2 ;
                description 'Turn on the switch.'
                            ;
              }
            }
          }
          leaf nud-fast-reply {
            if-feature nd-fast-reply ;
            description 'ND nud-fast-reply switch, and the different projects c'
                      + 'an have different default values.'
                        ;
            type enumeration {
              enum disable {
                value 0 ;
                description 'Disable nud-fast-reply.'
                            ;
              }
              enum enable {
                value 1 ;
                description 'Enable nud-fast-reply.'
                            ;
              }
            }
            ncd:revise-date 2020-07-08 ;
          }
        }
        container anti-attack {
          if-feature nd-anti-attack ;
          description 'Configure ND anti-attack function.'
                      ;
          leaf switch {
            description 'ND anti-attack switch, and the different projects can '
                      + 'have different default values.'
                        ;
            type enumeration {
              enum enable {
                value 1 ;
                description 'Enable the anti-attack function.'
                            ;
              }
              enum disable {
                value 0 ;
                description 'Disable the anti-attack function.'
                            ;
              }
            }
          }
          leaf threshold {
            description 'ND anti-attack threshold, packets number per 10 second'
                      + 's.Its default value which is between 10-1000 and gener'
                      + 'ally 60, depends on product specification.'
                        ;
            type uint16 {
              range 10..1000 {
                description 'The anti-attack threshold, from 10 to 1000.'
                            ;
              }
            }
          }
          ncd:revise-date 2020-06-18 ;
        }
      }
      container default-route {
        if-feature route-feature ;
        description 'The configuration of the default route.'
                    ;
        list default-route-priority {
          description 'Configure the priority of default route.'
                      ;
          key ifname ;
          leaf ifname {
            description 'The name of the interface.'
                        ;
            type ncd:ifname ;
          }
          leaf priority {
            description 'The priority of default route.'
                        ;
            type uint8 {
              range 1..254 ;
            }
            mandatory true ;
          }
        }
      }
      container nd-num-on-if {
        if-feature nd-if-number-defended-feature ;
        description 'Configure the max number of ND entries on one interface.'
                    ;
        presence nd-num ;
        leaf max-number {
          description "The max number.It's toplimit depends on ability of the d"
                    + "evice. The default value is generally 10000."
                      ;
          type uint32 {
            range 100..10000 {
              description "It's toplimit depends on ability of the device."
                          ;
            }
          }
          mandatory true ;
        }
      }
      container nd-global-proxys {
        if-feature global-proxy ;
        description 'Configure ND global proxy function.'
                    ;
        list nd-global-proxy {
          description 'Configure ND global proxy function.'
                      ;
          key ifname ;
          leaf ifname {
            description 'The name of the interface.'
                        ;
            type ncd:ifname ;
          }
          leaf global-proxy {
            description 'Global proxy switch.'
                        ;
            type enumeration {
              enum disable {
                value 0 ;
                description 'Disable ND global proxy funcion.'
                            ;
              }
              enum enable {
                value 1 ;
                description 'Enable ND global proxy funcion.'
                            ;
              }
            }
            mandatory true ;
          }
        }
        ncd:revise-date 2017-10-25 ;
      }
      container vpls-evpns {
        if-feature nd-vpls-evpn ;
        description 'Set ND VPLS EVPN configurations.'
                    ;
        list vpls-evpn {
          description 'Set ND VPLS EVPN configurations.'
                      ;
          key instance-name ;
          leaf instance-name {
            description 'The name of VPLS instance.'
                        ;
            type string ;
          }
          leaf proxy {
            description 'Set ND VPLS EVPN proxy function.'
                        ;
            type enumeration {
              enum enable {
                value 1 ;
              }
              enum disable {
                value 0 ;
              }
            }
            default disable ;
          }
          leaf l3-proxy {
            description 'Set ND VPLS EVPN L3 proxy function.'
                        ;
            type enumeration {
              enum enable {
                value 1 ;
              }
              enum disable {
                value 0 ;
              }
            }
            default disable ;
          }
          leaf broadcast {
            description 'Set ND VPLS EVPN L2 proxy broadcast function.'
                        ;
            type enumeration {
              enum enable {
                value 1 ;
              }
              enum disable {
                value 0 ;
              }
            }
            default enable ;
          }
          leaf proxy-suppress {
            description 'Set ND VPLS EVPN L2 proxy proxy-suppress function.'
                        ;
            type enumeration {
              enum enable {
                value 1 ;
              }
              enum disable {
                value 0 ;
              }
            }
            default disable ;
          }
          leaf probe-delay {
            if-feature vpls-evpn-probe-delay ;
            description 'Set ND VPLS EVPN probe-delay time in second.'
                        ;
            type uint32 {
              range 1..60 {
                description 'range 1-60s'
                            ;
              }
            }
            ncd:revise-date 2019-12-27 ;
          }
          leaf description {
            if-feature nd-vpls-evpn-description ;
            description 'The description of VPLS EVPN ND.'
                        ;
            type ncd:string-with-blank {
              length 1..64 {
                description 'The description range of instance'
                            ;
              }
            }
            ncd:revise-date 2020-05-23 ;
          }
        }
        ncd:revise-date 2018-08-23 ;
      }
      container nd-entry-limits {
        if-feature nd-entry-per-interface ;
        description 'Configure IPv6 ND entry limit for an interface.'
                    ;
        list nd-entry-limit {
          description 'Configure IPv6 ND entry limit for an interface.'
                      ;
          key ifname ;
          leaf ifname {
            description 'The name of the interface.'
                        ;
            type ncd:ifname ;
          }
          leaf limit-number {
            description 'ND entry number limit.'
                        ;
            type uint32 {
              range 100..10000 {
                description "It's toplimit depends on ability of the device."
                            ;
              }
            }
            mandatory true ;
          }
        }
        ncd:revise-date 2019-12-05 ;
      }
      container ipv6-nd-host-route {
        if-feature ipv6-nd-host-route-feature ;
        description 'Configure IPv6 ND host-route.'
                    ;
        list host-route {
          description 'Configure host-route attributes.'
                      ;
          key ifname ;
          leaf ifname {
            description 'The name of the interface.'
                        ;
            type ncd:ifname ;
          }
          leaf switch {
            description 'Enable or disable ND host route function.'
                        ;
            type enumeration {
              enum enable {
                value 1 ;
                description 'Enable ND host route function.'
                            ;
              }
              enum disable {
                value 0 ;
                description 'Disable ND host route function.'
                            ;
              }
            }
            mandatory true ;
          }
        }
        ncd:revise-date 2019-09-19 ;
      }
      container periodic-na-interval {
        if-feature periodic-na ;
        description 'Set interval time of sending NA periodically.'
                    ;
        list na-interval {
          description 'Set interval time of sending NA periodically.'
                      ;
          key ifname ;
          leaf ifname {
            description 'The name of the interface.'
                        ;
            type ncd:ifname ;
          }
          leaf interval {
            description 'Interval time.'
                        ;
            type uint32 {
              range 10..14400 ;
            }
            mandatory true ;
          }
        }
        ncd:revise-date 2020-02-03 ;
      }
      container ra-address-prefixs {
        if-feature ra-address-prefix ;
        description 'Configure the switch of advertising IPv6 address prefix by'
                  + ' RA(Router Advertisement)'
                    ;
        list ra-address-prefix {
          description 'Configure the switch of advertising IPv6 address prefix '
                    + 'by RA(Router Advertisement)'
                      ;
          key ifname ;
          leaf ifname {
            description 'The name of the interface.'
                        ;
            type ncd:ifname ;
          }
          leaf switch {
            description 'The switch of advertising IPv6 address prefix by RA(Ro'
                      + 'uter Advertisement)'
                        ;
            type enumeration {
              enum off {
                value 0 ;
                description 'Turn off the switch.'
                            ;
              }
              enum on {
                value 1 ;
                description 'Turn on the switch.'
                            ;
              }
            }
            default on ;
          }
        }
        ncd:revise-date 2020-07-01 ;
      }
      container mac-deletes {
        if-feature mac-delete-detect ;
        description 'Set ND configurations about mac delete.'
                    ;
        list mac-delete {
          description 'Set ND configurations about mac delete.'
                      ;
          key ifname ;
          leaf ifname {
            description 'The name of the interface.'
                        ;
            type ncd:ifname ;
          }
          leaf detect-interval {
            description 'Detect interval in second.'
                        ;
            type uint32 {
              range 1..1440 ;
            }
            units seconds ;
          }
        }
        ncd:revise-date 2020-07-18 ;
      }
      container ra-dns-servers {
        if-feature ra-dns ;
        description 'Configure RA DNS server options.'
                    ;
        list ra-dns-server {
          description 'Configure RA DNS server option.'
                      ;
          key 'ifname server-ip'
              ;
          leaf ifname {
            description 'The name of the interface.'
                        ;
            type ncd:ifname {
              length 1..31 ;
            }
          }
          leaf server-ip {
            description 'DNS server IP'
                        ;
            type ncd:ipv6-address ;
          }
          container lifetime-container {
            description 'Configure lifetime.'
                        ;
            choice lifetime {
              description Lifetime. ;
              mandatory true ;
              case finite {
                description 'Configure the finite lifetime for RA DNS server.'
                            ;
                leaf finite-lifetime {
                  description Lifetime. ;
                  type uint16 {
                    range 4..3600 ;
                  }
                  units second ;
                }
              }
              case infinite {
                description 'Configure the infinite lifetime for RA DNS server.'
                            ;
                leaf infinite-lifetime {
                  description 'Infinite lifetime.'
                              ;
                  type empty ;
                  units second ;
                }
              }
              case zero {
                description 'Configure the zero lifetime for RA DNS server.'
                            ;
                leaf zero-lifetime {
                  description 'Zero lifetime.'
                              ;
                  type empty ;
                  units second ;
                }
              }
            }
          }
        }
        ncd:revise-date 2020-11-07 ;
      }
      container ra-dns-searches {
        if-feature ra-dns ;
        description 'Configure RA DNS search list options.'
                    ;
        list ra-dns-search {
          description 'Configure RA DNS search list option.'
                      ;
          key 'ifname domain-name'
              ;
          leaf ifname {
            description 'The name of the interface.'
                        ;
            type ncd:ifname {
              length 1..31 ;
            }
          }
          leaf domain-name {
            description 'The DNS domain name.'
                        ;
            type string {
              length 1..254 ;
            }
          }
          container lifetime-container {
            description 'Configure lifetime.'
                        ;
            choice lifetime {
              description Lifetime. ;
              mandatory true ;
              case finite {
                description 'Configure the finite lifetime for RA DNS search li'
                          + 'st option.'
                            ;
                leaf finite-lifetime {
                  description Lifetime. ;
                  type uint16 {
                    range 4..3600 ;
                  }
                  units second ;
                }
              }
              case infinite {
                description 'Configure the infinite lifetime for RA DNS search '
                          + 'list option.'
                            ;
                leaf infinite-lifetime {
                  description 'Infinite lifetime.'
                              ;
                  type empty ;
                  units second ;
                }
              }
              case zero {
                description 'Configure the zero lifetime for RA DNS search list'
                          + ' option.'
                            ;
                leaf zero-lifetime {
                  description 'Zero lifetime.'
                              ;
                  type empty ;
                  units second ;
                }
              }
            }
          }
        }
        ncd:revise-date 2020-11-07 ;
      }
      container inter-chassis-backup {
        if-feature delete-notify ;
        description 'Set ND inter-chassis backup.'
                    ;
        list delete-notify {
          description 'Set ND inter-chassis backup delete-notify'
                      ;
          key ifname ;
          leaf ifname {
            description 'The name of the interface.'
                        ;
            type ncd:ifname ;
          }
          leaf switch {
            description 'Enable or disable ND inter-chassis backup delete-notif'
                      + 'y.'
                        ;
            type enumeration {
              enum enable {
                value 1 ;
                description 'Enable ND inter-chassis backup delete-notify.'
                            ;
              }
              enum disable {
                value 0 ;
                description 'Disable ND inter-chassis backup delete-notify.'
                            ;
              }
            }
            default enable ;
          }
        }
        ncd:revise-date 2021-04-20 ;
      }
    }
  }
  container operation {
    config false ;
    description 'Operation model info.'
                ;
    container nd {
      description 'Neighbor Discovery Protocol operation.'
                  ;
      container clear {
        description 'Clear operation.'
                    ;
        container nd-cache {
          description 'Clear ND dynamic cache entries.'
                      ;
          choice all-or-if {
            description 'Delete all dynamic ND cache entries or delete ND cache'
                      + ' entries on an interface.'
                        ;
            case all {
              description 'Delete all dynamic ND cache entries.'
                          ;
              leaf all-nd-cache {
                description 'All dynamic ND cache entries.'
                            ;
                type empty ;
              }
            }
            case by-if {
              description 'Delete ND cache entries on an interface.'
                          ;
              leaf ifname {
                description 'The name of the interface.'
                            ;
                type ncd:ifname ;
              }
            }
            ncd:revise-date 2015-04-08 ;
          }
        }
      }
    }
  }
  container state {
    config false ;
    description 'State model info.'
                ;
    container nd {
      description 'Neighbor discovery protocol state.'
                  ;
      container nd-caches {
        description 'Get ND cache entries.'
                    ;
        list nd-cache {
          description 'ND cache entries attributes.'
                      ;
          key 'ifname ipv6-address'
              ;
          leaf ifname {
            description 'The name of the interface.'
                        ;
            type ncd:ifname ;
          }
          leaf ipv6-address {
            description 'Nexthop IPv6 address.'
                        ;
            type ncd:ipv6-address ;
          }
          leaf mac {
            description 'MAC address.'
                        ;
            type ncd:mac-address ;
          }
          leaf status {
            description 'The current status of the entry.'
                        ;
            type string ;
          }
          leaf age {
            description 'The remaining life of the current status.'
                        ;
            type string ;
          }
          leaf type {
            description 'The type of the ND item.'
                        ;
            type string ;
            ncd:revise-date 2019-07-03 ;
          }
          ncd:select ifname ;
        }
      }
      container l2-proxy-items {
        if-feature get-l2-proxy-item ;
        description 'Show ND l2-proxy items'
                    ;
        list l2-proxy-item {
          if-feature get-l2-proxy-item ;
          description 'Show ND l2-proxy item'
                      ;
          key 'vpls-name ipv6-address'
              ;
          leaf vpls-name {
            description 'VPLS EVPN name'
                        ;
            type string ;
          }
          leaf ipv6-address {
            description 'IPv6 address'
                        ;
            type ncd:ipv6-address ;
          }
          leaf hardware-address {
            description 'MAC address'
                        ;
            type ncd:mac-address ;
          }
          leaf item-type {
            description 'L2-proxy item type'
                        ;
            type ncd:string-all ;
          }
          ncd:select vpls-name ;
        }
        ncd:revise-date 2020-05-06 ;
      }
      container mclag-check-items {
        if-feature mclag-consistency-check ;
        description 'Get the static ND information in MC-LAG consistency checki'
                  + 'ng.'
                    ;
        list mclag-check-item {
          description 'Get the static ND information in MC-LAG consistency chec'
                    + 'king.'
                      ;
          key 'ifname ipv6-address'
              ;
          leaf ifname {
            description 'The name of the interface.'
                        ;
            type ncd:ifname ;
          }
          leaf ipv6-address {
            description 'Nexthop IPv6 address.'
                        ;
            type ncd:ipv6-address ;
          }
          leaf local-mac {
            description 'MAC address of the local static ND item.'
                        ;
            type string ;
          }
          leaf remote-mac {
            description 'MAC address of the remote static ND item.'
                        ;
            type ncd:mac-address ;
          }
        }
        ncd:revise-date 2020-12-02 ;
      }
    }
  }
}
