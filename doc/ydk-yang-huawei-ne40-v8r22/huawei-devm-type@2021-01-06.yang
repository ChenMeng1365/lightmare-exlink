/*
Copyright (C) 2019-2021 Huawei Technologies Co., Ltd. All rights reserved.
*/
submodule huawei-devm-type {
  belongs-to huawei-devm {
    prefix devm;
  }

  organization
    "Huawei Technologies Co., Ltd.";
  contact
    "Huawei Industrial Base
     Bantian, Longgang
     Shenzhen 518129
     People's Republic of China
     Website: http://www.huawei.com
     Email: support@huawei.com";
  description
    "The submodule of devm : devm_type.";
   
   revision 2021-01-06 {
    description
      "Add a new port combination mode type.";
    reference
      "Huawei private.";
  }
   revision 2020-08-07 {
    description
      "Add a new operation status type.";
    reference
      "Huawei private.";
  }
   revision 2020-08-03 {
    description
      "Add a new type.";
    reference
      "Huawei private.";
  }
   revision 2020-04-29 {
    description
      "Add a new port type.";
    reference
      "Huawei private.";
  }
  revision 2020-04-18 {
    description
      "Add two notification types.";
    reference
      "Huawei private.";
  }

  revision 2020-04-10 {
    description
      "Modify description warnings.";
    reference
      "Huawei private.";
  }

  revision 2019-09-09 {
    description
      "Add new leafs.";
    reference
      "Huawei private.";
  }

  revision 2019-04-05 {
    description
      "Init revision.";
    reference
      "Huawei private.";
  }
  
  typedef entity-class-type {
    type enumeration {
      enum "other" {
        value 0;
        description
          "Other.";
      }
      enum "chassis" {
        value 1;
        description
          "Chassis.";
      }
      enum "mpuModule" {
        value 4;
        description
          "MPU.";
      }
      enum "lpuModule" {
        value 5;
        description
          "LPU.";
      }
      enum "sfuModule" {
        value 6;
        description
          "SFU.";
      }
      enum "clockModule" {
        value 7;
        description
          "CLK.";
      }
      enum "cardModule" {
        value 9;
        description
          "Card module.";
      }
      enum "port" {
        value 10;
        description
          "Port.";
      }
      enum "fan" {
        value 16;
        description
          "Fan.";
      }
      enum "powerSupply" {
        value 17;
        description
          "Power supply.";
      }
      enum "container" {
        value 18;
        description
          "Container.";
      }
      enum "ppModule" {
        value 4108;
        description
          "PP Module.";
      }
      enum "swfModule" {
        value 4109;
        description
          "Swf Module.";
      }
      enum "ecuModule" {
        value 4110;
        description
          "ECU.";
      }
      enum "icuModule" {
        value 4111;
        description
          "ICU.";
      }
      enum "lfe" {
        value 4162;
        description
          "LFE.";
      }
      enum "cfModule" {
        value 4170;
        description
          "CF card.";
      }  
      enum "lcd" {
        value 4181;
        description
          "LCD.";
      }
      enum "cmuModule" {
        value 5010;
        description
          "CMU.";
      }
      enum "pic" {
        value 5011;
        description
          "Pic.";
      }
      enum "Tsu" {
        value 5012;
        description
          "Tsu.";
      }
      enum "PEM" {
        value 5006;
        description
          "PEM.";
      }
      enum "pmu" {
        value 5031;
        description
          "PMU.";
      }
      enum "PM" {
        value 5032;
        description
          "PM.";
      }
      enum "tmppt" {
        value 4128;
        description
          "TMPPT.";
      }
      enum "vltpt" {
        value 4127;
        description
          "VLTPT.";
      }
    }
    description
      "Physical entity class.";
  }
  
   typedef entity-admin-state {
    type enumeration {
       enum "inactive" {
        value 0;
        description
          "Inactive state that disables service supply.";
      }
      enum "active" {
        value 1;
        description
          "Active state that enabled service supply.";
      }
      enum "notSupported" {
        value 2;
        description
          "Administration state not supported.";
      }
    }
    description
      "Entity admin state.";
  }

  typedef entity-oper-state-type {
    type enumeration {
      enum "unknown" {
        value 0;
        description
          "Unknown.";
      }
      enum "normal" {
        value 1;
        description
          "Normal.";
      }
      enum "fault" {
        value 2;
        description
          "Fault.";
      }
      enum "offline" {
        value 3;
        description
          "Offline.";
      }
      enum "notSupported" {
        value 4;
        description
          "Not supported.";
      }
      enum "opticalNotEquipped" {
        value 5;
        description
          "Optical module is not equipped.";
      }

      enum "notInstall" {
        value 6;
        description
          "Board is not installed.";
      }
      enum "wrongType" {
        value 7;
        description
          "Wrong board type.";
      }
      enum "registered" {
        value 8;
        description
          "Registered.";
      }
      enum "unregistered" {
        value 9;
        description
          "Unregistered.";
      }
      enum "poweroff" {
        value 10;
        description
          "Power off.";
      }
      enum "port-physical-down" {
        value 11;
        description
          "Port physical down.";
      }
      enum "online" {
        value 12;
        description
          "Online.";
      }
    }
    description
      "Entity operate state.";
  }
  
  typedef entity-standby-state {
    type enumeration {
      enum "master" {
        value 0;
        description
          "Master.";
      }
      enum "slave" {
        value 1;
        description
          "Slave.";
      }
      enum "notSupported" {
        value 2;
        description
          "Not supported.";
      }
      enum "systemMaster" {
        value 3;
        description
          "System master.";
      }
      enum "systemSlave" {
        value 4;
        description
          "System slave.";
      }
    }
    description
      "Entity standby state.";
  }

  typedef offline-class-type {
    type enumeration {
      enum "chassis" {
        value 1;
        description
          "Chassis.";
      }
      enum "board" {
        value 3;
        description
          "Board.";
      }
      enum "card" {
        value 8;
        description
          "Card position.";
      }
    }
    description
      "Offline class type.";
  }

  typedef container-class-type {
    type enumeration {
      enum "unknown" {
        value 0;
        description
          "Unknown.";
      }
      enum "boardSlot" {
        value 1;
        description
          "Board slot.";
      }
      enum "mpuSlot" {
        value 2;
        description
          "MPU slot.";
      }
      enum "lpuSlot" {
        value 3;
        description
          "LPU slot.";
      }
      enum "sfuSlot" {
        value 4;
        description
          "SFU slot.";
      }
      enum "icuSlot" {
        value 5;
        description
          "ICU slot.";
      }
      enum "ecuSlot" {
        value 6;
        description
          "ECU slot.";
      }
      enum "clkSlot" {
        value 7;
        description
          "CLK slot.";
      }
      enum "cmuSlot" {
        value 8;
        description
          "CMU slot.";
      }
      enum "fanSlot" {
        value 9;
        description
          "Fan slot.";
      }
      enum "powerSlot" {
        value 10;
        description
          "Power slot.";
      }
      enum "lcdSlot" {
        value 11;
        description
          "LCD slot.";
      }
      enum "picSlot" {
        value 12;
        description
          "PIC slot.";
      }
      enum "ofcSlot" {
        value 13;
        description
          "OFC slot.";
      }
      enum "cfcardSlot" {
        value 14;
        description
          "CF card slot.";
      }
      enum "virtualSlot" {
        value 15;
        description
          "Virtual slot.";
      }
      enum "virtualSubSlot" {
        value 16;
        description
          "Virtual sub-slot.";
      }
    }
    description
      "Container type.";
  }

  typedef lpu-service-type {
    type enumeration {
      enum "lpu" {
        value 0;
        description
          "LPU.";
      }
      enum "rnr" {
        value 1;
        description
          "RNR.";
      }
      enum "tsu" {
        value 2;
        description
          "TSU.";
      }
      enum "ns" {
        value 3;
        description
          "NS.";
      }
      enum "gre" {
        value 4;
        description
          "GRE.";
      }
      enum "vsu" {
        value 5;
        description
          "VSU.";
      }
    }
    description
      "LPU service type.";
  }

  typedef board-role-type {
    type enumeration {
      enum "unknown" {
        value 0;
        description
          "Unknown.";
      }
      enum "mmb" {
        value 1; 
        description
          "MMB.";
      }
      enum "plmb" {
        value 2;
        description
          "PLMB.";
      }
      enum "acmb" {
        value 3;
        description
          "ACMB.";
      }
      enum "mb" {
        value 4;
        description
          "MB.";
      }
      enum "lc" {
        value 5;
        description
          "LC.";
      }
      enum "sysmmb" {
        value 6;
        description
          "System mmb.";
      }
      enum "sysmb" {
        value 7;
        description
          "System mb.";
      }
    }
    description
      "Board role.";
  } 
 
  typedef port-class-type {
    type enumeration {
      enum "unknown" {
        value 0;
        description
          "Unknown.";
      }
      enum "Eth" {
        value 1;
        description
          "Ethernet.";
      }
      enum "Pos" {
        value 2;
        description
          "POS.";
      }
      enum "Cpos" {
        value 3;
        description
          "CPOS port.";
      }
      enum "E1" {
        value 4;
        description
          "E1 port.";
      }
      enum "GE" {
        value 5;
        description
          "GE port.";
      }
      enum "10GE" {
        value 6;
        description
          "10GE port.";
      }
      enum "GF" {
        value 7;
        description
          "GF port.";
      }
      enum "10GF" {
        value 8;
        description
          "10GF port.";
      }
      enum "40GF" {
        value 9;
        description
          "40GF port.";
      }
      enum "10GFCOM" {
        value 10;
        description
          "Combinable 10GF port.";
      }
      enum "40GFSPLIT" {
        value 11;
        description
          "Splitable 40GF port.";
      }
      enum "Otn" {
        value 12;
        description
          "OTN port.";
      }
      enum "100GF" {
        value 13;
        description
          "100GF port.";
      }
      enum "400GF" {
        value 14;
        description
          "400GF port.";
      }
      enum "25GF" {
        value 15;
        description
          "25GF port.";
      }
      enum "50GF" {
        value 16;
        description
          "50GF port.";
      }
      enum "200GF" {
        value 17;
        description
          "200GF port.";
      }
      enum "CELLULAR" {
        value 18;
        description
          "Cellular port.";
      }
       enum "FE" {
         value 19;
         description
           "FE.";
      }
       enum "FLEXE" {
         value 20;
         description
           "FLEXE.";
      }
       enum "VSR" {
         value 21;
         description
           "VSR.";
      }
      enum "OPTICALAMPLIFIER" {
        value 22;
        description
          "Optical amplifier port.";
      }
      enum "HP-GE" {
        value 23;
        description
          "High precision GE port.";
      }
      enum "E3" {
        value 24;
        description
        "E3 port.";
      }
      enum "ADM-CHANNEL" {
        value 25;
        description
        "ADM channel port.";
      }
      enum "ADM-PORT" {
        value 26;
        description
        "ADM port.";
      }
      enum "PHYSICAL-SERIAL" {
        value 27;
        description
        "Physical serial port.";
      }
    }
    description
      "Port type.";
  }

  typedef port-level-type {
    type enumeration {
      enum "GE" {
        value 1;
        description
          "GE.";
      }
    }
    description
      "Port level type.";
  }

  typedef port-hardware-type {
    type enumeration {
      enum "unknown" {
        value 0;
        description
          "Unknown.";
      }      
      enum "ETH-MGE-PORT" {
        value 1;
        description
          "Ethernet MEth Port.";
      }
      enum "ETH-10GF-PORT" {
        value 2;
        description
          "Ethernet 10G Fiber Port.";
      }
      enum "ETH-25GF-PORT" {
        value 3;
        description
          "Ethernet 25G Fiber Port.";
      }
      enum "ETH-40GF-PORT" {
        value 4;
        description
          "Ethernet 40G Fiber Port.";
      }
      enum "ETH-50GF-PORT" {
        value 5;
        description
          "Ethernet 50G Fiber Port.";
      }
      enum "ETH-100GF-PORT" {
        value 6;
        description
          "Ethernet 100G Fiber Port.";
      }
      enum "ETH-200GF-PORT" {
        value 7;
        description
          "Ethernet 200G Fiber Port.";
      }
      enum "ETH-400GF-PORT" {
        value 8;
        description
          "Ethernet 400G Fiber Port.";
      }
      enum "ETH-GE-PORT" {
        value 9;
        description
          "Ethernet GE Copper Port.";
      }
      enum "ETH-GF-PORT" {
        value 10;
        description
          "Ethernet GE Fiber Port.";
      }
      enum "CELLULAR-PORT" {
        value 11;
        description
          "Cellular Port.";
      }
    }
    description
      "Port hardtype.";
  }
  

  typedef port-medium-type {
    type enumeration {
      enum "notSupported" {
        value 0;
        description
          "Unsupported Type.";
      }
      enum "copper" {
        value 1;
        description
          "Copper.";
      }
      enum "fiber" {
        value 2;
        description
          "Fiber.";
      }
    }
    description
      "Port medium type.";
  }

  typedef hardware-type {
    type enumeration {
      enum "unknown" {
        value 0;
        description
          "Unknown.";
      }      
    }
    description
      "Entity hardtype.";
  }

  typedef loopback-state-type {
    type enumeration {
      enum "noLoopback" {
        value 0;
        description
          "No loopback.";
      }
      enum "localLoopback" {
        value 1;
        description
          "Local Loopback.";
      }
      enum "remoteLoopback" {
        value 2;
        description
          "Remote Loopback.";
      }
      enum "macLoopback" {
        value 3;
        description
          "MAC Loopback.";
      }
    }
    description
      "Port loopback state.";
  }

  typedef init-status-type {
    type enumeration {
      enum "fail" {
        value 0;
        description
          "Fail.";
      }
      enum "success" {
        value 1;
        description
          "Success.";
      }
      enum "unknown" {
        value 2;
        description
          "Unknown.";
      }
    }
    description
      "Card init status.";
  }
  
  typedef register-status-type {
    type enumeration {
      enum "unregistered" {
        value 0;
        description
          "Unregistered.";
      }
      enum "registered" {
        value 1;
        description
          "Registered.";
      }
      enum "unknown" {
        value 2;
        description
          "Unknown.";
      }
    }
    description
      "Card registered status.";
  }  

  typedef logic-status-type {
    type enumeration {
      enum "fail" {
        value 0;
        description
          "Fail.";
      }
      enum "success" {
        value 1;
        description
          "Success.";
      }
      enum "unknown" {
        value 2;
        description
          "Unknown.";
      }
    }
    description
      "Card logic status.";
  }

  typedef server-type {
    type enumeration {
      enum "ftp" {
        value 0;
        description
          "FTP.";
      }
      enum "tftp" {
        value 1;
        description
          "TFTP.";
      }
      enum "sftp" {
        value 2;
        description
          "SFTP.";
      }
    }
    description
      "Service type.";
  }

  typedef trans-type {
    type enumeration {
      enum "get" {
        value 0;
        description
          "GET.";
      }
      enum "put" {
        value 1;
        description
          "PUT.";
      }
    }
    description
      "Transmission type.";
  }

  typedef prefer-kex-type {
    type enumeration {
      enum "dh-exchange-group" {
        value 0;
        description
          "KEX_DH_EXCHANGE_GROUP.";
      }
      enum "dh-group1" {
        value 1;
        description
          "KEX_DH_GROUP1.";
      }
    }
    description
      "Prefer kex type.";
  }

  typedef cipher-type {
    type enumeration {
      enum "ase128" {
        value 1;
        description
          "ASE128.";
      }
      enum "aes128" {
        value 2;
        description
          "AES128.";
      }
    }
    description
      "Cipher type.";
  }

  typedef stoc-hmac-type {
    type enumeration {
      enum "md5" {
        value 0;
        description
          "MD5.";
      }
      enum "md5-96" {
        value 1;
        description
          "MD5-96.";
      }
      enum "sha1" {
        value 2;
        description
          "SHA1.";
      }
      enum "sha1-96" {
        value 3;
        description
          "SHA1-96.";
      }
    }
    description
      "Hmac type.";
  }


  typedef product-type {
    type enumeration {
      enum "unknown" {
        value 0;
        description
          "Unknown.";
      }
      enum "single" {
        value 1;
        description
          "Single.";
      }
      enum "ccc-0" {
        value 2;
        description
          "CCC-0.";
      }
      enum "ccc-1" {
        value 3;
        description
          "CCC-1.";
      }
      enum "ccc-2" {
        value 4;
        description
          "CCC-2.";
      }
    }
    description
      "Product type.";
  }
  typedef notification-entity-type {
    type enumeration {
      enum "UNKNOWN" {
        value 0;
        description
          "Unknown.";
      }
      enum "MPU" {
        value 1;
        description
          "MPU.";
      }
      enum "LPU" {
        value 2;
        description
          "LPU.";
      }
      enum "SFU" {
        value 3;
        description
          "SFU.";
      }
      enum "PIC" {
        value 4;
        description
          "PIC.";
      }
      enum "CF-CARD" {
        value 5;
        description
          "CF card.";
      }
      enum "OFC" {
        value 6;
        description
          "OFC.";
      }
    }
    description
      "Physical entity type.";
  }
  typedef notification-probable-cause-type {
    type enumeration {
      enum "unknown" {
        value 0;
        description
          "Unknown.";
      }
      enum "chasis-power-supply-insufficiency"{
        value 131336;
        description
          "The system power or the power of the backup power supply is insufficient.";
      }
      enum "all-sfu-boards-removed"{
        value 131337;
        description
          "No SFU is present in the chassis.";
      }
      enum "all-lpu-boards-removed"{
        value 131338;
        description
          "No LPU is present in the chassis.";
      }
      enum "all-cmu-boards-removed"{
        value 131339;
        description
          "No CMU is present in the chassis.";
      }
      enum "power-supply-module-mismatch-in-frame"{
        value 131340;
        description
          "Communication between the CMUs failed.";
      }
      enum "fail-to-get-slot-information-of-power-supply-module"{
        value 131341;
        description
          "Failed to obtain slot information of the power supply.";
      }
      enum "all-fans-absent"{
        value 131358;
        description
          "All fans are not in position.";
      }
      enum "sfu-board-dismatch-the-frame"{
        value 131586;
        description
          "Different SFUs were installed in the same chassis.";
      }
      enum "the-board-was-removed"{
        value 131840;
        description
          "A board was removed.";
      }
      enum "power-supply-for-a-board-was-abnormal"{
        value 132096;
        description
          "Power supply abnormal.";
      }
      enum "monitor-bus-of-board-partially-failed"{
        value 132097;
        description
          "Board CANBUS failed.";
      }
      enum "board-ce-powered-on-or-powered-off-properly-off"{
        value 132102;
        description
          "Board cannot be powered on or powered off properly.";
      }
      enum "battery-of-mpu-failed"{
        value 132103;
        description
          "Battery of mpu failed.";
      }
      enum "sensor-on-board-failed"{
        value 132105;
        description
          "The sensor on the board was faulty.";
      }
      enum "flash-memory-memory-on-board-failed"{
        value 132106;
        description
          "Flash memory failed.";
      }
      enum "phy-chip-on-board-partially-failed"{
        value 132107;
        description
          "Phy instability.";
      }
      enum "board-pll-malfunctions"{
        value 132128;
        description
          "Board PLL instability.";
      }
      enum "lanswitch-abnormal"{
        value 132134;
        description
          "LANSWITCH chip instability.";
      }
      enum "chip-malfunctions"{
        value 132137;
        description
          "Chip instability.";
      }
      enum "cpu-fault-occurred"{
        value 132152;
        description
          "A cpu fault occurred.";
      }
      enum "fan-or-power-dismatch-device"{
        value 132162;
        description
          "The fan model or power supply model does not match the device.";
      }
      enum "memory-size-is-different-from-rated"{
        value 132167;
        description
          "The memory size is different from the standard configuration.";
      }
      enum "data-channel-fault-occurred-on-forwarding-engine"{
        value 132189;
        description
          "A data channel fault occurred on the forwarding engine.";
      }
      enum "forward-engine-failed"{
        value 132190;
        description
          "The forwarding engine failed.";
      }
      enum "inter-card-broadcast-traffic-failed-to-be-forwarded"{
        value 132194;
        description
          "Inter-card broadcast traffic failed to be forwarded.";
      }
      enum "fabric-interface-input-or-output-bandwith-usage-exceeded"{
        value 132195;
        description
          "Fabric interface input or output bandwidth usage exceeded continuously.";
      }
      enum "ingress-clock-signals-channel-failed"{
        value 132196;
        description
          "Ingress clock signals channel failed.";
      }
      enum "egress-clock-signals-channel-failed"{
        value 132197;
        description
          "Egress clock signals channel failed.";
      }
      enum "38m-clock-failed"{
        value 132202;
        description
          "The 38M clock fails.";
      }
      enum "packet-reassembly-error-occurred"{
        value 132203;
        description
          "A packet reassembly error occurred.";
      }
      enum "hi-gig-link-on-board-failed"{
        value 132205;
        description
          "The serdes on the board failed.";
      }
      enum "board-clock-fails"{
        value 132207;
        description
          "The board clock fails.";
      }
      enum "ddr-fault-occurs-on-board"{
        value 132208;
        description
          "A DDR fault occurs on the board.";
      }
      enum "slot-id-of-board-fails-to-be-checked"{
        value 132209;
        description
          "The slot ID of the board fails to be checked.";
      }
      enum "pll-inside-forwarding-engine-is-not-ready"{
        value 132210;
        description
          "The PLL inside the forwarding engine is not ready.";
      }
      enum "internal-modular-of-forwarding-engine-is-abnormal"{
        value 132211;
        description
          "An internal modular of the forwarding engine is abnormal.";
      }
      enum "access-to-flash-memory-of-board-fails"{
        value 132212;
        description
          "Access to the flash memory of the board fails.";
      }
      enum "external-tcam-chip-could-nat-be-accessed"{
        value 132213;
        description
          "The micro switch of the board fails.";
      }
      enum "active-and-standby-mpus-cannot-communicate-with-each-other"{
        value 132214;
        description
          "The active and standby MPUs cannot communicate with each other.";
      }
      enum "fullin-signal-of-board-is-abnormal"{
        value 132215;
        description
          "The FULLIN signal of the board is abnormal.";
      }
      enum "serial-cpld-local-bus-fault-occurs-on-board"{
        value 132216;
        description
          "A SerialCpldLocalbus fault occurs on the board.";
      }
      enum "die-crack-of-cpu-side-occurs-on-board"{
        value 132275;
        description
          "A Die crack of CPU side occurs on the board.";
      }
      enum "die-crack-of-lsw-side-occurs-on-board"{
        value 132276;
        description
          "A Die crack of LSW side occurs on the board.";
      }
      enum "crc-fault-of-lsw-side-occurs-on-board"{
        value 132277;
        description
          "A CRC fault of LSW side occurs on the board.";
      }
      enum "crc-fault-of-cpu-side-occurs-on-board"{
        value 132278;
        description
          "A CRC fault of CPU side occurs on the board.";
      }
      enum "voltage-of-board-fails-to-be-checked"{
        value 132279;
        description
          "The voltage of the board fails to be checked.";
      }
      enum "slotid-signal-from-canbus-abnormal"{
        value 132290;
        description
          "The slot ID signal from the CANBUS is abnormal.";
      }
      enum "sensor-chip-faulty"{
        value 132298;
        description
          "The sensor chip on the board was faulty.";
      }
      enum "board-did-not-match-device"{
        value 132610;
        description
          "The board does not match the device.";
      }
      enum "fpga-logic-of-board-was-faulty"{
        value 132613;
        description
          "The FPGA entry of the board may be faulty.";
      }
      enum "epld-logic-of-board-was-faulty"{
        value 132614;
        description
          "The board failed CPLD local bus self-check.";
      }
      enum "clock-signals-failed-on-board"{
        value 132616;
        description
          "The clock signals of the board were incorrect.";
      }
      enum "board-was-power-off"{
        value 132626;
        description
          "The board was powered off.";
      }
      enum "board-registration-failed"{
        value 132627;
        description
          "The board was not registered.";
      }
      enum "board-obtained-abnormal-signals-from-master-and-slave-mpus"{
        value 132630;
        description
          "The board obtained abnormal signals from the master and slave MPUs.";
      }
      enum "board-type-mismatches-preconfiguration"{
        value 132666;
        description
          "The in-position board type conflicts with the pre-configured board type.";
      }
      enum "board-not-support-some-configurations-and-cannot-register"{
        value 132669;
        description
          "The board does not support some configurations and cannot register.";
      }
      enum "usb-overcurrent"{
        value 132670;
        description
          "USB overcurrent.";
      }
      enum "fpga-of-board-was-faulty"{
        value 132674;
        description
          "The FPGA of the board failed.";
      }
      enum "lsw-port-connected-to-mpu-fails"{
        value 132675;
        description
          "The PCIE of the board was faulty.";
      }
      enum "fpga-local-bus-self-test-failed"{
        value 132677;
        description
          "The FPGA local bus self-check failed.";
      }
      enum "notched-register-failed"{
        value 132688;
        description
          "Notched register failed.";
      }
      enum "pcie-link-failed"{
        value 132689;
        description
          "PCIE link failed.";
      }
      enum "different-sfus-mix-insert"{
        value 132699;
        description
          "Different SFUs were installed in the same chassis.";
      }
      enum "master-slave-board-switchover-was-performed"{
        value 133120;
        description
          "The master/slave board switchover was performed.";
      }
      enum "subcard-was-removed"{
        value 133376;
        description
          "A card was removed.";
      }
      enum "sensor-on-subcard-failed"{
        value 135170;
        description
          "The sensor on the subcard was faulty.";
      }
      enum "gephy-chip-on-sub-board-malfunctions"{
        value 135176;
        description
          "Phy instability.";
      }
      enum "chip-on-sub-board-malfunctions"{
        value 135180;
        description
          "The chip on the card fails.";
      }
      enum "phy-register-is-faulty"{
        value 135199;
        description
          "The PHY register is faulty.";
      }
      enum "epld-logic-of-subcard-was-faulty"{
        value 135424;
        description
          "The EPLD logic of the card was faulty.";
      }
      enum "clock-unit-on-subcard-was-faulty"{
        value 135427;
        description
          "The clock on the card failed.";
      }
      enum "card-was-powered-off"{
        value 135439;
        description
          "The card was powered off.";
      }
      enum "subcard-registration-failed-due-to-user-configuration"{
        value 135441;
        description
          "The card failed to be registered.";
      }
      enum "in-position-card-type-conflicts-with-pre-configured-card-type"{
        value 135464;
        description
          "The in-position card type conflicts with the pre-configured card type.";
      }
      enum "optical-module-was-removed"{
        value 135680;
        description
          "The optical module was removed.";
      }
      enum "output-optical-power-was-too-high"{
        value 136193;
        description
          "Output Optical Power Too High.";
      }
      enum "output-optical-power-was-too-low"{
        value 136194;
        description
          "Output Optical Power Too Low.";
      }
      enum "input-optical-power-was-too-high"{
        value 136195;
        description
          "Input Optical Power Too High.";
      }
      enum "input-optical-power-was-too-low"{
        value 136196;
        description
          "Input Optical Power Too Low.";
      }
      enum "voltage-of-optical-module-too-high"{
        value 136197;
        description
          "The voltage of the optical module was too high.";
      }
      enum "voltage-of-optical-module-too-low"{
        value 136198;
        description
          "The voltage of the optical module was too Low.";
      }
      enum "bias-current-of-optical-module-too-high"{
        value 136199;
        description
          "The bias current of the optical module was too high.";
      }
      enum "bias-current-of-optical-module-too-low"{
        value 136200;
        description
          "The bias current of the optical module was too low.";
      }
      enum "temperature-of-optical-module-too-high"{
        value 136201;
        description
          "The temperature of the optical module was too high.";
      }
      enum "temperature-of-optical-module-too-low"{
        value 136202;
        description
          "The temperature of the optical module was too low.";
      }
      enum "optical-module-dismatch"{
        value 136203;
        description
          "Optical module dismatch.";
      }
      enum "iic-of-optical-module-failed"{
        value 136231;
        description
          "The IIC of the optical module failed.";
      }
      enum "physical-interface-was-down"{
        value 144384;
        description
          "The physical interface was down.";
      }
      enum "optical-module-unautorized"{
        value 145920;
        description
          "An optical module that is not certified for Huawei Ethernet switches was installed.";
      }
      enum "some-internal-crc-error-packets-generated-on-sfu"{
        value 147200;
        description
          "A small number of internal CRC error packets are generated on the SFU.";
      }
      enum "packet-loss-occurred-in-queue-on-sfu"{
        value 147201;
        description
          "Packet loss occurred in a queue on an SFU.";
      }
      enum "packet-loss-occurred-in-queue-on-fdr-module-of-lpu"{
        value 147202;
        description
          "Packet loss occurred in a queue on the FDR module of an LPU.";
      }
      enum "buffer-usage-of-sfu-is-high"{
        value 147203;
        description
          "The buffer usage of the SFU is high. Check its bandwidth.";
      }
      enum "all-links-on-sfu-are-down"{
        value 147204;
        description
          "All links on the SFU are down.";
      }
      enum "packet-loss-occurs-on-forward-engine-ingress-interface"{
        value 147205;
        description
          "Packet loss occurs on forward engine ingress interface.";
      }
      enum "link-access-to-forwarding-engine-is-abnormal"{
        value 147206;
        description
          "Link access to the forwarding engine is abnormal.";
      }
      enum "volume-of-forwarded-traffic-is-close-to-maximum-capability"{
        value 147207;
        description
          "The volume of forwarded traffic is close to the maximum forwarding capability of the device.";
      }
      enum "cpu-failed-to-send-packets"{
        value 147208;
        description
          "The CPU failed to send packets.";
      }
      enum "port-between-lsw-and-coprocessor-is-down"{
        value 147209;
        description
          "The port between LSW and Coprocessor is Down.";
      }
      enum "pll-status-unlocked-on-port-between-lsw-and-coprocessor"{
        value 147210;
        description
          "The PLL status is unlocked on the port between LSW and Coprocessor.";
      }
      enum "crc-error-packets-arise-on-port-between-lsw-and-coprocessor"{
        value 147211;
        description
          "CRC error packets are generated on the port between LSW and Coprocessor.";
      }
      enum "bandwidth-usage-of-internal-communication-interfaces-exceeded"{
        value 147212;
        description
          "The bandwidth usage of internal communication interfaces exceeded.";
      }
      enum "packet-loss-occurred-on-internal-communication-interfaces"{
        value 147213;
        description
          "Packet loss occurred on internal communication interfaces.";
      }
      enum "bandwidth-of-links-between-sfu-and-lpu-was-insufficient"{
        value 147214;
        description
          "The bandwidth of links between an SFU and an LPU was insufficient.";
      }
      enum "access-to-forwarding-engine-is-unstable"{
        value 147215;
        description
          "Access to the forwarding engine is unstable.";
      }
      enum "hard-disk-is-not-certified"{
        value 132302;
        description
          "The currently used hard disk is not certified by Huawei.";
      }
      enum "disk-pulled-out"{
        value 132303;
        description
          "The hard disk was pulled out.";
      }
      enum "voltage-fails-to-be-checked"{
        value 135204;
        description
          "The voltage fails to be checked.";
      }
      enum "storage-medium-remove"{
        value 133377;
        description
          "A storage medium was removed.";
      }
      enum "device-certificate-verify-fail"{
        value 132305;
        description
          "The device certificate verification failed.";
      }
    }
    description
      "This list contains the root reasons of the Huawei proprietary notifications.";
  }
  typedef switch-status-type {
    type enumeration {
      enum "enable" {
        value 0;
        description
          "Switch open.";
      }
      enum "disable" {
        value 1;
        description
          "Switch close.";
      }
    }
    description
      "Switch status type.";
  }
  typedef port-combination-mode-type {
    type enumeration {
      enum "8X10GE" {
        value 0;
        description
          "8*10GE mode.";
      }
      enum "1X100GE" {
        value 1;
        description
          "1*100GE mode.";
      }
      enum "2X40GE" {
        value 2;
        description
          "2*40GE mode.";
      }
      enum "4X25GE" {
        value 3;
        description
          "4*25GE mode.";
      }
    }
    description
      "Port combination mode type.";
  }
  typedef present-status {
    type enumeration {
      enum "ABSENT" {
        value 0;
        description
          "Absent.";
      }
      enum "PRESENT" {
        value 1;
        description
          "Present.";
      }
    }
    description
      "Present status of an entity.";
  }
}
