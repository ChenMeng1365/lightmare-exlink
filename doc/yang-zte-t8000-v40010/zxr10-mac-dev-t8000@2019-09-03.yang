module zxr10-mac-dev-t8000 {
  namespace 'http://www.zte.com.cn/zxr10/netconf/schema/rosng/zxr10-mac-dev-t80'
          + '00'
            ;
  prefix mac-dev-t8000 ;
  import zxr10-mac {
    prefix mac ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2019-09-03 {
    description '1.Delete /mac:state/mac:mac/mac:mac-vpls-tables/mac:mac-vpls-t'
              + 'able/mac:evpn-tunnel-id.'+"\n"
              + '2.Delete /mac:state/mac:mac/mac:mac-vpls-tables/mac:mac-vpls-t'
              + 'able/mac:vni.'
                ;
  }
  revision 2017-11-15 {
    description '1.Delete deviation mac-vxlan-tables-expand, mac-permanent-vxla'
              + 'n-mac-address-no-vlan, delete-vxlan-no-config-mac.'
                ;
  }
  revision 2017-07-13 {
    description '1.T8000 added support lacp,lldp protocol.'
                ;
  }
  revision 2016-10-17 {
    description 'Add deviation for T8000.'
                ;
  }
  deviation /mac:state/mac:mac/mac:mac-tables {
    deviate not-supported ;
  }
  deviation /mac:state/mac:mac/mac:mac-count-tables {
    deviate not-supported ;
  }
  deviation '/mac:configuration/mac:mac/mac:vpls-instance-config/mac:vpls-confi'
          + 'g/mac:mac-learning/mac:remote-no-learning'
            {
    deviate not-supported ;
  }
  deviation '/mac:configuration/mac:mac/mac:vpls-instance-config/mac:vpls-confi'
          + 'g/mac:l2protocol-control-policy-expand/mac:zdp-ztp'
            {
    deviate not-supported ;
  }
  deviation '/mac:configuration/mac:mac/mac:vpls-instance-config/mac:vpls-confi'
          + 'g/mac:l2protocol-control-policy-expand/mac:all-bridge-multicast'
            {
    deviate not-supported ;
  }
  deviation '/mac:configuration/mac:mac/mac:vpls-instance-config/mac:vpls-confi'
          + 'g/mac:l2protocol-control-policy-expand/mac:dot1x'
            {
    deviate not-supported ;
  }
  deviation '/mac:configuration/mac:mac/mac:vpls-instance-config/mac:vpls-confi'
          + 'g/mac:l2protocol-control-policy-expand/mac:pvst-plus'
            {
    deviate not-supported ;
  }
  deviation '/mac:configuration/mac:mac/mac:vpls-instance-config/mac:vpls-confi'
          + 'g/mac:l2protocol-control-policy-expand/mac:udld'
            {
    deviate not-supported ;
  }
  deviation '/mac:configuration/mac:mac/mac:vpls-instance-config/mac:vpls-confi'
          + 'g/mac:l2protocol-control-policy-expand/mac:mstp'
            {
    deviate not-supported ;
  }
  deviation '/mac:configuration/mac:mac/mac:vpls-instance-config/mac:vpls-confi'
          + 'g/mac:l2protocol-control-policy-expand/mac:rstp'
            {
    deviate not-supported ;
  }
  deviation '/mac:configuration/mac:mac/mac:vpls-instance-config/mac:vpls-confi'
          + 'g/mac:l2protocol-control-policy-expand/mac:gvrp'
            {
    deviate not-supported ;
  }
  deviation '/mac:configuration/mac:mac/mac:vpls-instance-config/mac:vpls-confi'
          + 'g/mac:l2protocol-control-policy-expand/mac:pbb-te'
            {
    deviate not-supported ;
  }
  deviation '/mac:configuration/mac:mac/mac:vpls-instance-config/mac:vpls-confi'
          + 'g/mac:l2protocol-control-policy-expand/mac:mac-in-mac'
            {
    deviate not-supported ;
  }
  deviation '/mac:configuration/mac:mac/mac:vpls-instance-config/mac:vpls-confi'
          + 'g/mac:l2protocol-control-policy-expand/mac:efm'
            {
    deviate not-supported ;
  }
  deviation '/mac:configuration/mac:mac/mac:vpls-instance-config/mac:vpls-confi'
          + 'g/mac:l2protocol-control-policy-expand/mac:cfm'
            {
    deviate not-supported ;
  }
  deviation '/mac:configuration/mac:mac/mac:vpls-instance-config/mac:vpls-confi'
          + 'g/mac:l2protocol-control-policy-expand/mac:y1731'
            {
    deviate not-supported ;
  }
  deviation '/mac:configuration/mac:mac/mac:vpls-instance-config/mac:vpls-confi'
          + 'g/mac:l2protocol-control-policy-expand/mac:garp'
            {
    deviate not-supported ;
  }
  deviation '/mac:configuration/mac:mac/mac:vpls-instance-config/mac:vpls-confi'
          + 'g/mac:l2protocol-control-policy-expand/mac:gmrp'
            {
    deviate not-supported ;
  }
  deviation '/mac:configuration/mac:mac/mac:vpls-instance-config/mac:vpls-confi'
          + 'g/mac:l2protocol-control-policy-expand/mac:dldp'
            {
    deviate not-supported ;
  }
  deviation '/mac:configuration/mac:mac/mac:vpls-instance-config/mac:vpls-confi'
          + 'g/mac:l2protocol-control-policy-expand/mac:dot3x'
            {
    deviate not-supported ;
  }
  deviation '/mac:configuration/mac:mac/mac:vpls-instance-config/mac:vpls-confi'
          + 'g/mac:l2protocol-control-policy-expand/mac:erps'
            {
    deviate not-supported ;
  }
  deviation '/mac:configuration/mac:mac/mac:vpls-port-config/mac:mac-vfi-port-c'
          + 'onfig/mac:learn-priority'
            {
    deviate not-supported ;
  }
  deviation '/mac:configuration/mac:mac/mac:permanent-mac-address/mac:mac-perma'
          + 'nent-address-no-vpn'
            {
    deviate not-supported ;
  }
  deviation /mac:configuration/mac:mac/mac:global-config/mac:higig-learn {
    deviate not-supported ;
  }
  deviation '/mac:configuration/mac:mac/mac:global-config/mac:default-priority-'
          + 'movable'
            {
    deviate not-supported ;
  }
  deviation '/mac:configuration/mac:mac/mac:global-config/mac:lower-priority-mo'
          + 'vable'
            {
    deviate not-supported ;
  }
  deviation '/mac:configuration/mac:mac/mac:global-config/mac:normal-priority-m'
          + 'ovable'
            {
    deviate not-supported ;
  }
  deviation '/mac:configuration/mac:mac/mac:global-config/mac:higher-priority-m'
          + 'ovable'
            {
    deviate not-supported ;
  }
  deviation '/mac:configuration/mac:mac/mac:global-config/mac:exceed-limit-acti'
          + 'on'
            {
    deviate not-supported ;
  }
  deviation /mac:configuration/mac:mac/mac:global-config/mac:safe-mode-policy {
    deviate not-supported ;
  }
  deviation '/mac:configuration/mac:mac/mac:global-config/mac:auto-write-toperm'
          + 'anent'
            {
    deviate not-supported ;
  }
  deviation '/mac:configuration/mac:mac/mac:global-config/mac:auto-write-toperm'
          + 'anent-interval'
            {
    deviate not-supported ;
  }
  deviation '/mac:configuration/mac:mac/mac:global-config/mac:forbidden-mac-rea'
          + 'ction'
            {
    deviate not-supported ;
  }
  deviation '/mac:configuration/mac:mac/mac:global-config/mac:learn-disable-act'
          + 'ion'
            {
    deviate not-supported ;
  }
  deviation /mac:configuration/mac:mac/mac:global-config/mac:mac-update-notify {
    deviate not-supported ;
  }
  deviation '/mac:configuration/mac:mac/mac:global-config/mac:mac-notify-interv'
          + 'al'
            {
    deviate not-supported ;
  }
  deviation /mac:configuration/mac:mac/mac:global-config/mac:notify-max-mac-num {
    deviate not-supported ;
  }
  deviation /mac:configuration/mac:mac/mac:port-config {
    deviate not-supported ;
  }
  deviation /mac:configuration/mac:mac/mac:vlan-config {
    deviate not-supported ;
  }
  deviation /mac:configuration/mac:mac/mac:forbidden-mac {
    deviate not-supported ;
  }
  deviation /mac:configuration/mac:mac/mac:forbidden-bind-port {
    deviate not-supported ;
  }
  deviation /mac:operation/mac:mac/mac:to-statics {
    deviate not-supported ;
  }
  deviation /mac:operation/mac:mac/mac:delete-normal-no-config-mac {
    deviate not-supported ;
  }
  deviation /mac:operation/mac:mac/mac:learn-priority-policy {
    deviate not-supported ;
  }
}
