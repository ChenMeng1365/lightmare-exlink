module zxr10-vxlancar {
  namespace 'http://www.zte.com.cn/zxr10/netconf/schema/rosng/vxlancar'
            ;
  prefix vxlancar ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe QoS VXLAN CAR info.'
              ;
  revision 2021-01-28 {
    description 'Support to configure VXLAN CAR base on IPv4 address or vni, ad'
              + 'd new containers as follows:'+"\n"
              + '/configuration/qos/vni-or-addr-vxlan-cars.'
                ;
  }
  revision 2019-03-14 {
    description 'Support to configure VXLAN CAR, add new containers as follows:'
              + ''+"\n"
              + '/configuration/qos/ipv4-vxlan-cars.'
                ;
  }
  feature qos-vni-or-addr-vxlan-cars ;
  typedef qos-dscp-bitmap {
    type ncd:bitmap {
      pattern '(((((([1-9][0-9]{0,0})|0|([1-5][0-9]{1,1})|(6[0-2])|63)-(([1-9]['
            + '0-9]{0,0})|0|([1-5][0-9]{1,1})|(6[0-2])|63))|(([1-9][0-9]{0,0})|'
            + '0|([1-5][0-9]{1,1})|(6[0-2])|63)),){0,3}(((([1-9][0-9]{0,0})|0|('
            + '[1-5][0-9]{1,1})|(6[0-2])|63)-(([1-9][0-9]{0,0})|0|([1-5][0-9]{1'
            + ',1})|(6[0-2])|63))|(([1-9][0-9]{0,0})|0|([1-5][0-9]{1,1})|(6[0-2'
            + '])|63)){1,1})'
              {
        description 'Configure DSCP in range mode, support single DSCP value or'
                  + ' range(max num:4;spacing mark:,) in <0-63>.'
                    ;
      }
    }
    description 'The definition of QoS dscp in range mode, support single DSCP '
              + 'value or range(max num:4;spacing mark:,) in <0-63>. For exampl'
              + 'e,"6,10-30,40,50-60",etc.'
                ;
  }
  typedef qos-prec-bitmap {
    type ncd:bitmap {
      pattern '(((([0-7]-[0-7])|[0-7]),){0,3}(([0-7]-[0-7])|([0-7])){1,1})'
              {
        description 'Configure IP-Precedence in range mode, support single prec'
                  + 'edence value or range(max num:4;spacing mark:,) in <0-7>.'
                    ;
      }
    }
    description 'The definition of QoS IP-Precedence in range mode, support sin'
              + 'gle precedence value or range(max num:4;spacing mark:,) in <0-'
              + '7>. For example,"0,4-7",etc.'
                ;
  }
  typedef qos-vlan-bitmap {
    type ncd:bitmap {
      pattern '(((((([1-9][0-9]{1,2})|([2-9][0-9]{0,0})|1|([1-3][0-9]{3,3})|(40'
            + '[0-8][0-9]{1,1})|(409[0-3])|4094)-(([1-9][0-9]{1,2})|([2-9][0-9]'
            + '{0,0})|1|([1-3][0-9]{3,3})|(40[0-8][0-9]{1,1})|(409[0-3])|4094))'
            + '|(([1-9][0-9]{1,2})|([2-9][0-9]{0,0})|1|([1-3][0-9]{3,3})|(40[0-'
            + '8][0-9]{1,1})|(409[0-3])|4094)),){0,3}(((([1-9][0-9]{1,2})|([2-9'
            + '][0-9]{0,0})|1|([1-3][0-9]{3,3})|(40[0-8][0-9]{1,1})|(409[0-3])|'
            + '4094)-(([1-9][0-9]{1,2})|([2-9][0-9]{0,0})|1|([1-3][0-9]{3,3})|('
            + '40[0-8][0-9]{1,1})|(409[0-3])|4094))|(([1-9][0-9]{1,2})|([2-9][0'
            + '-9]{0,0})|1|([1-3][0-9]{3,3})|(40[0-8][0-9]{1,1})|(409[0-3])|409'
            + '4)){1,1})'
              {
        description 'Configure VLAN in range mode, support single VLAN value or'
                  + ' range(max num:4;spacing mark:,) in <1-4094>.'
                    ;
      }
    }
    description 'The definition of QoS VLAN in range mode, support single VLAN '
              + 'value or range(max num:4;spacing mark:,) in <1-4094>. For exam'
              + 'ple,"1-300,400,450-500",etc.'
                ;
  }
  typedef qos-mpls-bitmap {
    type ncd:bitmap {
      pattern '(((([0-7]-[0-7])|[0-7]),){0,3}(([0-7]-[0-7])|([0-7])){1,1})'
              {
        description 'Configure MPLS-EXP in range mode, support single MPLS-EXP '
                  + 'value or range(max num:4;spacing mark:,) in <0-7>.'
                    ;
      }
    }
    description 'The definition of QoS MPLS-EXP in range mode, support single M'
              + 'PLS-EXP value or range(max num:4;spacing mark:,) in <0-7>. For'
              + ' example,"0,3-5,7",etc.'
                ;
  }
  typedef qos-8021p-bitmap {
    type ncd:bitmap {
      pattern '(((([0-7]-[0-7])|[0-7]),){0,3}(([0-7]-[0-7])|([0-7])){1,1})'
              {
        description 'Configure 802.1p in range mode, support single 802.1p valu'
                  + 'e or range(max num:4;spacing mark:,) in <0-7>.'
                    ;
      }
    }
    description 'The definition of QoS 802.1p in range mode, support single 802'
              + '.1p value or range(max num:4;spacing mark:,) in <0-7>. For exa'
              + 'mple,"0,3-5,7",etc.'
                ;
  }
  typedef qos-vlan-range {
    type ncd:range {
      pattern '(((((([1-9][0-9]{1,2})|([2-9][0-9]{0,0})|1|([1-3][0-9]{3,3})|(40'
            + '[0-8][0-9]{1,1})|(409[0-3])|4094)-(([1-9][0-9]{1,2})|([2-9][0-9]'
            + '{0,0})|1|([1-3][0-9]{3,3})|(40[0-8][0-9]{1,1})|(409[0-3])|4094))'
            + '|(([1-9][0-9]{1,2})|([2-9][0-9]{0,0})|1|([1-3][0-9]{3,3})|(40[0-'
            + '8][0-9]{1,1})|(409[0-3])|4094)),){0,3}(((([1-9][0-9]{1,2})|([2-9'
            + '][0-9]{0,0})|1|([1-3][0-9]{3,3})|(40[0-8][0-9]{1,1})|(409[0-3])|'
            + '4094)-(([1-9][0-9]{1,2})|([2-9][0-9]{0,0})|1|([1-3][0-9]{3,3})|('
            + '40[0-8][0-9]{1,1})|(409[0-3])|4094))|(([1-9][0-9]{1,2})|([2-9][0'
            + '-9]{0,0})|1|([1-3][0-9]{3,3})|(40[0-8][0-9]{1,1})|(409[0-3])|409'
            + '4)){1,1})'
              {
        description 'Configure VLAN in range mode, support single VLAN value or'
                  + ' range(max num:4;spacing mark:,) in <1-4094>.'
                    ;
      }
    }
    description 'The definition of QoS VLAN in range mode, support single VLAN '
              + 'value or range(max num:4;spacing mark:,) in <1-4094>. For exam'
              + 'ple,"1-300,400,450-500",etc.'
                ;
  }
  typedef qos-service-class {
    type enumeration {
      enum be {
        value 1 ;
        description 'Best effort'
                    ;
      }
      enum af1 {
        value 2 ;
        description 'Assured forwarding class 1'
                    ;
      }
      enum af2 {
        value 3 ;
        description 'Assured forwarding class 2'
                    ;
      }
      enum af3 {
        value 4 ;
        description 'Assured forwarding class 3'
                    ;
      }
      enum af4 {
        value 5 ;
        description 'Assured forwarding class 4'
                    ;
      }
      enum ef {
        value 6 ;
        description 'Expedited forward'
                    ;
      }
      enum cs6 {
        value 7 ;
        description 'Internetwork control service class'
                    ;
      }
      enum cs7 {
        value 8 ;
        description 'Network control service class'
                    ;
      }
    }
    description 'The definition of server class of PHB info, see below:'+"\n"
              + '             be (1) Best effort'+"\n"
              + '             af1(2) Assured forwarding class 1'+"\n"
              + '             af2(3) Assured forwarding class 2'+"\n"
              + '             af3(4) Assured forwarding class 3'+"\n"
              + '             af4(5) Assured forwarding class 4'+"\n"
              + '             ef (6) Expedited forward'+"\n"
              + '             cs6(7) Internetwork control service class'+"\n"
              + '             cs7(8) Network control service class'
                ;
  }
  typedef qos-color-type {
    type enumeration {
      enum green {
        value 1 ;
        description 'Green packets'
                    ;
      }
      enum yellow {
        value 2 ;
        description 'Yellow packets'
                    ;
      }
      enum red {
        value 3 ;
        description 'Red packets'
                    ;
      }
    }
    description 'The definition of color type of PHB info, see below:'+"\n"
              + '             green  (1) Green packets'+"\n"
              + '             yellow (2) Yellow packets'+"\n"
              + '             red    (3) Red packets'
                ;
  }
  typedef qos-reserved-words {
    type enumeration {
      enum default {
        value 0 ;
        description 'Match packets with default dscp (000000)'
                    ;
      }
      enum af11 {
        value 10 ;
        description 'Match packets with AF11 dscp (001010)'
                    ;
      }
      enum af12 {
        value 12 ;
        description 'Match packets with AF12 dscp (001100)'
                    ;
      }
      enum af13 {
        value 14 ;
        description 'Match packets with AF13 dscp (001110)'
                    ;
      }
      enum af21 {
        value 18 ;
        description 'Match packets with AF21 dscp (010010)'
                    ;
      }
      enum af22 {
        value 20 ;
        description 'Match packets with AF22 dscp (010100)'
                    ;
      }
      enum af23 {
        value 22 ;
        description 'Match packets with AF23 dscp (010110)'
                    ;
      }
      enum af31 {
        value 26 ;
        description 'Match packets with AF31 dscp (011010)'
                    ;
      }
      enum af32 {
        value 28 ;
        description 'Match packets with AF32 dscp (011100)'
                    ;
      }
      enum af33 {
        value 30 ;
        description 'Match packets with AF33 dscp (011110)'
                    ;
      }
      enum af41 {
        value 34 ;
        description 'Match packets with AF41 dscp (100010)'
                    ;
      }
      enum af42 {
        value 36 ;
        description 'Match packets with AF42 dscp (100100)'
                    ;
      }
      enum af43 {
        value 38 ;
        description 'Match packets with AF43 dscp (100110)'
                    ;
      }
      enum ef {
        value 46 ;
        description 'Match packets with EF dscp (101110)'
                    ;
      }
      enum cs1 {
        value 8 ;
        description 'Match packets with CS1(precedence 1) dscp (001000)'
                    ;
      }
      enum cs2 {
        value 16 ;
        description 'Match packets with CS2(precedence 2) dscp (010000)'
                    ;
      }
      enum cs3 {
        value 24 ;
        description 'Match packets with CS3(precedence 3) dscp (011000)'
                    ;
      }
      enum cs4 {
        value 32 ;
        description 'Match packets with CS4(precedence 4) dscp (100000)'
                    ;
      }
      enum cs5 {
        value 40 ;
        description 'Match packets with CS5(precedence 5) dscp (101000)'
                    ;
      }
      enum cs6 {
        value 48 ;
        description 'Match packets with CS6(precedence 6) dscp (110000)'
                    ;
      }
      enum cs7 {
        value 56 ;
        description 'Match packets with CS7(precedence 7) dscp (111000)'
                    ;
      }
    }
    description 'The definition of resserved words of DSCP info ,see below:'+"\n"
              + '      default(0) Match packets with default dscp (000000)     '
              + ' '+"\n"
              + '      af11(10)   Match packets with AF11 dscp (001010)        '
              + '                        '+"\n"
              + '      af12(12)   Match packets with AF12 dscp (001100)        '
              + '                        '+"\n"
              + '      af13(14)   Match packets with AF13 dscp (001110)        '
              + '                        '+"\n"
              + '      af21(18)   Match packets with AF21 dscp (010010)        '
              + '                        '+"\n"
              + '      af22(20)   Match packets with AF22 dscp (010100)        '
              + '                        '+"\n"
              + '      af23(22)   Match packets with AF23 dscp (010110)        '
              + '                        '+"\n"
              + '      af31(26)   Match packets with AF31 dscp (011010)        '
              + '                        '+"\n"
              + '      af32(28)   Match packets with AF32 dscp (011100)        '
              + '                        '+"\n"
              + '      af33(30)   Match packets with AF33 dscp (011110)        '
              + '                        '+"\n"
              + '      af41(34)   Match packets with AF41 dscp (100010)        '
              + '                        '+"\n"
              + '      af42(36)   Match packets with AF42 dscp (100100)        '
              + '                        '+"\n"
              + '      af43(38)   Match packets with AF43 dscp (100110)   '+"\n"
              + '      ef(46)     Match packets with EF dscp (101110)          '
              + '                   '+"\n"
              + '      cs1(8)     Match packets with CS1(precedence 1) dscp (00'
              + '1000)                   '+"\n"
              + '      cs2(16)    Match packets with CS2(precedence 2) dscp (01'
              + '0000)                   '+"\n"
              + '      cs3(24)    Match packets with CS3(precedence 3) dscp (01'
              + '1000)                   '+"\n"
              + '      cs4(32)    Match packets with CS4(precedence 4) dscp (10'
              + '0000)                   '+"\n"
              + '      cs5(40)    Match packets with CS5(precedence 5) dscp (10'
              + '1000)                   '+"\n"
              + '      cs6(48)    Match packets with CS6(precedence 6) dscp (11'
              + '0000)                   '+"\n"
              + '      cs7(56)    Match packets with CS7(precedence 7) dscp (11'
              + '1000)'
                ;
  }
  typedef qos-ip-type {
    type enumeration {
      enum any {
        value 0 ;
        description 'Based on any IP'
                    ;
      }
      enum ipv4 {
        value 1 ;
        description 'Based on IPv4'
                    ;
      }
      enum ipv6 {
        value 2 ;
        description 'Based on IPv6'
                    ;
      }
    }
    description 'Configure based on IP, see below:'+"\n"
              + '      any  Packets based on any IP;'+"\n"
              + '      ipv4 Packets based on IPv4;'+"\n"
              + '      ipv6 Packets based on IPv6;'
                ;
  }
  typedef qos-rate-unit-type {
    type enumeration {
      enum kbps {
        value 1 ;
        description 'Kilobits per second'
                    ;
      }
      enum mbps {
        value 2 ;
        description 'Megabits per second'
                    ;
      }
      enum gbps {
        value 3 ;
        description 'Gigabits per second'
                    ;
      }
      enum pps {
        value 4 ;
        description 'Packet per second'
                    ;
      }
    }
    description 'The definition of rate unit of police car info, see below:'+"\n"
              + '             kbps  (1) Kilobits per second'+"\n"
              + '             mbps  (2) Megabits per second'+"\n"
              + '             gbps  (3) Gigabits per second'+"\n"
              + '             pps   (4) Packet   per second'
                ;
  }
  typedef qos-bucket-unit-type {
    type enumeration {
      enum kb {
        value 1 ;
        description Kilobits ;
      }
      enum mb {
        value 2 ;
        description Megabits ;
      }
      enum gb {
        value 3 ;
        description Gigabits ;
      }
    }
    description 'The definition of bucket unit of police car info, see below:'+"\n"
              + '             kb  (1) Kilobits'+"\n"
              + '             mb  (2) Megabits'+"\n"
              + '             gb  (3) Gigabits'
                ;
  }
  typedef qos-threshold-unit-type {
    type enumeration {
      enum kbytes {
        value 1 ;
        description Kilobytes ;
      }
      enum mbytes {
        value 2 ;
        description Megabytes ;
      }
      enum gbytes {
        value 3 ;
        description Gigabytes ;
      }
    }
    description 'The definition of threshold unit of wred info, see below:'+"\n"
              + '             kb  (1) Kilobytes'+"\n"
              + '             mb  (2) Megabytes'+"\n"
              + '             gb  (3) Gigabytes'
                ;
  }
  typedef qos-direction {
    type enumeration {
      enum input {
        value 1 ;
        description 'input  Attaches to the input flow'
                    ;
      }
      enum output {
        value 2 ;
        description 'output Attaches to the output flow'
                    ;
      }
    }
    description 'The flow direction, as follows,'+"\n"
              + '     input  Attaches to the input flow'+"\n"
              + '     output Attaches to the output flow'
                ;
  }
  typedef qos-port-range {
    type ncd:range {
      pattern '(((((([1-9][0-9]{1,3})|([1-9][0-9]{0,0})|0|([1-5][0-9]{4,4})|(6['
            + '0-4][0-9]{3,3})|(65[0-4][0-9]{2,2})|(655[0-2][0-9]{1,1})|(6553[0'
            + '-4])|65535)-(([1-9][0-9]{1,3})|([1-9][0-9]{0,0})|0|([1-5][0-9]{4'
            + ',4})|(6[0-4][0-9]{3,3})|(65[0-4][0-9]{2,2})|(655[0-2][0-9]{1,1})'
            + '|(6553[0-4])|65535))|(([1-9][0-9]{1,3})|([1-9][0-9]{0,0})|0|([1-'
            + '5][0-9]{4,4})|(6[0-4][0-9]{3,3})|(65[0-4][0-9]{2,2})|(655[0-2][0'
            + '-9]{1,1})|(6553[0-4])|65535)),){0,3}(((([1-9][0-9]{1,3})|([1-9]['
            + '0-9]{0,0})|0|([1-5][0-9]{4,4})|(6[0-4][0-9]{3,3})|(65[0-4][0-9]{'
            + '2,2})|(655[0-2][0-9]{1,1})|(6553[0-4])|65535)-(([1-9][0-9]{1,3})'
            + '|([1-9][0-9]{0,0})|0|([1-5][0-9]{4,4})|(6[0-4][0-9]{3,3})|(65[0-'
            + '4][0-9]{2,2})|(655[0-2][0-9]{1,1})|(6553[0-4])|65535))|(([1-9][0'
            + '-9]{1,3})|([1-9][0-9]{0,0})|0|([1-5][0-9]{4,4})|(6[0-4][0-9]{3,3'
            + '})|(65[0-4][0-9]{2,2})|(655[0-2][0-9]{1,1})|(6553[0-4])|65535)){'
            + '1,1})'
              {
        description 'Configure port in range mode, support single port value or'
                  + ' range(max num:4;spacing mark:,) in <0-65535>.'
                    ;
      }
    }
    description 'The definition of port in range mode, support single port valu'
              + 'e or range(max num:4;spacing mark:,) in <0-65535>. For example'
              + ',"1-300,400,450-500",etc.'
                ;
  }
  container configuration {
    description 'Configuration information'
                ;
    container qos {
      description 'Configuration about QoS'
                  ;
      container ipv4-vxlan-cars {
        description 'Configure VXLAN rate limit parameters'
                    ;
        list ipv4-vxlan-car {
          description 'Configure VXLAN item'
                      ;
          key 'vni-id src-addr dst-addr'
              ;
          leaf vni-id {
            description 'VNI ID'
                        ;
            type uint32 {
              range 1..16777215 {
                description 'VNI ID'
                            ;
              }
            }
          }
          leaf src-addr {
            description 'Source address of VXLAN tunnel'
                        ;
            type ncd:ipv4-address ;
          }
          leaf dst-addr {
            description 'Destination address of VXLAN tunnel'
                        ;
            type ncd:ipv4-address ;
          }
          container rate-limit {
            description 'Configure interface rate limit parameters'
                        ;
            container localports {
              description 'Match local port'
                          ;
              list localport {
                description 'Configure interface rate limit based on matching l'
                          + 'ocalport'
                            ;
                key if-direct ;
                leaf if-direct {
                  description 'Specify the direction of VXLAN, as follows,'+"\n"
                            + '     input  Rate limit on input'+"\n"
                            + '     output Rate limit on output'
                              ;
                  type enumeration {
                    enum input {
                      value 1 ;
                      description 'Rate limit on input'
                                  ;
                    }
                    enum output {
                      value 2 ;
                      description 'Rate limit on output'
                                  ;
                    }
                  }
                }
                leaf cir {
                  description 'Configure the CIR(Committed Information Rate) va'
                            + 'lue (default: kilobits per second)'
                              ;
                  type uint32 {
                    range 8..4294967295 {
                      description 'The CIR value (default: kilobits per second)'
                                + ',support <8-4294967295>'
                                  ;
                    }
                  }
                  mandatory true ;
                }
                leaf cbs {
                  description 'Configure the CBS(Committed Burst Size) size in '
                            + 'bytes'
                              ;
                  type uint32 {
                    range 1..4294967295 {
                      description 'The CBS(Committed Burst Size) size in bytes,'
                                + ' support <1-4294967295>'
                                  ;
                    }
                  }
                  units byte ;
                  mandatory true ;
                }
              }
            }
          }
        }
      }
      container vni-or-addr-vxlan-cars {
        // if-feature qos-vni-or-addr-vxlan-cars ;
        description 'Configure VXLAN rate limit parameters'
                    ;
        container vni-id-vxlan-cars {
          description 'Configure VXLAN item base on vni'
                      ;
          list vni-id-vxlan-car {
            description 'Configure VXLAN item'
                        ;
            key vni-id ;
            leaf vni-id {
              description 'VNI ID'
                          ;
              type uint32 {
                range 1..16777215 {
                  description 'VNI ID'
                              ;
                }
              }
            }
            container rate-limit {
              description 'Configure rate limit parameters'
                          ;
              container unknown-multicasts {
                description 'Match unknown-multicast'
                            ;
                list unknown-multicast {
                  description 'Configure interface rate limit based on matching'
                            + ' unknown-multicasts'
                              ;
                  key if-direct ;
                  leaf if-direct {
                    description 'Specify the direction of VXLAN, as follows,'+"\n"
                              + '     input  Rate limit on input'+"\n"
                              + '     output Rate limit on output'
                                ;
                    type enumeration {
                      enum input {
                        value 1 ;
                        description 'Rate limit on input'
                                    ;
                      }
                      enum output {
                        value 2 ;
                        description 'Rate limit on output'
                                    ;
                      }
                    }
                  }
                  leaf cir-value {
                    description 'Configure the CIR(Committed Information Rate) '
                              + 'value (default: kilobits per second)'
                                ;
                    type uint32 {
                      range 8..4294967295 {
                        description 'The CIR value (default: kilobits per secon'
                                  + 'd),support <8-4294967295>'
                                    ;
                      }
                    }
                    mandatory true ;
                  }
                  leaf cir-unit {
                    description 'Configure the unit of  CIR value, see below:'+"\n"
                              + '             kbps  (1) Kilobits per second'+"\n"
                              + '             mbps  (2) Megabits per second'+"\n"
                              + '             gbps  (3) Gigabits per second'+"\n"
                              + '             pps   (4) Packet   per second'
                                ;
                    type qos-rate-unit-type ;
                    default kbps ;
                  }
                  leaf cbs {
                    description 'Configure the CBS(Committed Burst Size) size i'
                              + 'n bytes'
                                ;
                    type uint32 {
                      range 1..4294967295 {
                        description 'The CBS(Committed Burst Size) size in byte'
                                  + 's, support <1-4294967295>'
                                    ;
                      }
                    }
                    units byte ;
                    mandatory true ;
                  }
                }
              }
              container broadcasts {
                description 'Match broadcast'
                            ;
                list broadcast {
                  description 'Configure interface rate limit based on matching'
                            + ' broadcasts'
                              ;
                  key if-direct ;
                  leaf if-direct {
                    description 'Specify the direction of VXLAN, as follows,'+"\n"
                              + '     input  Rate limit on input'+"\n"
                              + '     output Rate limit on output'
                                ;
                    type enumeration {
                      enum input {
                        value 1 ;
                        description 'Rate limit on input'
                                    ;
                      }
                      enum output {
                        value 2 ;
                        description 'Rate limit on output'
                                    ;
                      }
                    }
                  }
                  leaf cir-value {
                    description 'Configure the CIR(Committed Information Rate) '
                              + 'value (default: kilobits per second)'
                                ;
                    type uint32 {
                      range 8..4294967295 {
                        description 'The CIR value (default: kilobits per secon'
                                  + 'd),support <8-4294967295>'
                                    ;
                      }
                    }
                    mandatory true ;
                  }
                  leaf cir-unit {
                    description 'Configure the unit of  CIR value, see below:'+"\n"
                              + '             kbps  (1) Kilobits per second'+"\n"
                              + '             mbps  (2) Megabits per second'+"\n"
                              + '             gbps  (3) Gigabits per second'+"\n"
                              + '             pps   (4) Packet   per second'
                                ;
                    type qos-rate-unit-type ;
                    default kbps ;
                  }
                  leaf cbs {
                    description 'Configure the CBS(Committed Burst Size) size i'
                              + 'n bytes'
                                ;
                    type uint32 {
                      range 1..4294967295 {
                        description 'The CBS(Committed Burst Size) size in byte'
                                  + 's, support <1-4294967295>'
                                    ;
                      }
                    }
                    units byte ;
                  }
                }
              }
              container multicasts {
                description 'Match multicast'
                            ;
                list multicast {
                  description 'Configure interface rate limit based on matching'
                            + ' multicasts'
                              ;
                  key if-direct ;
                  leaf if-direct {
                    description 'Specify the direction of VXLAN, as follows,'+"\n"
                              + '     input  Rate limit on input'+"\n"
                              + '     output Rate limit on output'
                                ;
                    type enumeration {
                      enum input {
                        value 1 ;
                        description 'Rate limit on input'
                                    ;
                      }
                      enum output {
                        value 2 ;
                        description 'Rate limit on output'
                                    ;
                      }
                    }
                  }
                  leaf cir-value {
                    description 'Configure the CIR(Committed Information Rate) '
                              + 'value (default: kilobits per second)'
                                ;
                    type uint32 {
                      range 8..4294967295 {
                        description 'The CIR value (default: kilobits per secon'
                                  + 'd),support <8-4294967295>'
                                    ;
                      }
                    }
                    mandatory true ;
                  }
                  leaf cir-unit {
                    description 'Configure the unit of  CIR value, see below:'+"\n"
                              + '             kbps  (1) Kilobits per second'+"\n"
                              + '             mbps  (2) Megabits per second'+"\n"
                              + '             gbps  (3) Gigabits per second'+"\n"
                              + '             pps   (4) Packet   per second'
                                ;
                    type qos-rate-unit-type ;
                    default kbps ;
                  }
                  leaf cbs {
                    description 'Configure the CBS(Committed Burst Size) size i'
                              + 'n bytes'
                                ;
                    type uint32 {
                      range 1..4294967295 {
                        description 'The CBS(Committed Burst Size) size in byte'
                                  + 's, support <1-4294967295>'
                                    ;
                      }
                    }
                    units byte ;
                    mandatory true ;
                  }
                }
              }
              container unicasts {
                description 'Match unicast'
                            ;
                list unicast {
                  description 'Configure interface rate limit based on matching'
                            + ' unicasts'
                              ;
                  key if-direct ;
                  leaf if-direct {
                    description 'Specify the direction of VXLAN, as follows,'+"\n"
                              + '     input  Rate limit on input'+"\n"
                              + '     output Rate limit on output'
                                ;
                    type enumeration {
                      enum input {
                        value 1 ;
                        description 'Rate limit on input'
                                    ;
                      }
                      enum output {
                        value 2 ;
                        description 'Rate limit on output'
                                    ;
                      }
                    }
                  }
                  leaf cir-value {
                    description 'Configure the CIR(Committed Information Rate) '
                              + 'value (default: kilobits per second)'
                                ;
                    type uint32 {
                      range 8..4294967295 {
                        description 'The CIR value (default: kilobits per secon'
                                  + 'd),support <8-4294967295>'
                                    ;
                      }
                    }
                    mandatory true ;
                  }
                  leaf cir-unit {
                    description 'Configure the unit of  CIR value, see below:'+"\n"
                              + '             kbps  (1) Kilobits per second'+"\n"
                              + '             mbps  (2) Megabits per second'+"\n"
                              + '             gbps  (3) Gigabits per second'+"\n"
                              + '             pps   (4) Packet   per second'
                                ;
                    type qos-rate-unit-type ;
                    default kbps ;
                  }
                  leaf cbs {
                    description 'Configure the CBS(Committed Burst Size) size i'
                              + 'n bytes'
                                ;
                    type uint32 {
                      range 1..4294967295 {
                        description 'The CBS(Committed Burst Size) size in byte'
                                  + 's, support <1-4294967295>'
                                    ;
                      }
                    }
                    units byte ;
                    mandatory true ;
                  }
                }
              }
              container unknown-unicasts {
                description 'Match unknown-unicast'
                            ;
                list unknown-unicast {
                  description 'Configure interface rate limit based on matching'
                            + ' unknown-unicasts'
                              ;
                  key if-direct ;
                  leaf if-direct {
                    description 'Specify the direction of VXLAN, as follows,'+"\n"
                              + '     input  Rate limit on input'+"\n"
                              + '     output Rate limit on output'
                                ;
                    type enumeration {
                      enum input {
                        value 1 ;
                        description 'Rate limit on input'
                                    ;
                      }
                      enum output {
                        value 2 ;
                        description 'Rate limit on output'
                                    ;
                      }
                    }
                  }
                  leaf cir-value {
                    description 'Configure the CIR(Committed Information Rate) '
                              + 'value (default: kilobits per second)'
                                ;
                    type uint32 {
                      range 8..4294967295 {
                        description 'The CIR value (default: kilobits per secon'
                                  + 'd),support <8-4294967295>'
                                    ;
                      }
                    }
                    mandatory true ;
                  }
                  leaf cir-unit {
                    description 'Configure the unit of  CIR value, see below:'+"\n"
                              + '             kbps  (1) Kilobits per second'+"\n"
                              + '             mbps  (2) Megabits per second'+"\n"
                              + '             gbps  (3) Gigabits per second'+"\n"
                              + '             pps   (4) Packet   per second'
                                ;
                    type qos-rate-unit-type ;
                    default kbps ;
                  }
                  leaf cbs {
                    description 'Configure the CBS(Committed Burst Size) size i'
                              + 'n bytes'
                                ;
                    type uint32 {
                      range 1..4294967295 {
                        description 'The CBS(Committed Burst Size) size in byte'
                                  + 's, support <1-4294967295>'
                                    ;
                      }
                    }
                    units byte ;
                  }
                }
              }
            }
          }
        }
        container addr-vxlan-cars {
          description 'Configure VXLAN item base on IPv4 address'
                      ;
          list addr-vxlan-car {
            description 'Configure VXLAN item'
                        ;
            key 'src-addr dst-addr'
                ;
            leaf src-addr {
              description 'Source address of VXLAN tunnel'
                          ;
              type ncd:ipv4-address ;
            }
            leaf dst-addr {
              description 'Destination address of VXLAN tunnel'
                          ;
              type ncd:ipv4-address ;
            }
            container rate-limit {
              description 'Configure rate limit parameters'
                          ;
              container unknown-multicasts {
                description 'Match unknown-multicast'
                            ;
                list unknown-multicast {
                  description 'Configure interface rate limit based on matching'
                            + ' unknown-multicasts'
                              ;
                  key if-direct ;
                  leaf if-direct {
                    description 'Specify the direction of VXLAN, as follows,'+"\n"
                              + '     input  Rate limit on input'+"\n"
                              + '     output Rate limit on output'
                                ;
                    type enumeration {
                      enum input {
                        value 1 ;
                        description 'Rate limit on input'
                                    ;
                      }
                      enum output {
                        value 2 ;
                        description 'Rate limit on output'
                                    ;
                      }
                    }
                  }
                  leaf cir-value {
                    description 'Configure the CIR(Committed Information Rate) '
                              + 'value (default: kilobits per second)'
                                ;
                    type uint32 {
                      range 8..4294967295 {
                        description 'The CIR value (default: kilobits per secon'
                                  + 'd),support <8-4294967295>'
                                    ;
                      }
                    }
                    mandatory true ;
                  }
                  leaf cir-unit {
                    description 'Configure the unit of  CIR value, see below:'+"\n"
                              + '             kbps  (1) Kilobits per second'+"\n"
                              + '             mbps  (2) Megabits per second'+"\n"
                              + '             gbps  (3) Gigabits per second'+"\n"
                              + '             pps   (4) Packet   per second'
                                ;
                    type qos-rate-unit-type ;
                    default kbps ;
                  }
                  leaf cbs {
                    description 'Configure the CBS(Committed Burst Size) size i'
                              + 'n bytes'
                                ;
                    type uint32 {
                      range 1..4294967295 {
                        description 'The CBS(Committed Burst Size) size in byte'
                                  + 's, support <1-4294967295>'
                                    ;
                      }
                    }
                    units byte ;
                    mandatory true ;
                  }
                }
              }
              container broadcasts {
                description 'Match broadcast'
                            ;
                list broadcast {
                  description 'Configure interface rate limit based on matching'
                            + ' broadcasts'
                              ;
                  key if-direct ;
                  leaf if-direct {
                    description 'Specify the direction of VXLAN, as follows,'+"\n"
                              + '     input  Rate limit on input'+"\n"
                              + '     output Rate limit on output'
                                ;
                    type enumeration {
                      enum input {
                        value 1 ;
                        description 'Rate limit on input'
                                    ;
                      }
                      enum output {
                        value 2 ;
                        description 'Rate limit on output'
                                    ;
                      }
                    }
                  }
                  leaf cir-value {
                    description 'Configure the CIR(Committed Information Rate) '
                              + 'value (default: kilobits per second)'
                                ;
                    type uint32 {
                      range 8..4294967295 {
                        description 'The CIR value (default: kilobits per secon'
                                  + 'd),support <8-4294967295>'
                                    ;
                      }
                    }
                    mandatory true ;
                  }
                  leaf cir-unit {
                    description 'Configure the unit of  CIR value, see below:'+"\n"
                              + '             kbps  (1) Kilobits per second'+"\n"
                              + '             mbps  (2) Megabits per second'+"\n"
                              + '             gbps  (3) Gigabits per second'+"\n"
                              + '             pps   (4) Packet   per second'
                                ;
                    type qos-rate-unit-type ;
                    default kbps ;
                  }
                  leaf cbs {
                    description 'Configure the CBS(Committed Burst Size) size i'
                              + 'n bytes'
                                ;
                    type uint32 {
                      range 1..4294967295 {
                        description 'The CBS(Committed Burst Size) size in byte'
                                  + 's, support <1-4294967295>'
                                    ;
                      }
                    }
                    units byte ;
                    mandatory true ;
                  }
                }
              }
              container multicasts {
                description 'Match multicast'
                            ;
                list multicast {
                  description 'Configure interface rate limit based on matching'
                            + ' multicasts'
                              ;
                  key if-direct ;
                  leaf if-direct {
                    description 'Specify the direction of VXLAN, as follows,'+"\n"
                              + '     input  Rate limit on input'+"\n"
                              + '     output Rate limit on output'
                                ;
                    type enumeration {
                      enum input {
                        value 1 ;
                        description 'Rate limit on input'
                                    ;
                      }
                      enum output {
                        value 2 ;
                        description 'Rate limit on output'
                                    ;
                      }
                    }
                  }
                  leaf cir-value {
                    description 'Configure the CIR(Committed Information Rate) '
                              + 'value (default: kilobits per second)'
                                ;
                    type uint32 {
                      range 8..4294967295 {
                        description 'The CIR value (default: kilobits per secon'
                                  + 'd),support <8-4294967295>'
                                    ;
                      }
                    }
                    mandatory true ;
                  }
                  leaf cir-unit {
                    description 'Configure the unit of  CIR value, see below:'+"\n"
                              + '             kbps  (1) Kilobits per second'+"\n"
                              + '             mbps  (2) Megabits per second'+"\n"
                              + '             gbps  (3) Gigabits per second'+"\n"
                              + '             pps   (4) Packet   per second'
                                ;
                    type qos-rate-unit-type ;
                    default kbps ;
                  }
                  leaf cbs {
                    description 'Configure the CBS(Committed Burst Size) size i'
                              + 'n bytes'
                                ;
                    type uint32 {
                      range 1..4294967295 {
                        description 'The CBS(Committed Burst Size) size in byte'
                                  + 's, support <1-4294967295>'
                                    ;
                      }
                    }
                    units byte ;
                    mandatory true ;
                  }
                }
              }
              container unicasts {
                description 'Match unicast'
                            ;
                list unicast {
                  description 'Configure interface rate limit based on matching'
                            + ' unicasts'
                              ;
                  key if-direct ;
                  leaf if-direct {
                    description 'Specify the direction of VXLAN, as follows,'+"\n"
                              + '     input  Rate limit on input'+"\n"
                              + '     output Rate limit on output'
                                ;
                    type enumeration {
                      enum input {
                        value 1 ;
                        description 'Rate limit on input'
                                    ;
                      }
                      enum output {
                        value 2 ;
                        description 'Rate limit on output'
                                    ;
                      }
                    }
                  }
                  leaf cir-value {
                    description 'Configure the CIR(Committed Information Rate) '
                              + 'value (default: kilobits per second)'
                                ;
                    type uint32 {
                      range 8..4294967295 {
                        description 'The CIR value (default: kilobits per secon'
                                  + 'd),support <8-4294967295>'
                                    ;
                      }
                    }
                    mandatory true ;
                  }
                  leaf cir-unit {
                    description 'Configure the unit of  CIR value, see below:'+"\n"
                              + '             kbps  (1) Kilobits per second'+"\n"
                              + '             mbps  (2) Megabits per second'+"\n"
                              + '             gbps  (3) Gigabits per second'+"\n"
                              + '             pps   (4) Packet   per second'
                                ;
                    type qos-rate-unit-type ;
                    default kbps ;
                  }
                  leaf cbs {
                    description 'Configure the CBS(Committed Burst Size) size i'
                              + 'n bytes'
                                ;
                    type uint32 {
                      range 1..4294967295 {
                        description 'The CBS(Committed Burst Size) size in byte'
                                  + 's, support <1-4294967295>'
                                    ;
                      }
                    }
                    units byte ;
                    mandatory true ;
                  }
                }
              }
              container unknown-unicasts {
                description 'Match unknown-unicast'
                            ;
                list unknown-unicast {
                  description 'Configure interface rate limit based on matching'
                            + ' unknown-unicasts'
                              ;
                  key if-direct ;
                  leaf if-direct {
                    description 'Specify the direction of VXLAN, as follows,'+"\n"
                              + '     input  Rate limit on input'+"\n"
                              + '     output Rate limit on output'
                                ;
                    type enumeration {
                      enum input {
                        value 1 ;
                        description 'Rate limit on input'
                                    ;
                      }
                      enum output {
                        value 2 ;
                        description 'Rate limit on output'
                                    ;
                      }
                    }
                  }
                  leaf cir-value {
                    description 'Configure the CIR(Committed Information Rate) '
                              + 'value (default: kilobits per second)'
                                ;
                    type uint32 {
                      range 8..4294967295 {
                        description 'The CIR value (default: kilobits per secon'
                                  + 'd),support <8-4294967295>'
                                    ;
                      }
                    }
                    mandatory true ;
                  }
                  leaf cir-unit {
                    description 'Configure the unit of  CIR value, see below:'+"\n"
                              + '             kbps  (1) Kilobits per second'+"\n"
                              + '             mbps  (2) Megabits per second'+"\n"
                              + '             gbps  (3) Gigabits per second'+"\n"
                              + '             pps   (4) Packet   per second'
                                ;
                    type qos-rate-unit-type ;
                    default kbps ;
                  }
                  leaf cbs {
                    description 'Configure the CBS(Committed Burst Size) size i'
                              + 'n bytes'
                                ;
                    type uint32 {
                      range 1..4294967295 {
                        description 'The CBS(Committed Burst Size) size in byte'
                                  + 's, support <1-4294967295>'
                                    ;
                      }
                    }
                    units byte ;
                    mandatory true ;
                  }
                }
              }
            }
          }
        }
        ncd:revise-date 2021-01-28 ;
      }
    }
  }
}
