module zxr10-mac {
  namespace 'http://www.zte.com.cn/zxr10/netconf/schema/rosng/mac'
            ;
  prefix mac ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe MAC.'
              ;
  revision 2021-04-06 {
    description '1.Add a leaf: /configuration/mac/vpls-port-config/mac-vfi-port'
              + '-config/learn-enable.'
                ;
  }
  revision 2020-12-15 {
    description '1.Add /configuration/mac/permanent-mac-address/mac-permanent-m'
              + 'ac-address-vpn-vlan/permanent-mac-address-vpn-vlan/mac-type/pe'
              + 'rmanent/interface/iforvlanif/esi.'+"\n"
              + '2.Add /configuration/mac/permanent-mac-address/mac-permanent-m'
              + 'ac-address-no-vlan/permanent-mac-address-no-vlan/mac-type/perm'
              + 'anent/interface/iforvlanif/esi.'+"\n"
              + '3.Modified /configuration/mac/permanent-mac-address/mac-perman'
              + 'ent-mac-address-vpn-vlan/permanent-mac-address-vpn-vlan/mac-ty'
              + 'pe/permanent/interface/iforvlanif. Add mimactions.'+"\n"
              + '4.Modified /configuration/mac/permanent-mac-address/mac-perman'
              + 'ent-mac-address-no-vlan/permanent-mac-address-no-vlan/mac-type'
              + '/permanent/interface/iforvlanif. Add mimactions.'
                ;
  }
  revision 2020-11-24 {
    description '1.Modify /mac:configuration/mac:mac/mac:vpls-instance-config/m'
              + 'ac:vpls-config/mac:mac-moving/mac:suppressible. Add a performa'
              + 'nce parameter to control the suppressible.'
                ;
  }
  revision 2020-02-25 {
    description '1.Add a leaf /mac:state/mac:mac/mac:mac-vpls-tables/mac:mac-vp'
              + 'ls-table/mac:sid'
                ;
  }
  revision 2020-02-21 {
    description '1.Add /configuration/mac/permanent-mac-address/mac-permanent-m'
              + 'ac-address-vpn-vlan/permanent-mac-address-vpn-vlan/mac-type/pe'
              + 'rmanent/interface/iforvlanif/vxlan-tunnel.'
                ;
  }
  revision 2020-02-06 {
    description '1.Add /configuration/mac/vpls-instance-config/vpls-config/mac-'
              + 'age.'+"\n"
              + '2.Add /configuration/mac/vpls-instance-config/vpls-config/mac-'
              + 'age/aging-time-local. '+"\n"
              + '3.Add /configuration/mac/vpls-instance-config/vpls-config/mac-'
              + 'age/aging-time-remote.'
                ;
  }
  revision 2020-01-20 {
    description '1.Modify /mac:configuration/mac:mac/mac:vpls-pw-config/mac:mac'
              + '-vfi-pw-config/mac:traffic-rate-limit/mac:traffic-maximum. Add'
              + ' a performance parameter to control the max-rate.'
                ;
  }
  revision 2019-10-22 {
    description '1.Add a container /mac:configuration/mac:mac/mac:vpls-port-con'
              + 'fig/mac:mac-vfi-port-config/mac:black-hole-mac-max-count.'
                ;
  }
  revision 2019-09-29 {
    description '1.Add a container /configuration/mac/vpls-instance-config/vpls'
              + '-config/mac-moving/black-hole for evpn.'
                ;
  }
  revision 2019-08-01 {
    description '1.Add a container /configuration/mac/vpls-static-vxlan-tunnel-'
              + 'config'
                ;
  }
  revision 2018-06-20 {
    description '1.Add /configuration/mac/permanent-mac-address/mac-permanent-m'
              + 'ac-address-no-vlan/permanent-mac-address-no-vlan/mac-type/perm'
              + 'anent/interface/iforvlanif/vxlan-tunnel'
                ;
  }
  revision 2018-05-24 {
    description '1.modify /mac:configuration/mac:mac/mac:vpls-instance-config/m'
              + 'ac:vpls-config/mac:mac-entries'+"\n"
              + '2.Add state/mac/global-status/vpls-evpn-mac-count.'
                ;
  }
  revision 2018-03-15 {
    description '1.Add /mac:state/mac:mac/mac:mac-vpls-tables/mac:mac-vpls-tabl'
              + 'e/mac:esi'
                ;
  }
  revision 2018-01-23 {
    description '1.Add configuration/mac/vpls-instance-config/vpls-config/mac-l'
              + 'earning/learn for evpn.'+"\n"
              + '2.Add configuration/mac/vpls-instance-config/vpls-config/mac-l'
              + 'earning/evpn-remote-mac-receiving for evpn.'+"\n"
              + '3.Add configuration/mac/vpls-instance-config/vpls-config/mac-l'
              + 'earning/evpn-local-mac-advertising for evpn.'
                ;
  }
  revision 2017-12-12 {
    description '1.Add configuration/mac/vpls-instance-config/vpls-config/mac-m'
              + 'oving-count for vpls and evpn.'+"\n"
              + '2.Configuration/mac/vpls-instance-config/vpls-config/mac-movin'
              + 'g/suppressible,auto-recovery-time and sampling-period are defi'
              + 'ned by performance parameter.'+"\n"
              + '3.Modify description of configuration/mac/vpls-instance-config'
              + '/vpls-config/mac-moving/suppressible,auto-recovery-time and sa'
              + 'mpling-period.'+"\n"
              + '4.Modefy vpls evpn to support configuration/mac/vpls-instance-'
              + 'config/vpls-config/mac-moving/suppressible,auto-recovery-time '
              + 'and sampling-period.'
                ;
  }
  revision 2017-11-15 {
    description '1.Obsolete state/mac/mac-vxlan-tables-expand ;'+"\n"
              + '2.Obsolete configuration/mac/permanent-mac-address/mac-permane'
              + 'nt-vxlan-mac-address-no-vlan ;'+"\n"
              + '3.Obsolete operation/mac/delete-vxlan-no-config-mac .'
                ;
  }
  revision 2017-09-20 {
    description '1.Add the leaf of l2bfd leaf in configuration/mac/vpls-instanc'
              + 'e-config/vpls-config/l2protocol-control-policy-expand.'
                ;
  }
  revision 2017-08-21 {
    description '1.Add /mac:state/mac:mac/mac:mac-vxlan-tables-expand/mac:mac-v'
              + 'xlan-table/mac:esi'
                ;
  }
  revision 2017-07-11 {
    description '1.Add the /mac:state/mac:mac/mac:mac-vpls-tables/mac:mac-vpls-'
              + 'table/mac:out-label.'+"\n"
              + '2.Add the /mac:state/mac:mac/mac:mac-vpls-tables/mac:mac-vpls-'
              + 'table/mac:next-hop.'
                ;
  }
  revision 2016-10-08 {
    description '1.Delete the user-protocol-name node which in configuration/ma'
              + 'c/vpls-instance-config/vpls-config/l2protocol-control-policy.
'
              + ''+"\n"
              + '2.Add the user-protocol-template container in configuration/ma'
              + 'c/vpls-instance-config/vpls-config/l2protocol-control-policy.'
                ;
  }
  revision 2016-08-11 {
    description '1.Add the /mac:state/mac:mac/mac:mac-vxlan-tables-expand/mac:m'
              + 'ac-vxlan-table/mac:internal-vlan-id.'+"\n"
              + '2.Add the /mac:state/mac:mac/mac:mac-vxlan-tables-expand/mac:m'
              + 'ac-vxlan-table/mac:external-vlan-id.'+"\n"
              + '3.Modify /mac:configuration/mac:mac/mac:permanent-mac-address/'
              + 'mac:mac-permanent-vxlan-mac-address-no-vlan.'+"\n"
              + '4.Obsolete /mac:configuration/mac:mac/mac:permanent-mac-addres'
              + 's/mac:mac-permanent-vxlan-mac-address-vlan.'+"\n"
              + '5.Obsolete /mac:operation/mac:mac/mac:delete-vxlan-no-config-m'
              + 'ac/mac:vlan-id.'+"\n"
              + '6.Change value of /mac:state/mac:mac/mac:mac-vxlan-tables-expa'
              + 'nd/mac:mac-vxlan-table/mac:vlan-id to zero.'
                ;
  }
  revision 2016-06-23 {
    description '1.Add the evpn-tunnel-id leaf node in state/mac/mac-vpls-table'
              + 's/mac-vpls-table.'+"\n"
              + '2.Add the vni leaf node in state/mac/mac-vpls-tables/mac-vpls-'
              + 'table.'
                ;
  }
  revision 2016-06-07 {
    description '1.Add /mac:configuration/mac:mac/mac:port-config/mac:mac-port-'
              + 'config/mac:dampening-policy, /mac:configuration/mac:mac/mac:po'
              + 'rt-config/mac:mac-port-config/mac:dampening-timeout'+"\n"
              + '2.Add /operation/mac/learn-priority-policies'
                ;
  }
  revision 2016-05-18 {
    description '1.Add value enable-no-alarm for /mac:configuration/mac:mac/mac'
              + ':global-config/mac:safe-mode-policy;'+"\n"
              + '2.Add value enable-shutdown for /mac:configuration/mac:mac/mac'
              + ':global-config/mac:safe-mode-policy;'+"\n"
              + '3.Add value enable-no-alarm for /mac:configuration/mac:mac/mac'
              + ':port-config/mac:mac-port-config/mac:safe-mode-policy;'+"\n"
              + '4.Add value enable-shutdown for /mac:configuration/mac:mac/mac'
              + ':port-config/mac:mac-port-config/mac:safe-mode-policy;'+"\n"
              + '5.Change discription of value enable-block for /mac:configurat'
              + 'ion/mac:mac/mac:port-config/mac:mac-port-config/mac:safe-mode-'
              + 'policy.'
                ;
  }
  revision 2016-02-23 {
    description '1.Add value shutdown for /mac:configuration/mac:mac/mac:port-c'
              + 'onfig/mac:mac-port-config/mac:exceed-limit-action.'
                ;
  }
  revision 2016-01-28 {
    description '1.Obsolete state/mac/mac-vxlan-tables.'+"\n"
              + '2.Obsolete configuration/mac/permanent-mac-address/mac-permane'
              + 'nt-vxlan-mac-address.'+"\n"
              + '3.Add state/mac/vxlan-tables-expand.'+"\n"
              + '4.Add configuration/mac/permanent-mac-address/mac-permanent-vx'
              + 'lan-mac-address-no-vlan.'+"\n"
              + '5.Add configuration/mac/permanent-mac-address/mac-permanent-vx'
              + 'lan-mac-address-vlan.'
                ;
  }
  revision 2016-01-15 {
    description '1.Add the terminated enumeration for all-bridge-multicast,cdp,'
              + 'cfm,dldp,dot1x,efm,garp,gmrp,gvrp,pvst+,udld,zdp-ztp,vtp,zesr '
              + 'leafs which in configuration/mac/vpls-instance-config/vpls-con'
              + 'fig/l2protocol-control-policy-expand;'+"\n"
              + '2.Add the leafs of dot3x and erps leafs in configuration/mac/v'
              + 'pls-instance-config/vpls-config/l2protocol-control-policy-expa'
              + 'nd.'
                ;
  }
  revision 2015-12-01 {
    description '1.Add IPv6 case for zxr10-mac/state/mac/mac-vxlan-tables/mac-v'
              + 'xlan-table/remote-ip.'+"\n"
              + '2.Add IPv6 case for zxr10-mac/configuration/mac/permanent-mac-'
              + 'address/mac-permanent-vxlan-mac-address/permanent-vxlan-mac-ad'
              + 'dress/remote-ip.'
                ;
  }
  revision 2015-11-09 {
    description '1.Add the l2protocol-control-policy-expand container in config'
              + 'uration/mac/vpls-instance-config/vpls-config.'+"\n"
              + '2.Obsolete the l2protocol-control-policy container which in co'
              + 'nfiguration/mac/vpls-instance-config/vpls-config.'
                ;
  }
  revision 2015-08-24 {
    description '1.Delete the remote-ip leaf in state/mac/mac-vxlan-tables/mac-'
              + 'vxlan-table.'+"\n"
              + '2.Delete the remote-ip leaf in configuration/mac/permanent-mac'
              + '-address/mac-permanent-vxlan-mac-address.'+"\n"
              + '3.Add the remote-ip choice node in state/mac/mac-vxlan-tables/'
              + 'mac-vxlan-table.'+"\n"
              + '4.Add the remote-ip choice node in configuration/mac/permanent'
              + '-mac-address/mac-permanent-vxlan-mac-address.'
                ;
  }
  revision 2015-07-15 {
    description '1.Add the garp,gmrp,dldp leafs in configuration/mac/vpls-insta'
              + 'nce-config/l2protocol-control-policy.'
                ;
  }
  revision 2015-07-10 {
    description '1.Change vlan-id of mac-vpls-table type from word32 to word16.'
              + ''+"\n"
              + '2.Change vlan-id of mac-table type from word32 to word16,value'
              + ' from 0-4094 to 1-4094.'
                ;
  }
  revision 2015-02-28 {
    description '1.Add the leaf of user-protocol-name in configuration/vpls-ins'
              + 'tance-config/l2protocol-control-policy.'
                ;
  }
  revision 2015-02-11 {
    description '1.Delete default value of traffic-maximum.'+"\n"
              + '2.Modify description.'
                ;
  }
  revision 2015-01-28 {
    description '1.Add the leafs of pvst-plus,udld,mstp,rstp,gvrp,pbb-te,mac-in'
              + '-mac,efm,cfm,y1731 in configuration/vpls-instance-config/l2pro'
              + 'tocol-control-policy.'
                ;
  }
  revision 2015-01-08 {
    description '1.Modify description.'+"\n"
              + '2.Add unint if need.'+"\n"
              + '3.Add range of interface name.'+"\n"
              + '4.Add default value of count of mac-count-tables.'
                ;
  }
  revision 2014-12-22 {
    description '1.Modify description.Change vlan to VLAN.Change mac to MAC.Cha'
              + 'nge vpls to VPLS.'+"\n"
              + '2.Add some description and unit.'
                ;
  }
  revision 2014-11-22 {
    description '1.Add a container mac-vxlan-tables on zxr10-mac/state/mac.'+"\n"
              + '2.Add a container mac-permanent-vxlan-mac-address on zxr10-mac'
              + '/configuration/mac/permanent-mac-address.'+"\n"
              + '3.Add a container delete-vxlan-macs on zxr10-mac/operation/mac'
              + '.'
                ;
  }
  revision 2014-11-11 {
    description '1.Add the container of unknown-multicast-traffic in configurat'
              + 'ion/mac/vpls-pw-config/traffic-rate-limit.'
                ;
  }
  revision 2014-08-21 {
    description '1.Add a leaf mac-count on zxr10-mac/state/mac/vpls-states/vpls'
              + '-state list.'+"\n"
              + '2.Add a container mac-count-tables on zxr10-mac/state/mac.'
                ;
  }
  revision 2014-05-16 {
    description 'Change "_" to "-".'+"\n"
              + 'Change range of nickname of state to 1-65471.'+"\n"
              + 'Change if-filter-id of delete-vpls-dynamc-mac to 335.'+"\n"
              + 'Change if-filter-id of mac-vfi-port-config to 331.'+"\n"
              + 'Change if-filter-id of vpls-port-states to 331.'
                ;
  }
  revision 2014-03-06 {
    description 'Add normal MAC NETCONFIG model.Add if filter.Delete default vp'
              + 'ls.Add performance parameter.Add features.Change vlanid of del'
              + 'ete-dynamic-mac from uint32 to uint16.'+"\n"
              + 'Add range of aging-time coniguration.'+"\n"
              + 'Change value range of sampling-period of mac-learning.Change m'
              + 'iminfo of max-mac-num of mac-port-config.'+"\n"
              + 'Change permanent MAC model.Add choice of permanent MAC type.Ad'
              + 'd choice of permanent MAC ifname.'+"\n"
              + 'Add default value of default-priority-movable and forbidden-ma'
              + 'c-reaction.'+"\n"
              + 'delete max-mac-num-action of port-config and vlan-config.'+"\n"
              + 'Add exceed-limit-action of vlan-config.'+"\n"
              + 'Modify enum value of exceed-limit-action and learn-disable-act'
              + 'ion'+"\n"
              + 'Add default value of safe-mode-policy and learn-disable-action'
              + '.'+"\n"
              + 'Change leaf not-learn of vpls-config to learn and modify descr'
              + 'iption.'+"\n"
              + 'Modify description of auto-recovery-time,move-dampening,anti-m'
              + 'ove.'+"\n"
              + 'Delete value 1 of anti-move.'+"\n"
              + 'Delete leaf garp and dot3x.'+"\n"
              + 'Delete leaf maximum-entries and maximum-action.'+"\n"
              + 'Add container mac-entries.'+"\n"
              + 'Change leaf stp-snooping and zesr-snooping to choice.'+"\n"
              + 'Delete container traffic-rate of vpls-port-config and add cont'
              + 'ainer vpls-pw-config.'+"\n"
              + 'Modify container interface of permanent-mac-address-no-vpn to '
              + 'outgoing, and iforvlanif to ifornickname.'+"\n"
              + 'Modify container Modify container all-vpls-instance-mac-summar'
              + 'y to global status.'+"\n"
              + 'Modify leaf ac-mac-count,pw-mac-count,filter-mac-count to vpls'
              + '-ac-mac-count,vpls-pw-mac-count,vpls-filter-mac-count.'+"\n"
              + 'Remove all leaf instance-type.'+"\n"
              + 'Modify if-filter-id of vpls to 331.'+"\n"
              + 'Modify if-filter-id of mac-vpls-table state to 335.'+"\n"
              + 'Add deviation .'+"\n"
              + 'Add container if only list.'+"\n"
              + 'Change name if name of container is same to list.'
                ;
  }
  revision 2013-11-18 {
    description 'Change if name lenth from 1-31 to 0-31.Change model of stp and'
              + ' zesr.Change permanent mac type from uint8 to mac.'
                ;
  }
  revision 2013-11-05 {
    description 'Change or add some discription.Change permanent MAC model.Chan'
              + 'ge default if name to NULL.'
                ;
  }
  revision 2013-07-18 {
    description 'Initial version.'
                ;
    reference ''
              ;
  }
  container state {
    description 'MAC state info.'
                ;
    config false ;
    container mac {
      description 'MAC state info.'
                  ;
      container mac-vpls-tables {
        description 'MAC table of VPLS instance.'
                    ;
        list mac-vpls-table {
          description 'MAC table of VPLS instance.'
                      ;
          key 'instance-name vlan-id mac-address'
              ;
          ncd:select instance-name ;
          ncd:select vlan-id ;
          ncd:select mac-address ;
          ncd:select if-name ;
          ncd:select multiflag ;
          ncd:select 'instance-name vlan-id mac-address'
                     ;
          leaf instance-name {
            description 'VPLS instance name.'
                        ;
            type string {
              length 1..32 {
                description 'The length of VPLS instance name.'
                            ;
              }
            }
          }
          leaf vlan-id {
            description 'VLAN ID.0 means VLAN is invalid.'
                        ;
            type uint16 {
              range 0..4094 {
                description 'VLAN ID must be in this range.'
                            ;
              }
            }
          }
          leaf mac-address {
            description 'MAC address.'
                        ;
            type ncd:mac-address ;
          }
          leaf if-name {
            description 'Interface name.'
                        ;
            type ncd:ifname {
              length 1..31 {
                description 'The length of interface name.'
                            ;
              }
            }
          }
          leaf multiflag {
            description 'The type of MAC address.'
                        ;
            type enumeration {
              enum dynamic {
                value 1 ;
                description 'Dynamic MAC address.'
                            ;
              }
              enum static {
                value 2 ;
                description 'Static MAC address.'
                            ;
              }
              enum permanent {
                value 3 ;
                description 'Permanent MAC address.'
                            ;
              }
              enum source-filter {
                value 4 ;
                description 'Source-filter MAC address.'
                            ;
              }
              enum dst-filter {
                value 5 ;
                description 'Destination-filter MAC address.'
                            ;
              }
              enum both-filter {
                value 6 ;
                description 'Both-filter MAC address.'
                            ;
              }
              enum to-static {
                value 7 ;
                description 'To-static MAC address.'
                            ;
              }
              enum to-permanent {
                value 8 ;
                description 'To-permanent MAC address.'
                            ;
              }
            }
          }
          leaf evpn-tunnel-id {
            description 'EVPN tunnel ID.'
                        ;
            type uint32 ;
          }
          leaf vni {
            description VNI. ;
            type uint32 {
              range 1..16777215 ;
            }
          }
          leaf out-label {
            description 'MPLS EVPN out-label.'
                        ;
            type uint32 ;
          }
          leaf sid {
            description 'SRV6 EVPN SID.'
                        ;
            type ncd:ipv6-address ;
          }
          container next-hop {
            description 'Nexthop IP address.'
                        ;
            choice next-hop-ip {
              description 'Nexthop IP address.'
                          ;
              case ipv4 {
                description 'IPv4 address.'
                            ;
                leaf ipv4-address {
                  description 'Nexthop IPv4 address.'
                              ;
                  type ncd:ipv4-address ;
                }
              }
              case ipv6 {
                description 'IPv6 address.'
                            ;
                leaf ipv6-address {
                  description 'Nexthop IPv6 address.'
                              ;
                  type ncd:ipv6-address ;
                }
              }
            }
          }
          leaf esi {
            description 'ESI of MAC address.'
                        ;
            type string {
              length 1..51 {
                description 'The length of ESI.'
                            ;
              }
            }
          }
        }
      }
      container mac-tables {
        description 'MAC table.'
                    ;
        list mac-table {
          description 'MAC table.'
                      ;
          key 'vlan-id mac-address'
              ;
          ncd:select vlan-id ;
          ncd:select mac-address ;
          ncd:select multiflag ;
          ncd:select if-name ;
          ncd:select nickname ;
          ncd:select 'vlan-id mac-address'
                     ;
          leaf vlan-id {
            description 'VLAN ID.'
                        ;
            type uint16 {
              range 1..4094 {
                description 'VLAN ID must be in this range.'
                            ;
              }
            }
          }
          leaf mac-address {
            description 'MAC address.'
                        ;
            type ncd:mac-address ;
          }
          leaf if-name {
            description 'Interface name.'
                        ;
            type ncd:ifname {
              length 1..31 {
                description 'The length of interface name.'
                            ;
              }
            }
          }
          leaf multiflag {
            description 'The type of MAC address.'
                        ;
            type enumeration {
              enum dynamic {
                value 1 ;
                description 'Dynamic MAC address.'
                            ;
              }
              enum static {
                value 2 ;
                description 'Static MAC address.'
                            ;
              }
              enum permanent {
                value 3 ;
                description 'Permanent MAC address.'
                            ;
              }
              enum source-filter {
                value 4 ;
                description 'Source-filter MAC address.'
                            ;
              }
              enum dst-filter {
                value 5 ;
                description 'Destination-filter MAC address.'
                            ;
              }
              enum both-filter {
                value 6 ;
                description 'Both-filter MAC address.'
                            ;
              }
              enum to-static {
                value 7 ;
                description 'To-static MAC address.'
                            ;
              }
              enum to-permanent {
                value 8 ;
                description 'To-permanent MAC address.'
                            ;
              }
            }
          }
          leaf nickname {
            description 'Nickname of TRILL MAC.'
                        ;
            type uint16 {
              range 1..65471 {
                description 'Nickname must be in this range.'
                            ;
              }
            }
          }
        }
      }
      container vpls-port-states {
        description 'State of VPLS interface.'
                    ;
        list vpls-port-state {
          description 'State of VPLS interface.'
                      ;
          key 'instance-name if-name'
              ;
          ncd:select 'instance-name if-name'
                     ;
          leaf instance-name {
            description 'VPLS instance name.'
                        ;
            type string {
              length 1..32 {
                description 'The length of VPLS instance name.'
                            ;
              }
            }
          }
          leaf if-name {
            description 'Interface name.'
                        ;
            type ncd:ifname {
              length 1..31 {
                description 'The length of interface name.'
                            ;
              }
            }
          }
          leaf forward-state {
            description 'The forwarding state of interface.'
                        ;
            type enumeration {
              enum forwarding {
                value 0 ;
                description 'Forward state.'
                            ;
              }
              enum block {
                value 1 ;
                description 'Block state.'
                            ;
              }
            }
            default forwarding ;
          }
          leaf recovery-time {
            description 'Recovery time of blocked interface.'
                        ;
            type uint32 ;
            units second ;
            default 0 ;
          }
        }
      }
      container vpls-states {
        description 'State of VPLS instance.'
                    ;
        list vpls-state {
          description 'State of VPLS instance.'
                      ;
          key instance-name ;
          leaf instance-name {
            description 'VPLS instance name.'
                        ;
            type string {
              length 1..32 {
                description 'The length of VPLS instance name.'
                            ;
              }
            }
          }
          leaf forward-state {
            description 'The forwarding state of VPLS instance.'
                        ;
            type enumeration {
              enum forward {
                value 0 ;
                description 'Forward state.'
                            ;
              }
              enum block {
                value 1 ;
                description 'Block state.'
                            ;
              }
            }
            default forward ;
          }
          leaf mac-count {
            description 'Count of current VPLS MAC.'
                        ;
            type uint32 ;
            default 0 ;
          }
        }
      }
      container global-status {
        description 'Global status.'
                    ;
        leaf vpls-mac-count {
          description 'Count of VPLS MAC.'
                      ;
          type uint32 ;
          default 0 ;
        }
        leaf vpls-ac-mac-count {
          description 'Count of VPLS AC MAC.'
                      ;
          type uint32 ;
          default 0 ;
        }
        leaf vpls-pw-mac-count {
          description 'Count of VPLS PW MAC.'
                      ;
          type uint32 ;
          default 0 ;
        }
        leaf vpls-evpn-mac-count {
          description 'Count of EVPN MAC.'
                      ;
          type uint32 ;
          default 0 ;
        }
        leaf vpls-filter-mac-count {
          description 'Count of VPLS filter MAC.'
                      ;
          type uint32 ;
          default 0 ;
        }
        leaf is-protected {
          description 'Whether the global MAC count overruns the limit.'
                      ;
          type enumeration {
            enum not-overrun {
              value 1 ;
              description 'Global MAC count does not overrun the limit.'
                          ;
            }
            enum overrun {
              value 2 ;
              description 'Global MAC count overruns the limit.'
                          ;
            }
          }
          default not-overrun ;
        }
        leaf history-max-num {
          description 'Maximum MAC count in history.'
                      ;
          type uint32 ;
          default 0 ;
        }
      }
      container mac-count-tables {
        description 'MAC count table.'
                    ;
        list mac-count-table {
          description 'MAC count table.'
                      ;
          key multiflag ;
          ncd:select vlan-id ;
          ncd:select mac-address ;
          ncd:select if-name ;
          ncd:select multiflag ;
          ncd:select nickname ;
          ncd:select 'vlan-id mac-address'
                     ;
          ncd:select 'vlan-id if-name'
                     ;
          leaf multiflag {
            description 'The type of MAC address.'
                        ;
            type enumeration {
              enum dynamic {
                value 1 ;
                description 'Dynamic MAC address.'
                            ;
              }
              enum static {
                value 2 ;
                description 'Static MAC address.'
                            ;
              }
              enum permanent {
                value 3 ;
                description 'Permanent MAC address.'
                            ;
              }
              enum source-filter {
                value 4 ;
                description 'Source-filter MAC address.'
                            ;
              }
              enum dst-filter {
                value 5 ;
                description 'Destination-filter MAC address.'
                            ;
              }
              enum both-filter {
                value 6 ;
                description 'Both-filter MAC address.'
                            ;
              }
              enum to-static {
                value 7 ;
                description 'To-static MAC address.'
                            ;
              }
              enum to-permanent {
                value 8 ;
                description 'To-permanent MAC address.'
                            ;
              }
              enum all {
                value 9 ;
                description 'All type.'
                            ;
              }
            }
          }
          leaf vlan-id {
            description 'VLAN ID.'
                        ;
            type uint16 {
              range 1..4094 {
                description 'VLAN ID must be in this range.'
                            ;
              }
            }
          }
          leaf mac-address {
            description 'MAC address.'
                        ;
            type ncd:mac-address ;
          }
          leaf if-name {
            description 'Interface name.'
                        ;
            type ncd:ifname {
              length 1..31 {
                description 'The length of interface name.'
                            ;
              }
            }
          }
          leaf nickname {
            description 'Nickname of TRILL MAC.'
                        ;
            type uint16 {
              range 1..65471 {
                description 'Nickname must be in this range.'
                            ;
              }
            }
          }
          leaf count {
            description 'MAC count.'
                        ;
            type uint32 ;
            default 0 ;
          }
        }
      }
      container mac-vxlan-tables-expand {
        description 'VXLAN MAC table.'
                    ;
        status obsolete ;
        list mac-vxlan-table {
          description 'VXLAN MAC table.'
                      ;
          key 'vlan-id mac-address vxlan-id'
              ;
          ncd:select vxlan-id ;
          ncd:select 'vlan-id mac-address vxlan-id'
                     ;
          leaf vlan-id {
            description 'VLAN ID.0 means VLAN is invalid.'
                        ;
            type uint16 {
              range 0 {
                description 'VLAN ID must be in this range.'
                            ;
              }
            }
          }
          leaf mac-address {
            description 'MAC address.'
                        ;
            type ncd:mac-address ;
          }
          leaf vxlan-id {
            description 'VXLAN ID of MAC address.'
                        ;
            type uint32 {
              range 1..16777215 {
                description 'VXLAN ID range.'
                            ;
              }
            }
          }
          leaf tunnel-id {
            description 'Tunnel ID of MAC address.'
                        ;
            type uint32 {
              range 1..4294967295 {
                description 'Tunnel ID range.'
                            ;
              }
            }
          }
          leaf if-name {
            description 'Interface name of MAC address.'
                        ;
            type ncd:ifname {
              length 1..31 {
                description 'The length of interface name.'
                            ;
              }
            }
          }
          leaf multiflag {
            description 'The type of MAC address.'
                        ;
            type enumeration {
              enum dynamic {
                value 1 ;
                description 'Dynamic MAC address.'
                            ;
              }
              enum static {
                value 2 ;
                description 'Static MAC address.'
                            ;
              }
              enum permanent {
                value 3 ;
                description 'Permanent MAC address.'
                            ;
              }
              enum source-filter {
                value 4 ;
                description 'Source-filter MAC address.'
                            ;
              }
              enum dst-filter {
                value 5 ;
                description 'Destination-filter MAC address.'
                            ;
              }
              enum both-filter {
                value 6 ;
                description 'Both-filter MAC address.'
                            ;
              }
              enum to-static {
                value 7 ;
                description 'To-static MAC address.'
                            ;
              }
              enum to-permanent {
                value 8 ;
                description 'To-permanent MAC address.'
                            ;
              }
            }
          }
          leaf internal-vlan-id {
            description 'Internal VLAN ID.0 means VLAN is invalid.'
                        ;
            type uint16 {
              range 0..4094 {
                description 'Internal VLAN ID must be in this range.'
                            ;
              }
            }
          }
          leaf external-vlan-id {
            description 'External VLAN ID.0 means VLAN is invalid.'
                        ;
            type uint16 {
              range 0..4094 {
                description 'External VLAN ID must be in this range.'
                            ;
              }
            }
          }
          container ip-of-vxlan-mac {
            description 'Remote IP address of MAC address.'
                        ;
            choice remote-ip {
              description 'Remote IP address of MAC address.'
                          ;
              case ipv4 {
                description 'IPv4 address.'
                            ;
                leaf ipv4-address {
                  description 'Remote IPv4 address.'
                              ;
                  type ncd:ipv4-address ;
                }
              }
              case ipv6 {
                description 'IPv6 address.'
                            ;
                leaf ipv6-address {
                  description 'Remote IPv6 address.'
                              ;
                  type ncd:ipv6-address ;
                }
              }
            }
          }
          leaf esi {
            description 'ESI of MAC address.'
                        ;
            type string ;
          }
        }
      }
      container mac-vxlan-tables {
        description 'VXLAN MAC table.'
                    ;
        status obsolete ;
        list mac-vxlan-table {
          description 'VXLAN MAC table.'
                      ;
          status obsolete ;
          key 'vlan-id mac-address'
              ;
          ncd:select vxlan-id ;
          ncd:select 'vlan-id mac-address'
                     ;
          leaf vlan-id {
            description 'VLAN ID.'
                        ;
            type uint16 {
              range 1..4094 {
                description 'VLAN ID must be in this range.'
                            ;
              }
            }
          }
          leaf mac-address {
            description 'MAC address.'
                        ;
            type ncd:mac-address ;
          }
          leaf if-name {
            description 'Interface name.'
                        ;
            type ncd:ifname {
              length 1..31 {
                description 'The length of interface name.'
                            ;
              }
            }
          }
          leaf multiflag {
            description 'The type of MAC address.'
                        ;
            type enumeration {
              enum dynamic {
                value 1 ;
                description 'Dynamic MAC address.'
                            ;
              }
              enum static {
                value 2 ;
                description 'Static MAC address.'
                            ;
              }
              enum permanent {
                value 3 ;
                description 'Permanent MAC address.'
                            ;
              }
              enum source-filter {
                value 4 ;
                description 'Source-filter MAC address.'
                            ;
              }
              enum dst-filter {
                value 5 ;
                description 'Destination-filter MAC address.'
                            ;
              }
              enum both-filter {
                value 6 ;
                description 'Both-filter MAC address.'
                            ;
              }
              enum to-static {
                value 7 ;
                description 'To-static MAC address.'
                            ;
              }
              enum to-permanent {
                value 8 ;
                description 'To-permanent MAC address.'
                            ;
              }
            }
          }
          choice remote-ip {
            description 'Remote IP address.'
                        ;
            case ipv4 {
              description 'IPv4 address.'
                          ;
              leaf ipv4-address {
                description 'Remote IPv4 address.'
                            ;
                type ncd:ipv4-address ;
              }
            }
            case ipv6 {
              description 'IPv6 address.'
                          ;
              leaf ipv6-address {
                description 'Remote IPv6 address.'
                            ;
                type ncd:ipv6-address ;
              }
            }
          }
          leaf vxlan-id {
            description 'VXLAN ID.'
                        ;
            type uint32 {
              range 1..16777215 {
                description 'VXLAN ID range.'
                            ;
              }
            }
          }
        }
      }
    }
  }
  container configuration {
    description 'Configuration model info.'
                ;
    container mac {
      description 'Configuration model of MAC.'
                  ;
      container vpls-instance-config {
        description 'MAC configuration of VPLS instance.'
                    ;
        list vpls-config {
          description 'MAC configuration of VPLS instance.'
                      ;
          key instance-name ;
          leaf instance-name {
            description 'VPLS instance name.'
                        ;
            type string {
              length 1..32 {
                description 'The length of VPLS instance name.'
                            ;
              }
            }
          }
          container l2protocol-control-policy {
            description 'L2 protocol control policy.'
                        ;
            status obsolete ;
            leaf global-policy {
              description 'L2 protocol control policy.'
                          ;
              type enumeration {
                enum disable {
                  value 0 ;
                  description 'Disable global-policy.'
                              ;
                }
                enum enable {
                  value 1 ;
                  description 'Enable global-policy.'
                              ;
                }
              }
              default disable ;
            }
            leaf zdp-ztp {
              description 'ZDP-ZTP protocol control policy.'
                          ;
              type enumeration {
                enum disable {
                  value 0 ;
                  description 'ZDP-ZTP not tunnelled.'
                              ;
                }
                enum enable {
                  value 1 ;
                  description 'ZDP-ZTP tunnelled.'
                              ;
                }
              }
              default disable ;
            }
            leaf dot1x {
              description 'DOT1X protocol control policy.'
                          ;
              type enumeration {
                enum disable {
                  value 0 ;
                  description 'DOT1X not tunnelled.'
                              ;
                }
                enum enable {
                  value 1 ;
                  description 'DOT1X tunnelled.'
                              ;
                }
              }
              default disable ;
            }
            leaf lldp {
              description 'LLDP protocol control policy.'
                          ;
              type enumeration {
                enum disable {
                  value 0 ;
                  description 'LLDP not tunnelled.'
                              ;
                }
                enum enable {
                  value 1 ;
                  description 'LLDP tunnelled.'
                              ;
                }
              }
              default disable ;
            }
            leaf vtp {
              description 'VTP protocol control policy.'
                          ;
              type enumeration {
                enum disable {
                  value 0 ;
                  description 'VTP not tunnelled.'
                              ;
                }
                enum enable {
                  value 1 ;
                  description 'VTP tunnelled.'
                              ;
                }
              }
              default disable ;
            }
            leaf cdp {
              description 'CDP protocol control policy.'
                          ;
              type enumeration {
                enum disable {
                  value 0 ;
                  description 'CDP not tunnelled.'
                              ;
                }
                enum enable {
                  value 1 ;
                  description 'CDP tunnelled.'
                              ;
                }
              }
              default disable ;
            }
            leaf all-bridge-multicast {
              description 'All-bridge-multicast protocol control policy.'
                          ;
              type enumeration {
                enum disable {
                  value 0 ;
                  description 'All-bridge-multicast not tunnelled.'
                              ;
                }
                enum enable {
                  value 1 ;
                  description 'All-bridge-multicast tunnelled.'
                              ;
                }
              }
              default disable ;
            }
            leaf lacp {
              description 'LACP protocol control policy.'
                          ;
              type enumeration {
                enum disable {
                  value 0 ;
                  description 'LACP not tunnelled.'
                              ;
                }
                enum enable {
                  value 1 ;
                  description 'LACP tunnelled.'
                              ;
                }
              }
              default disable ;
            }
            choice stp {
              description 'STP protocol control policy.'
                          ;
              default not-tunnelled ;
              case not-tunnelled {
                description 'Not tunnelled.'
                            ;
                leaf stp-not-tunnelled-flag {
                  description 'Not tunnelled.'
                              ;
                  type enumeration {
                    enum not-tunnelled {
                      value 0 ;
                      description 'Not tunnelled.'
                                  ;
                    }
                  }
                  default not-tunnelled ;
                }
              }
              case tunnelled {
                description Tunnelled. ;
                leaf stp-tunnelled-flag {
                  description Tunnelled. ;
                  type enumeration {
                    enum tunnelled {
                      value 1 ;
                      description Tunnelled. ;
                    }
                  }
                  default tunnelled ;
                }
              }
              case tunnelled-monitored {
                description 'Tunnelled and monitored.'
                            ;
                leaf stp-tunnelled-monitored-flag {
                  description 'Tunnelled and monitored.'
                              ;
                  type enumeration {
                    enum tunnelled-monitored {
                      value 3 ;
                      description 'Tunnelled and monitored.'
                                  ;
                    }
                  }
                  default tunnelled-monitored ;
                }
              }
            }
            choice zesr {
              description 'ZESR protocol control policy.'
                          ;
              default not-tunnelled ;
              case not-tunnelled {
                description 'Not tunnelled.'
                            ;
                leaf zesr-not-tunnelled-flag {
                  description 'Not tunnelled.'
                              ;
                  type enumeration {
                    enum not-tunnelled {
                      value 0 ;
                      description 'Not tunnelled.'
                                  ;
                    }
                  }
                  default not-tunnelled ;
                }
              }
              case tunnelled {
                description Tunnelled. ;
                leaf zesr-tunnelled-flag {
                  description Tunnelled. ;
                  type enumeration {
                    enum tunnelled {
                      value 1 ;
                      description Tunnelled. ;
                    }
                  }
                  default tunnelled ;
                }
              }
              case tunnelled-monitored {
                description 'Tunnelled and monitored.'
                            ;
                leaf zesr-tunnelled-monitored-flag {
                  description 'Tunnelled and monitored.'
                              ;
                  type enumeration {
                    enum tunnelled-monitored {
                      value 3 ;
                      description 'Tunnelled and monitored.'
                                  ;
                    }
                  }
                  default tunnelled-monitored ;
                }
              }
            }
            leaf pvst-plus {
              description 'PVST+ protocol control policy.'
                          ;
              type enumeration {
                enum disable {
                  value 0 ;
                  description 'PVST+ not tunnelled.'
                              ;
                }
                enum enable {
                  value 1 ;
                  description 'PVST+ tunnelled.'
                              ;
                }
              }
              default disable ;
            }
            leaf udld {
              description 'Udld protocol control policy.'
                          ;
              type enumeration {
                enum disable {
                  value 0 ;
                  description 'Udld not tunnelled.'
                              ;
                }
                enum enable {
                  value 1 ;
                  description 'Udld tunnelled.'
                              ;
                }
              }
              default disable ;
            }
            leaf mstp {
              description 'Mstp protocol control policy.'
                          ;
              type enumeration {
                enum disable {
                  value 0 ;
                  description 'Mstp not tunnelled'
                              ;
                }
                enum enable {
                  value 1 ;
                  description 'Mstp tunnelled'
                              ;
                }
              }
              default disable ;
            }
            leaf rstp {
              description 'Rstp protocol control policy.'
                          ;
              type enumeration {
                enum disable {
                  value 0 ;
                  description 'Rstp not tunnelled.'
                              ;
                }
                enum enable {
                  value 1 ;
                  description 'Rstp tunnelled.'
                              ;
                }
              }
              default disable ;
            }
            leaf gvrp {
              description 'Gvrp protocol control policy.'
                          ;
              type enumeration {
                enum disable {
                  value 0 ;
                  description 'Gvrp not tunnelled.'
                              ;
                }
                enum enable {
                  value 1 ;
                  description 'Gvrp tunnelled.'
                              ;
                }
              }
              default disable ;
            }
            leaf pbb-te {
              description 'Pbb-te protocol control policy.'
                          ;
              type enumeration {
                enum disable {
                  value 0 ;
                  description 'Pbb-te not tunnelled.'
                              ;
                }
                enum enable {
                  value 1 ;
                  description 'Pbb-te tunnelled.'
                              ;
                }
              }
              default disable ;
            }
            leaf mac-in-mac {
              description 'MAC-in-MAC protocol control policy.'
                          ;
              type enumeration {
                enum disable {
                  value 0 ;
                  description 'MAC-in-MAC not tunnelled.'
                              ;
                }
                enum enable {
                  value 1 ;
                  description 'MAC-in-MAC tunnelled.'
                              ;
                }
              }
              default disable ;
            }
            leaf efm {
              description 'EFM protocol control policy.'
                          ;
              type enumeration {
                enum disable {
                  value 0 ;
                  description 'EFM not tunnelled.'
                              ;
                }
                enum enable {
                  value 1 ;
                  description 'EFM tunnelled.'
                              ;
                }
              }
              default disable ;
            }
            leaf cfm {
              description 'CFM protocol control policy.'
                          ;
              type enumeration {
                enum disable {
                  value 0 ;
                  description 'CFM not tunnelled.'
                              ;
                }
                enum enable {
                  value 1 ;
                  description 'CFM tunnelled.'
                              ;
                }
              }
              default disable ;
            }
            leaf y1731 {
              description 'Y1731 protocol control policy.'
                          ;
              type enumeration {
                enum disable {
                  value 0 ;
                  description 'Y1731 not tunnelled.'
                              ;
                }
                enum enable {
                  value 1 ;
                  description 'Y1731 tunnelled.'
                              ;
                }
              }
              default disable ;
            }
            leaf user-protocol-name {
              description 'The class name of user protocol.'
                          ;
              type string {
                length 1..31 {
                  description 'The length of user protocol class name.'
                              ;
                }
              }
            }
            leaf garp {
              description 'Garp protocol control policy.'
                          ;
              type enumeration {
                enum disable {
                  value 0 ;
                  description 'Garp not tunnelled.'
                              ;
                }
                enum enable {
                  value 1 ;
                  description 'Garp tunnelled.'
                              ;
                }
              }
              default disable ;
            }
            leaf gmrp {
              description 'Gmrp protocol control policy.'
                          ;
              type enumeration {
                enum disable {
                  value 0 ;
                  description 'Gmrp not tunnelled.'
                              ;
                }
                enum enable {
                  value 1 ;
                  description 'Gmrp tunnelled.'
                              ;
                }
              }
              default disable ;
            }
            leaf dldp {
              description 'Dldp protocol control policy.'
                          ;
              type enumeration {
                enum disable {
                  value 0 ;
                  description 'Dldp not tunnelled.'
                              ;
                }
                enum enable {
                  value 1 ;
                  description 'Dldp tunnelled.'
                              ;
                }
              }
              default disable ;
            }
          }
          container mac-moving {
            description 'MAC move policy configuration.'
                        ;
            leaf suppressible {
              description 'MAC or MAC/IP routing move dampening policy.Default '
                        + 'value is defined by performance parameter.'
                          ;
              type enumeration {
                enum disable {
                  value 0 ;
                  description 'Disable MAC move dampening policy.'
                              ;
                }
                enum enable {
                  value 1 ;
                  description 'Enable MAC move dampening policy.'
                              ;
                }
              }
            }
            container mac-moving-count {
              description 'Maximum MAC or MAC/IP routing move count.'
                          ;
              presence mac-moving-count ;
              leaf max-count {
                description 'Maximum MAC or MAC/IP routing move count.The defau'
                          + 'lt value ,mim value and max value is defined by pe'
                          + 'rformance parameter.'
                            ;
                type uint32 {
                  range 1..4294967295 {
                    description 'Mim value and max value is defined by performa'
                              + 'nce parameter.'
                                ;
                  }
                }
                mandatory true ;
              }
              leaf suppress-by-max-count {
                description 'MAC or MAC/IP routing move dampening by max-count '
                          + 'or by max-frequency.'
                            ;
                type empty ;
                mandatory true ;
              }
            }
            leaf max-frequency {
              description 'Maximum MAC move frequency.'
                          ;
              type uint32 {
                range 1..100 {
                  description 'Frequency must be in this range.'
                              ;
                }
              }
              default 2 ;
            }
            leaf auto-recovery-time {
              description 'Auto recovery time,unit second.The default value ,mi'
                        + 'm value and max value is defined by performance para'
                        + 'meter.0 means not to recover.'
                          ;
              type uint32 {
                range 0..4294967295 {
                  description 'Mim value and max value is defined by performanc'
                            + 'e parameter.0 means not to recover.'
                              ;
                }
              }
              units second ;
            }
            leaf sampling-period {
              description 'MAC or MAC/IP routing move dampening count interval,'
                        + 'unit second.The default value ,mim value and max val'
                        + 'ue is defined by performance parameter.'
                          ;
              type uint32 {
                range 1..4294967295 {
                  description 'Mim value and max value is defined by performanc'
                            + 'e parameter.'
                              ;
                }
              }
              units second ;
            }
            leaf anti-move {
              description 'Anti MAC move flag.'
                          ;
              type enumeration {
                enum local-to-pw-disable {
                  value 0 ;
                  description 'Local MAC can not move to remote.'
                              ;
                }
                enum disable {
                  value 2 ;
                  description 'MAC can move.'
                              ;
                }
              }
              default disable ;
            }
            container black-hole {
              description 'MAC or MAC/IP routing move dampening Black-Hole filt'
                        + 'er.'
                          ;
              leaf source-filter {
                description 'MAC or MAC/IP routing move dampening Black-Hole so'
                          + 'urce filter.'
                            ;
                type enumeration {
                  enum not-filter {
                    value 0 ;
                    description 'MAC or MAC/IP routing move dampening Black-Hol'
                              + 'e source not filter.'
                                ;
                  }
                  enum filter {
                    value 1 ;
                    description 'MAC or MAC/IP routing move dampening Black-Hol'
                              + 'e source filter.'
                                ;
                  }
                }
                default not-filter ;
              }
              leaf destination-filter {
                description 'MAC or MAC/IP routing move dampening Black-Hole de'
                          + 'stination filter.'
                            ;
                type enumeration {
                  enum not-filter {
                    value 0 ;
                    description 'MAC or MAC/IP routing move dampening Black-Hol'
                              + 'e destination not filter.'
                                ;
                  }
                  enum filter {
                    value 1 ;
                    description 'MAC or MAC/IP routing move dampening Black-Hol'
                              + 'e destination filter.'
                                ;
                  }
                }
                default not-filter ;
              }
            }
          }
          container mac-learning {
            description 'MAC learn policy configuration.'
                        ;
            leaf learn {
              description 'MAC learn control policy.'
                          ;
              type enumeration {
                enum disable {
                  value 0 ;
                  description 'Can not learn MAC address.'
                              ;
                }
                enum enable {
                  value 1 ;
                  description 'Can learn MAC address.'
                              ;
                }
              }
              default enable ;
            }
            leaf remote-no-learning {
              description 'Do not learn remote MAC entries.'
                          ;
              type enumeration {
                enum disable {
                  value 0 ;
                  description 'Can learn remote MAC address.'
                              ;
                }
                enum enable {
                  value 1 ;
                  description 'Can not learn remote MAC address.'
                              ;
                }
              }
              default disable ;
            }
            leaf rate-limited {
              description 'MAC learn speed control policy.'
                          ;
              type enumeration {
                enum disable {
                  value 0 ;
                  description 'Disable MAC learn speed control policy.'
                              ;
                }
                enum enable {
                  value 1 ;
                  description 'Enable MAC learn speed control policy.'
                              ;
                }
              }
              default disable ;
            }
            leaf max-frequency {
              description 'Maximum MAC learn speed.'
                          ;
              type uint32 {
                range 1..100 {
                  description 'Frequency must be in this range.'
                              ;
                }
              }
              default 2 ;
            }
            leaf sampling-period {
              description 'Sample period of MAC learn.'
                          ;
              type uint32 {
                range 1..10 {
                  description '1-10 senconds.'
                              ;
                }
              }
              units second ;
              default 5 ;
            }
            leaf auto-recovery-time {
              description 'Auto recovery time of blocked VPLS instance.'
                          ;
              type uint32 {
                range 0..120 {
                  description '0-120 seconds.0 means no to recover.'
                              ;
                }
              }
              units second ;
              default 10 ;
            }
            leaf evpn-local-mac-advertising {
              description 'EVPN local MAC advertising policy.'
                          ;
              type enumeration {
                enum enable {
                  value 1 ;
                  description 'EVPN local MAC advertising enable.'
                              ;
                }
                enum disable {
                  value 2 ;
                  description 'EVPN local MAC advertising disable.'
                              ;
                }
              }
              default enable ;
            }
            leaf evpn-remote-mac-receiving {
              description 'EVPN remote advertised MAC receiving policy.'
                          ;
              type enumeration {
                enum enable {
                  value 1 ;
                  description 'EVPN remote advertised MAC receiving enable.'
                              ;
                }
                enum disable {
                  value 2 ;
                  description 'EVPN remote advertised MAC receiving disable.'
                              ;
                }
              }
              default enable ;
            }
          }
          container mac-entries {
            description 'Maximum MAC entries and action when MAC entries is exc'
                      + 'eeding the maximum.'
                        ;
            presence mac-entries ;
            leaf maximum-entries {
              description 'Maximum MAC entries.'
                          ;
              type uint32 {
                range 1..4294967295 {
                  description 'Minimum is 1. Maximum and default is defined by '
                            + 'performance parameter.'
                              ;
                }
              }
              mandatory true ;
            }
            leaf maximum-action {
              description 'The action when MAC entries is exceeding the maximum.'
                          ;
              type enumeration {
                enum broadcast {
                  value 0 ;
                  description 'The action when MAC entries is exceeding the max'
                            + 'imum is broadcast.'
                              ;
                }
                enum drop {
                  value 1 ;
                  description 'The action when MAC entries is exceeding the max'
                            + 'imum is drop.'
                              ;
                }
              }
              mandatory true ;
            }
          }
          container l2protocol-control-policy-expand {
            description 'L2 protocol control policy expand.'
                        ;
            leaf global-policy {
              description 'L2 protocol control policy global on-off.'
                          ;
              type enumeration {
                enum disable {
                  value 0 ;
                  description 'Global policy is disable.'
                              ;
                }
                enum enable {
                  value 1 ;
                  description 'Global policy is enable.'
                              ;
                }
              }
              default disable ;
            }
            leaf zdp-ztp {
              description 'ZDP-ZTP protocol control policy.'
                          ;
              type enumeration {
                enum tunnelled {
                  value 1 ;
                  description 'ZDP-ZTP is tunnelled.'
                              ;
                }
                enum terminated {
                  value 2 ;
                  description 'ZDP-ZTP is terminated.'
                              ;
                }
              }
            }
            leaf vtp {
              description 'VTP protocol control policy.'
                          ;
              type enumeration {
                enum tunnelled {
                  value 1 ;
                  description 'VTP is tunnelled.'
                              ;
                }
                enum terminated {
                  value 2 ;
                  description 'VTP is terminated.'
                              ;
                }
              }
            }
            leaf cdp {
              description 'CDP protocol control policy.'
                          ;
              type enumeration {
                enum tunnelled {
                  value 1 ;
                  description 'CDP is tunnelled.'
                              ;
                }
                enum terminated {
                  value 2 ;
                  description 'CDP is terminated.'
                              ;
                }
              }
            }
            leaf all-bridge-multicast {
              description 'All-bridge-multicast protocol control policy.'
                          ;
              type enumeration {
                enum tunnelled {
                  value 1 ;
                  description 'All-bridge-multicast is tunnelled.'
                              ;
                }
                enum terminated {
                  value 2 ;
                  description 'All-bridge-multicast is terminated.'
                              ;
                }
              }
            }
            leaf dot1x {
              description 'DOT1X protocol control policy.'
                          ;
              type enumeration {
                enum tunnelled {
                  value 1 ;
                  description 'DOT1X is tunnelled.'
                              ;
                }
                enum terminated {
                  value 2 ;
                  description 'DOT1X is terminated.'
                              ;
                }
              }
            }
            leaf zesr {
              description 'ZESR protocol control policy.'
                          ;
              type enumeration {
                enum tunnelled {
                  value 1 ;
                  description 'ZESR is tunnelled.'
                              ;
                }
                enum terminated {
                  value 2 ;
                  description 'ZESR is terminated.'
                              ;
                }
                enum tunnelled-monitored {
                  value 3 ;
                  description 'ZESR is tunnelled-monitored.'
                              ;
                }
              }
            }
            leaf lacp {
              description 'LACP protocol control policy.'
                          ;
              type enumeration {
                enum tunnelled {
                  value 1 ;
                  description 'LACP is tunnelled.'
                              ;
                }
                enum terminated {
                  value 2 ;
                  description 'LACP is terminated.'
                              ;
                }
              }
            }
            leaf lldp {
              description 'LLDP protocol control policy.'
                          ;
              type enumeration {
                enum tunnelled {
                  value 1 ;
                  description 'LLDP is tunnelled.'
                              ;
                }
                enum terminated {
                  value 2 ;
                  description 'LLDP is terminated.'
                              ;
                }
              }
            }
            leaf stp {
              description 'STP protocol control policy.'
                          ;
              type enumeration {
                enum tunnelled {
                  value 1 ;
                  description 'STP is tunnelled.'
                              ;
                }
                enum terminated {
                  value 2 ;
                  description 'STP is terminated.'
                              ;
                }
                enum tunnelled-monitored {
                  value 3 ;
                  description 'STP is tunnelled-monitored.'
                              ;
                }
              }
            }
            leaf pvst-plus {
              description 'PVST+ protocol control policy.'
                          ;
              type enumeration {
                enum tunnelled {
                  value 1 ;
                  description 'PVST+ is tunnelled.'
                              ;
                }
                enum terminated {
                  value 2 ;
                  description 'PVST+ is terminated.'
                              ;
                }
              }
            }
            leaf udld {
              description 'UDLD protocol control policy.'
                          ;
              type enumeration {
                enum tunnelled {
                  value 1 ;
                  description 'UDLD is tunnelled.'
                              ;
                }
                enum terminated {
                  value 2 ;
                  description 'UDLD is terminated.'
                              ;
                }
              }
            }
            leaf mstp {
              description 'MSTP protocol control policy.'
                          ;
              type enumeration {
                enum tunnelled {
                  value 1 ;
                  description 'MSTP is tunnelled.'
                              ;
                }
              }
            }
            leaf rstp {
              description 'RSTP protocol control policy.'
                          ;
              type enumeration {
                enum tunnelled {
                  value 1 ;
                  description 'RSTP is tunnelled.'
                              ;
                }
              }
            }
            leaf gvrp {
              description 'GVRP protocol control policy.'
                          ;
              type enumeration {
                enum tunnelled {
                  value 1 ;
                  description 'GVRP is tunnelled.'
                              ;
                }
                enum terminated {
                  value 2 ;
                  description 'GVRP is terminated.'
                              ;
                }
              }
            }
            leaf pbb-te {
              description 'PBB-TE protocol control policy.'
                          ;
              type enumeration {
                enum tunnelled {
                  value 1 ;
                  description 'PBB-TE is tunnelled.'
                              ;
                }
              }
            }
            leaf mac-in-mac {
              description 'MAC-IN-MAC protocol control policy.'
                          ;
              type enumeration {
                enum tunnelled {
                  value 1 ;
                  description 'MAC-IN-MAC is tunnelled.'
                              ;
                }
              }
            }
            leaf efm {
              description 'EFM protocol control policy.'
                          ;
              type enumeration {
                enum tunnelled {
                  value 1 ;
                  description 'EFM is tunnelled.'
                              ;
                }
                enum terminated {
                  value 2 ;
                  description 'EFM is terminated.'
                              ;
                }
              }
            }
            leaf cfm {
              description 'CFM protocol control policy.'
                          ;
              type enumeration {
                enum tunnelled {
                  value 1 ;
                  description 'CFM is tunnelled.'
                              ;
                }
                enum terminated {
                  value 2 ;
                  description 'CFM is terminated.'
                              ;
                }
              }
            }
            leaf y1731 {
              description 'Y1731 protocol control policy.'
                          ;
              type enumeration {
                enum tunnelled {
                  value 1 ;
                  description 'Y1731 is tunnelled.'
                              ;
                }
              }
            }
            leaf garp {
              description 'GARP protocol control policy.'
                          ;
              type enumeration {
                enum tunnelled {
                  value 1 ;
                  description 'GARP is tunnelled.'
                              ;
                }
                enum terminated {
                  value 2 ;
                  description 'GARP is terminated.'
                              ;
                }
              }
            }
            leaf gmrp {
              description 'GMRP protocol control policy.'
                          ;
              type enumeration {
                enum tunnelled {
                  value 1 ;
                  description 'GMRP is tunnelled.'
                              ;
                }
                enum terminated {
                  value 2 ;
                  description 'GMRP is terminated.'
                              ;
                }
              }
            }
            leaf dldp {
              description 'DLDP protocol control policy.'
                          ;
              type enumeration {
                enum tunnelled {
                  value 1 ;
                  description 'DLDP is tunnelled.'
                              ;
                }
                enum terminated {
                  value 2 ;
                  description 'DLDP is terminated.'
                              ;
                }
              }
            }
            leaf dot3x {
              description 'DOT3X protocol control policy.'
                          ;
              type enumeration {
                enum tunnelled {
                  value 1 ;
                  description 'DOT3X is tunnelled.'
                              ;
                }
                enum terminated {
                  value 2 ;
                  description 'DOT3X is terminated.'
                              ;
                }
              }
            }
            leaf erps {
              description 'ERPS protocol control policy.'
                          ;
              type enumeration {
                enum tunnelled {
                  value 1 ;
                  description 'ERPS is tunnelled.'
                              ;
                }
                enum terminated {
                  value 2 ;
                  description 'ERPS is terminated.'
                              ;
                }
              }
            }
            leaf l2bfd {
              description 'L2BFD protocol control policy.'
                          ;
              type enumeration {
                enum tunnelled {
                  value 1 ;
                  description 'L2BFD is tunnelled.'
                              ;
                }
                enum terminated {
                  value 2 ;
                  description 'L2BFD is terminated.'
                              ;
                }
              }
            }
            container user-protocol-template {
              description 'The template of user protocol.'
                          ;
              presence user-protocol-template ;
              leaf user-protocol-name {
                description 'The class name of user protocol.'
                            ;
                type string {
                  length 1..31 {
                    description 'The length of user protocol class name.'
                                ;
                  }
                }
                mandatory true ;
              }
              leaf user-protocol-action {
                description 'User protocol template action.'
                            ;
                type enumeration {
                  enum dropped {
                    value 0 ;
                    description 'User protocol template action is dropped.'
                                ;
                  }
                  enum tunnelled {
                    value 1 ;
                    description 'User protocol template action is tunnelled.'
                                ;
                  }
                  enum terminated {
                    value 2 ;
                    description 'User protocol template action is terminated.'
                                ;
                  }
                }
                mandatory true ;
              }
            }
          }
          container mac-age {
            description 'MAC age configuration.'
                        ;
            leaf aging-time-local {
              description 'Local MAC aging time.'
                          ;
              type uint16 {
                range 60..65535 {
                  description 'Unit:Second.Minimum is 60 seconds. Maximum and d'
                            + 'efault is defined by performance parameter.'
                              ;
                }
              }
              units second ;
            }
            leaf aging-time-remote {
              description 'Remote MAC aging time.'
                          ;
              type uint16 {
                range 60..65535 {
                  description 'Unit:Second.Minimum is 60 seconds. Maximum and d'
                            + 'efault is defined by performance parameter.'
                              ;
                }
              }
              units second ;
            }
          }
        }
      }
      container vpls-port-config {
        description 'Configuration of interface bound to VPLS instance.'
                    ;
        list mac-vfi-port-config {
          description 'Configuration of interface bound to VPLS instance.'
                      ;
          key 'if-name instance-name'
              ;
          leaf if-name {
            description 'Interface name.'
                        ;
            type ncd:ifname {
              length 1..31 {
                description 'The length of interface name.'
                            ;
              }
            }
          }
          leaf instance-name {
            description 'VPLS instance name.'
                        ;
            type string {
              length 1..32 {
                description 'The length of VPLS instance name.'
                            ;
              }
            }
          }
          leaf learn-priority {
            description 'Interface learn priority.'
                        ;
            type enumeration {
              enum default {
                value 0 ;
                description 'Default priority.'
                            ;
              }
              enum lower {
                value 1 ;
                description 'Lower priority.'
                            ;
              }
              enum normal {
                value 2 ;
                description 'Normal priority.'
                            ;
              }
              enum higher {
                value 3 ;
                description 'Higher priority.'
                            ;
              }
            }
            default default ;
          }
          leaf move-blockable {
            description 'MAC move blockable level.'
                        ;
            type enumeration {
              enum unblockable {
                value 0 ;
                description 'Do not block.'
                            ;
              }
              enum blockable-primary {
                value 1 ;
                description 'Can block and blockable level is primary.'
                            ;
              }
              enum blockable-secondary {
                value 2 ;
                description 'Can block and blockable level is secondary.'
                            ;
              }
            }
            default blockable-secondary ;
          }
          container mac-entries {
            description 'Maximum MAC entries and action when MAC entries is exc'
                      + 'eeding the maximum.'
                        ;
            presence mac-entries ;
            leaf maximum {
              description 'Maximum MAC entries.'
                          ;
              type uint32 {
                range 1..4294967295 {
                  description 'Minimum is 1. Maximum and default is defined by '
                            + 'performance parameter.'
                              ;
                }
              }
              mandatory true ;
            }
            leaf max-mac-entries-action {
              description 'The action when MAC entries is exceeding the maximum.'
                          ;
              type enumeration {
                enum broadcast {
                  value 0 ;
                  description 'The action when MAC entries is exceeding the max'
                            + 'imum is broadcast.'
                              ;
                }
                enum drop {
                  value 1 ;
                  description 'The action when MAC entries is exceeding the max'
                            + 'imum is drop.'
                              ;
                }
              }
              mandatory true ;
            }
          }
          leaf black-hole-mac-max-count {
            description 'Maximum Black-Hole MAC count.'
                        ;
            type uint8 {
              range 1..10 {
                description 'Default is 1.'
                            ;
              }
            }
            default 1 ;
          }
          leaf learn-enable {
            description 'MAC learn switch.'
                        ;
            type enumeration {
              enum disable {
                value 0 ;
                description 'Disable MAC learn.'
                            ;
              }
              enum enable {
                value 1 ;
                description 'Enable MAC learn.'
                            ;
              }
            }
            default enable ;
          }
        }
      }
      container vpls-static-vxlan-tunnel-config {
        description 'Configuration of static VXLAN tunnel.'
                    ;
        list static-vxlan-tunnel-config {
          description 'Configuration of static VXLAN tunnel.'
                      ;
          key if-name ;
          leaf if-name {
            description 'Interface name.'
                        ;
            type ncd:ifname {
              length 1..31 {
                description 'The length of interface name.'
                            ;
              }
            }
          }
          container mac-entries {
            description 'Maximum MAC entries and action when MAC entries is exc'
                      + 'eeding the maximum.'
                        ;
            presence mac-entries ;
            leaf maximum {
              description 'Maximum MAC entries.'
                          ;
              type uint32 {
                range 1..4294967295 {
                  description 'Minimum is 1. Maximum and default is defined by '
                            + 'performance parameter.'
                              ;
                }
              }
              mandatory true ;
            }
            leaf max-mac-entries-action {
              description 'The action when MAC entries is exceeding the maximum.'
                          ;
              type enumeration {
                enum broadcast {
                  value 0 ;
                  description 'The action when MAC entries is exceeding the max'
                            + 'imum is broadcast.'
                              ;
                }
                enum drop {
                  value 1 ;
                  description 'The action when MAC entries is exceeding the max'
                            + 'imum is drop.'
                              ;
                }
              }
              mandatory true ;
            }
          }
        }
      }
      container vpls-pw-config {
        description 'Only PW configuration of VPLS instance.'
                    ;
        list mac-vfi-pw-config {
          description 'Only PW configuration of VPLS instance.'
                      ;
          key 'pw-name instance-name'
              ;
          leaf pw-name {
            description 'PW name.'
                        ;
            type ncd:ifname {
              length 1..31 {
                description 'Then length of interface name.'
                            ;
              }
            }
          }
          leaf instance-name {
            description 'VPLS instance name.'
                        ;
            type string {
              length 1..32 {
                description 'The length of VPLS instance name.'
                            ;
              }
            }
          }
          container traffic-rate-limit {
            description 'Traffic control policy.'
                        ;
            leaf traffic-maximum {
              description 'Maximum traffic rate.Operation of removing means not'
                        + ' to limit.Reading no value means no limit.'
                          ;
              type uint32 {
                range 64..4000000000 {
                  description 'Minimum is 64. Maximum is defined by performance'
                            + ' parameter.'
                              ;
                }
              }
              units kbps ;
            }
            container unicast-traffic {
              description 'Unicast traffic control policy.'
                          ;
              leaf maximum {
                description 'Maximum percent of known unicast traffic.'
                            ;
                type uint32 {
                  range 1..100 {
                    description Percent. ;
                  }
                }
                units percent ;
                default 100 ;
              }
              leaf action {
                description 'Action when know unicast traffic exceed the maximu'
                          + 'm.'
                            ;
                type enumeration {
                  enum drop {
                    value 1 ;
                    description 'Drop the traffic.'
                                ;
                  }
                }
                default drop ;
              }
            }
            container unknown-unicast-traffic {
              description 'Unknown unicast traffic control policy.'
                          ;
              leaf maximum {
                description 'Maximum percent of unknown unicast traffic.'
                            ;
                type uint32 {
                  range 1..100 {
                    description Percent. ;
                  }
                }
                units percent ;
                default 100 ;
              }
              leaf action {
                description 'Action when unknown unicast traffic exceed the max'
                          + 'imum.'
                            ;
                type enumeration {
                  enum drop {
                    value 1 ;
                    description 'Drop the traffic.'
                                ;
                  }
                }
                default drop ;
              }
            }
            container unknown-multicast-traffic {
              description 'Unknown multicast traffic control policy.'
                          ;
              leaf maximum {
                description 'Maximum percent of unknown multicast traffic.'
                            ;
                type uint32 {
                  range 1..100 {
                    description Percent. ;
                  }
                }
                units percent ;
                default 100 ;
              }
              leaf action {
                description 'Action when unknown multicast traffic exceed the m'
                          + 'aximum.'
                            ;
                type enumeration {
                  enum drop {
                    value 1 ;
                    description 'Drop the traffic.'
                                ;
                  }
                }
                default drop ;
              }
            }
            container broadcast-traffic {
              description 'Broadcast traffic control policy.'
                          ;
              leaf maximum {
                description 'Maximum percent of broadcast traffic.'
                            ;
                type uint32 {
                  range 1..100 {
                    description Percent. ;
                  }
                }
                units percent ;
                default 100 ;
              }
              leaf action {
                description 'Action when broadcast traffic exceed the maximum.'
                            ;
                type enumeration {
                  enum drop {
                    value 1 ;
                    description 'Drop the traffic.'
                                ;
                  }
                }
                default drop ;
              }
            }
            container multicast-traffic {
              description 'Multicast traffic control policy.'
                          ;
              leaf maximum {
                description 'Maximum percent of multicast traffic.'
                            ;
                type uint32 {
                  range 1..100 {
                    description Percent. ;
                  }
                }
                units percent ;
                default 100 ;
              }
              leaf action {
                description 'Action when multicast traffic exceed the maximum.'
                            ;
                type enumeration {
                  enum drop {
                    value 1 ;
                    description 'Drop the traffic.'
                                ;
                  }
                }
                default drop ;
              }
            }
          }
        }
      }
      container permanent-mac-address {
        description 'Permanent MAC address configuration.'
                    ;
        container mac-permanent-mac-address-vpn-vlan {
          description 'Permanent MAC address configuration.'
                      ;
          list permanent-mac-address-vpn-vlan {
            description 'Permanent MAC address configuration.'
                        ;
            key 'vlan-id mac-address instance-name'
                ;
            leaf vlan-id {
              description 'VLAN ID.'
                          ;
              type uint16 {
                range 1..4094 {
                  description 'VLAN ID must be in this range.'
                              ;
                }
              }
            }
            leaf mac-address {
              description 'MAC address.'
                          ;
              type ncd:mac-address ;
            }
            leaf instance-name {
              description 'VPLS instance name.'
                          ;
              type string {
                length 1..32 {
                  description 'The length of VPLS instance name.'
                              ;
                }
              }
            }
            choice mac-type {
              description 'MAC type.'
                          ;
              mandatory true ;
              case permanent {
                description 'Permanent MAC.'
                            ;
                leaf flag {
                  description 'Multiflag of MAC address.'
                              ;
                  type enumeration {
                    enum permanent {
                      value 3 ;
                      description 'Permanent MAC.'
                                  ;
                    }
                  }
                  mandatory true ;
                }
                container interface {
                  description 'Outgoing info.'
                              ;
                  choice iforvlanif {
                    description 'VLAN interface,other interface or esi.'
                                ;
                    mandatory true ;
                    case if {
                      description 'Interface name.'
                                  ;
                      leaf if-name {
                        description 'Interface name.'
                                    ;
                        type ncd:ifname {
                          length 1..31 {
                            description 'The length of interface name.'
                                        ;
                          }
                        }
                        mandatory true ;
                      }
                    }
                    case vlanif {
                      description 'VLAN interface.'
                                  ;
                      leaf vlanif {
                        description 'VLAN interface name.'
                                    ;
                        type ncd:ifname {
                          length 1..31 {
                            description 'The length of interface name.'
                                        ;
                          }
                        }
                        mandatory true ;
                      }
                      leaf phy-if-name {
                        description 'Physical interface name.'
                                    ;
                        type ncd:ifname {
                          length 1..31 {
                            description 'The length of interface name.'
                                        ;
                          }
                        }
                        mandatory true ;
                      }
                    }
                    case vxlan-tunnel {
                      description 'VXLAN tunnel.'
                                  ;
                      leaf vxlan-tunnel-name {
                        description 'VXLAN tunnel name.'
                                    ;
                        type ncd:ifname {
                          length 1..31 {
                            description 'The length of interface name.'
                                        ;
                          }
                        }
                        mandatory true ;
                      }
                      leaf vni {
                        description VNI. ;
                        type uint32 {
                          range 1..16777215 {
                            description 'VNI must be in this range.'
                                        ;
                          }
                        }
                        mandatory true ;
                      }
                    }
                    case esi {
                      description 'Ethernet segment.'
                                  ;
                      leaf type {
                        description 'ESI type.'
                                    ;
                        type enumeration {
                          enum static {
                            value 1 ;
                          }
                        }
                        mandatory true ;
                      }
                      leaf octets {
                        description 'Ethernet segment identifier(ESI).'
                                    ;
                        type string ;
                        mandatory true ;
                      }
                    }
                  }
                }
              }
              case filter {
                description 'Filter MAC.'
                            ;
                leaf filter-flag {
                  description 'Multiflag of MAC address.'
                              ;
                  type enumeration {
                    enum source-filter {
                      value 4 ;
                      description 'Source-filter MAC address.'
                                  ;
                    }
                    enum dst-filter {
                      value 5 ;
                      description 'Destination-filter MAC address.'
                                  ;
                    }
                    enum both-filter {
                      value 6 ;
                      description 'Both-filter MAC address.'
                                  ;
                    }
                  }
                  mandatory true ;
                }
              }
            }
          }
        }
        container mac-permanent-mac-address-no-vlan {
          description 'Permanent MAC address with no VLAN.'
                      ;
          list permanent-mac-address-no-vlan {
            description 'Permanent MAC address with no VLAN.'
                        ;
            key 'mac-address instance-name'
                ;
            leaf mac-address {
              description 'MAC address.'
                          ;
              type ncd:mac-address ;
            }
            leaf instance-name {
              description 'VPLS instance name.'
                          ;
              type string {
                length 1..32 {
                  description 'The length of VPLS instance name.'
                              ;
                }
              }
            }
            choice mac-type {
              description 'MAC type.'
                          ;
              mandatory true ;
              case permanent {
                description 'Permanent MAC.'
                            ;
                leaf flag {
                  description 'Multiflag of MAC address.'
                              ;
                  type enumeration {
                    enum permanent {
                      value 3 ;
                      description 'Permanent MAC.'
                                  ;
                    }
                  }
                  mandatory true ;
                }
                container interface {
                  description 'Outgo info.'
                              ;
                  choice iforvlanif {
                    description 'VLAN interface,other interface or esi.'
                                ;
                    mandatory true ;
                    case if {
                      description 'Interface name.'
                                  ;
                      leaf if-name {
                        description 'Interface name.'
                                    ;
                        type ncd:ifname {
                          length 1..31 {
                            description 'The length of interface name.'
                                        ;
                          }
                        }
                        mandatory true ;
                      }
                    }
                    case vlanif {
                      description 'VLAN interface.'
                                  ;
                      leaf vlanif {
                        description 'Interface name.'
                                    ;
                        type ncd:ifname {
                          length 1..31 {
                            description 'The length of interface name.'
                                        ;
                          }
                        }
                        mandatory true ;
                      }
                      leaf phy-if-name {
                        description 'Physical interface name.'
                                    ;
                        type ncd:ifname {
                          length 1..31 {
                            description 'The length of interface name.'
                                        ;
                          }
                        }
                        mandatory true ;
                      }
                    }
                    case vxlan-tunnel {
                      description 'VXLAN tunnel.'
                                  ;
                      leaf vxlan-tunnel-name {
                        description 'VXLAN tunnel name.'
                                    ;
                        type ncd:ifname {
                          length 1..31 {
                            description 'The length of interface name.'
                                        ;
                          }
                        }
                        mandatory true ;
                      }
                      leaf vni {
                        description VNI. ;
                        type uint32 {
                          range 1..16777215 {
                            description 'VNI must be in this range.'
                                        ;
                          }
                        }
                        mandatory true ;
                      }
                    }
                    case esi {
                      description 'Ethernet segment.'
                                  ;
                      leaf type {
                        description 'ESI type.'
                                    ;
                        type enumeration {
                          enum static {
                            value 1 ;
                          }
                        }
                        mandatory true ;
                      }
                      leaf octets {
                        description 'Ethernet segment identifier(ESI).'
                                    ;
                        type string ;
                        mandatory true ;
                      }
                    }
                  }
                }
              }
              case filter {
                description 'Filter MAC.'
                            ;
                leaf filter-flag {
                  description 'Multiflag of MAC address.'
                              ;
                  type enumeration {
                    enum source-filter {
                      value 4 ;
                      description 'Source-filter MAC address.'
                                  ;
                    }
                    enum dst-filter {
                      value 5 ;
                      description 'Destination-filter MAC address.'
                                  ;
                    }
                    enum both-filter {
                      value 6 ;
                      description 'Both-filter MAC address.'
                                  ;
                    }
                  }
                  mandatory true ;
                }
              }
            }
          }
        }
        container mac-permanent-address-no-vpn {
          description 'Permanent MAC address with no VPN.'
                      ;
          list permanent-mac-address-no-vpn {
            description 'Permanent MAC address with no VPN.'
                        ;
            key 'vlan-id mac-address'
                ;
            leaf mac-address {
              description 'MAC address.'
                          ;
              type ncd:mac-address ;
            }
            leaf vlan-id {
              description 'VLAN ID.'
                          ;
              type uint16 {
                range 1..4094 {
                  description 'VLAN ID must be in this range.'
                              ;
                }
              }
            }
            choice mac-type {
              description 'MAC type.'
                          ;
              mandatory true ;
              case permanent {
                description 'Permanent MAC.'
                            ;
                leaf flag {
                  description 'Multiflag of MAC address.'
                              ;
                  type enumeration {
                    enum permanent {
                      value 3 ;
                      description 'Permanent MAC.'
                                  ;
                    }
                  }
                  mandatory true ;
                }
                container outgoing {
                  description Outgoing. ;
                  choice ifornickname {
                    description 'Interface name or nickname.'
                                ;
                    mandatory true ;
                    case if {
                      description 'Interface name.'
                                  ;
                      leaf if-name {
                        description 'Interface name.'
                                    ;
                        type ncd:ifname {
                          length 1..31 {
                            description 'The length of interface name.'
                                        ;
                          }
                        }
                        mandatory true ;
                      }
                    }
                    case nickname {
                      description 'Nickname of TRILL MAC.'
                                  ;
                      leaf nickname {
                        description 'Nickname of TRILL MAC.'
                                    ;
                        type uint16 {
                          range 1..65471 {
                            description 'Nickname must be in this range.'
                                        ;
                          }
                        }
                        mandatory true ;
                      }
                    }
                  }
                }
              }
              case filter {
                description 'Filter MAC.'
                            ;
                leaf filter-flag {
                  description 'Multiflag of MAC address.'
                              ;
                  type enumeration {
                    enum source-filter {
                      value 4 ;
                      description 'Source-filter MAC address.'
                                  ;
                    }
                    enum dst-filter {
                      value 5 ;
                      description 'Destination-filter MAC address.'
                                  ;
                    }
                    enum both-filter {
                      value 6 ;
                      description 'Both-filter MAC address.'
                                  ;
                    }
                  }
                  mandatory true ;
                }
              }
            }
          }
        }
        container mac-permanent-vxlan-mac-address-no-vlan {
          description 'Permanent VXLAN MAC address with no VLAN.'
                      ;
          status obsolete ;
          list permanent-vxlan-mac-address-no-vlan {
            description 'Permanent VXLAN MAC address with no VLAN.'
                        ;
            key 'mac-address vxlan-id'
                ;
            leaf mac-address {
              description 'MAC address.'
                          ;
              type ncd:mac-address ;
            }
            leaf vxlan-id {
              description 'VXLAN ID of MAC address.'
                          ;
              type uint32 {
                range 1..16777215 {
                  description 'VXLAN ID range.'
                              ;
                }
              }
            }
            leaf internal-vlan-id {
              description 'Internal VLAN ID.'
                          ;
              type uint16 {
                range 1..4094 {
                  description 'Internal VLAN ID range.'
                              ;
                }
              }
            }
            leaf vtep-name {
              description 'Vtep name of MAC address.'
                          ;
              status obsolete ;
              type ncd:ifname {
                length 1..31 {
                  description 'The length of interface name.'
                              ;
                }
              }
              mandatory true ;
            }
            leaf multiflag {
              description 'The type of MAC address.'
                          ;
              type enumeration {
                enum permanent {
                  value 3 ;
                  description 'Permanent MAC.'
                              ;
                }
              }
              mandatory true ;
            }
            container ip-of-vxlan-mac-address-no-vlan {
              description 'Remote IP address of MAC address.'
                          ;
              status obsolete ;
              choice remote-ip {
                description 'Remote IP address of MAC address.'
                            ;
                mandatory true ;
                case ipv4 {
                  description 'IPv4 address .'
                              ;
                  leaf ipv4-address {
                    description 'Remote IPv4 address.'
                                ;
                    type ncd:ipv4-address ;
                    mandatory true ;
                  }
                }
                case ipv6 {
                  description 'IPv6 address.'
                              ;
                  leaf ipv6-address {
                    description 'Remote IPv6 address.'
                                ;
                    type ncd:ipv6-address ;
                    mandatory true ;
                  }
                }
              }
            }
            container vxlan-mac-outgoing {
              description 'Outgoing of MAC address.'
                          ;
              choice outgoing {
                description 'Outgoing of MAC address.'
                            ;
                mandatory true ;
                case local-if-name {
                  description 'Local interface name of MAC address.'
                              ;
                  leaf local-if-name {
                    description 'Local interface name of MAC address.'
                                ;
                    type ncd:ifname {
                      length 1..31 {
                        description 'The length of interface name.'
                                    ;
                      }
                    }
                    mandatory true ;
                  }
                }
                case vtep-name {
                  description 'Vtep name of MAC address.'
                              ;
                  leaf vtep-name {
                    description 'Vtep name of MAC address.'
                                ;
                    type ncd:ifname {
                      length 1..31 {
                        description 'The length of interface name.'
                                    ;
                      }
                    }
                    mandatory true ;
                  }
                  container ip-of-vxlan-mac-address-no-vlan {
                    description 'Remote IP address of MAC address.'
                                ;
                    choice remote-ip {
                      description 'Remote IP address of MAC address.'
                                  ;
                      mandatory true ;
                      case ipv4 {
                        description 'IPv4 address.'
                                    ;
                        leaf ipv4-address {
                          description 'Remote IPv4 address.'
                                      ;
                          type ncd:ipv4-address ;
                          mandatory true ;
                        }
                      }
                      case ipv6 {
                        description 'IPv6 address.'
                                    ;
                        leaf ipv6-address {
                          description 'Remote IPv6 address.'
                                      ;
                          type ncd:ipv6-address ;
                          mandatory true ;
                        }
                      }
                    }
                  }
                }
              }
            }
          }
        }
        container mac-permanent-vxlan-mac-address-vlan {
          description 'Permanent VXLAN MAC address with VLAN.'
                      ;
          status obsolete ;
          list permanent-vxlan-mac-address-vlan {
            description 'Permanent VXLAN MAC address with VLAN.'
                        ;
            key 'mac-address vlan-id vxlan-id'
                ;
            leaf mac-address {
              description 'MAC address.'
                          ;
              type ncd:mac-address ;
            }
            leaf vlan-id {
              description 'VLAN ID of MAC address.'
                          ;
              type uint16 {
                range 1..4094 {
                  description 'VLAN ID must be in this range.'
                              ;
                }
              }
            }
            leaf vxlan-id {
              description 'VXLAN ID of MAC address.'
                          ;
              type uint32 {
                range 1..16777215 {
                  description 'VXLAN ID range.'
                              ;
                }
              }
            }
            leaf multiflag {
              description 'The type of MAC address.'
                          ;
              type enumeration {
                enum permanent {
                  value 3 ;
                  description 'Permanent MAC.'
                              ;
                }
              }
              mandatory true ;
            }
            container vxlan-mac-outgoing {
              description 'Outgoing of MAC address.'
                          ;
              choice outgoing {
                description 'Outgoing of MAC address.'
                            ;
                mandatory true ;
                case local-if-name {
                  description 'Local interface name of MAC address.'
                              ;
                  leaf local-if-name {
                    description 'Local interface name of MAC address.'
                                ;
                    type ncd:ifname {
                      length 1..31 {
                        description 'The length of interface name.'
                                    ;
                      }
                    }
                    mandatory true ;
                  }
                }
                case vtep-name {
                  description 'Vtep name of MAC address.'
                              ;
                  leaf vtep-name {
                    description 'Vtep name of MAC address.'
                                ;
                    type ncd:ifname {
                      length 1..31 {
                        description 'The length of interface name.'
                                    ;
                      }
                    }
                    mandatory true ;
                  }
                  container ip-of-vxlan-mac-address-vlan {
                    description 'Remote IP address of MAC address..'
                                ;
                    choice remote-ip {
                      description 'Remote IP address of MAC address.'
                                  ;
                      mandatory true ;
                      case ipv4 {
                        description 'IPv4 address.'
                                    ;
                        leaf ipv4-address {
                          description 'Remote IPv4 address.'
                                      ;
                          type ncd:ipv4-address ;
                          mandatory true ;
                        }
                      }
                      case ipv6 {
                        description 'IPv6 address.'
                                    ;
                        leaf ipv6-address {
                          description 'Remote IPv6 address.'
                                      ;
                          type ncd:ipv6-address ;
                          mandatory true ;
                        }
                      }
                    }
                  }
                }
              }
            }
          }
        }
        container mac-permanent-vxlan-mac-address {
          description 'Permanent MAC address with VXLAN.'
                      ;
          status obsolete ;
          list permanent-vxlan-mac-address {
            description 'Permanent MAC address with VXLAN.'
                        ;
            status obsolete ;
            key 'mac-address vlan-id'
                ;
            leaf mac-address {
              description 'MAC address.'
                          ;
              type ncd:mac-address ;
            }
            leaf vlan-id {
              description 'VLAN ID.'
                          ;
              type uint16 {
                range 1..4094 {
                  description 'VLAN ID must be in this range.'
                              ;
                }
              }
            }
            leaf if-name {
              description 'Interface name.'
                          ;
              type ncd:ifname {
                length 1..31 {
                  description 'The length of interface name.'
                              ;
                }
              }
              mandatory true ;
            }
            leaf multiflag {
              description 'The type of MAC address.'
                          ;
              type enumeration {
                enum permanent {
                  value 3 ;
                  description 'Permanent MAC.'
                              ;
                }
              }
              mandatory true ;
            }
            choice remote-ip {
              description 'Remote IP address.'
                          ;
              mandatory true ;
              case ipv4 {
                description 'IPv4 address.'
                            ;
                leaf ipv4-address {
                  description 'Remote IPv4 address.'
                              ;
                  type ncd:ipv4-address ;
                  mandatory true ;
                }
              }
              case ipv6 {
                description 'IPv6 address.'
                            ;
                leaf ipv6-address {
                  description 'Remote IPv6 address.'
                              ;
                  type ncd:ipv6-address ;
                  mandatory true ;
                }
              }
            }
            leaf vxlan-id {
              description 'VXLAN ID.'
                          ;
              type uint32 {
                range 1..16777215 {
                  description 'VXLAN ID range.'
                              ;
                }
              }
              mandatory true ;
            }
          }
        }
      }
      container global-config {
        description 'MAC global configuration.'
                    ;
        leaf learn-enable {
          description 'Global MAC learn configuration.'
                      ;
          type enumeration {
            enum disable {
              value 0 ;
              description 'Disable MAC learn.'
                          ;
            }
            enum enable {
              value 1 ;
              description 'Enable MAC learn.'
                          ;
            }
          }
          default enable ;
        }
        leaf max-mac-num {
          description 'Maximum MAC entries.'
                      ;
          type uint32 {
            range 1..4294967295 {
              description 'Minimum is 1. Maximum and default is defined by perf'
                        + 'ormance parameter.'
                          ;
            }
          }
        }
        leaf higig-learn {
          description 'Higig learn configuration.'
                      ;
          type enumeration {
            enum disable {
              value 0 ;
              description 'Disable higig learn.'
                          ;
            }
            enum enable {
              value 1 ;
              description 'Enable higig learn.'
                          ;
            }
          }
          default enable ;
        }
        leaf aging-time {
          description 'MAC aging time.'
                      ;
          type uint32 {
            range '0 | 60..65535'
                  {
              description 'Unit:Second.0:disable aging.Minimum is 60 seconds. M'
                        + 'aximum and default is defined by performance paramet'
                        + 'er.'
                          ;
            }
          }
          units second ;
        }
        leaf alarm-threshold {
          description 'When the percent of learned MAC exceed the configuration'
                    + ', alarm.'
                      ;
          type uint8 {
            range 1..100 {
              description Percent. ;
            }
          }
          units percent ;
          default 80 ;
        }
        leaf default-priority-movable {
          description 'The switch of MAC movable in default priority.'
                      ;
          type enumeration {
            enum enable {
              value 0 ;
              description 'Can move.'
                          ;
            }
            enum disable {
              value 1 ;
              description 'Can not move.'
                          ;
            }
          }
          default enable ;
        }
        leaf lower-priority-movable {
          description 'The switch of MAC movable in lower priority.'
                      ;
          type enumeration {
            enum enable {
              value 0 ;
              description 'Can move.'
                          ;
            }
            enum disable {
              value 1 ;
              description 'Can not move.'
                          ;
            }
          }
          default enable ;
        }
        leaf normal-priority-movable {
          description 'The switch of MAC movable in normal priority.'
                      ;
          type enumeration {
            enum enable {
              value 0 ;
              description 'Can move.'
                          ;
            }
            enum disable {
              value 1 ;
              description 'Can not move.'
                          ;
            }
          }
          default enable ;
        }
        leaf higher-priority-movable {
          description 'The switch of MAC movable in higher priority.'
                      ;
          type enumeration {
            enum enable {
              value 0 ;
              description 'Can move.'
                          ;
            }
            enum disable {
              value 1 ;
              description 'Can not move.'
                          ;
            }
          }
          default enable ;
        }
        leaf exceed-limit-action {
          description 'The action when MAC entries is exceeding the maximum.'
                      ;
          type enumeration {
            enum forward {
              value 0 ;
              description Forward. ;
            }
            enum drop {
              value 1 ;
              description Drop. ;
            }
          }
          default forward ;
        }
        leaf safe-mode-policy {
          description 'Safe mode policy.'
                      ;
          type enumeration {
            enum disable {
              value 0 ;
              description 'Disable the policy.'
                          ;
            }
            enum enable-alarm {
              value 1 ;
              description 'Alarm when the MAC move is illegal.'
                          ;
            }
            enum enable-block {
              value 2 ;
              description 'Block the interface when the MAC move is illegal.'
                          ;
            }
            enum enable-shutdown {
              value 3 ;
              description 'Shutdown the interface when the MAC move is illegal.'
                          ;
            }
            enum enable-no-alarm {
              value 4 ;
              description 'Not alarm when the MAC move is illegal.'
                          ;
            }
          }
          default disable ;
        }
        leaf auto-write-topermanent {
          description 'Configuration of auto writing topermaent MAC to file.'
                      ;
          type enumeration {
            enum disable {
              value 0 ;
              description 'Do not auto write.'
                          ;
            }
            enum enable {
              value 1 ;
              description 'Auto write.'
                          ;
            }
          }
          default disable ;
        }
        leaf auto-write-topermanent-interval {
          description 'Interval of auto writing topermaent MAC.'
                      ;
          type uint32 {
            range 1..14400 {
              description '1-14400 minutes.'
                          ;
            }
          }
          units minute ;
          default 1440 ;
        }
        leaf forbidden-mac-reaction {
          description 'Reaction when learned forbidden MAC.'
                      ;
          type enumeration {
            enum no-alarm {
              value 0 ;
              description 'NO alarm.'
                          ;
            }
            enum alarm {
              value 1 ;
              description Alarm. ;
            }
          }
          default no-alarm ;
        }
        leaf learn-disable-action {
          description 'Action when leaning MAC is disabled.'
                      ;
          type enumeration {
            enum forward {
              value 0 ;
              description Forward. ;
            }
            enum drop {
              value 1 ;
              description Drop. ;
            }
          }
          default forward ;
        }
        leaf mac-update-notify {
          description 'Notify switch of MAC update.'
                      ;
          type enumeration {
            enum disable {
              value 0 ;
              description 'Disable notify.'
                          ;
            }
            enum enable {
              value 1 ;
              description 'Enable notify.'
                          ;
            }
          }
          default disable ;
        }
        leaf mac-notify-interval {
          description 'Interval of notify.'
                      ;
          type uint32 {
            range 5..86400 {
              description '5-86400 seconds.'
                          ;
            }
          }
          units second ;
          default 300 ;
        }
        leaf notify-max-mac-num {
          description 'Maximum notified MAC count.'
                      ;
          type uint32 {
            range 1..300 {
              description 'Maximum count must be in this range.'
                          ;
            }
          }
          default 50 ;
        }
      }
      container port-config {
        description 'MAC interface configuration.'
                    ;
        list mac-port-config {
          description 'MAC interface configuration.'
                      ;
          key if-name ;
          leaf if-name {
            description 'Interface name.'
                        ;
            type ncd:ifname {
              length 1..31 {
                description 'The length of interface name.'
                            ;
              }
            }
          }
          leaf learn-enable {
            description 'MAC learn switch.'
                        ;
            type enumeration {
              enum disable {
                value 0 ;
                description 'Disable MAC learn.'
                            ;
              }
              enum enable {
                value 1 ;
                description 'Enable MAC learn.'
                            ;
              }
            }
            default enable ;
          }
          leaf max-mac-num {
            description 'Maximum MAC entries.'
                        ;
            type uint32 {
              range 1..4294967295 {
                description 'Minimum is 1. Maximum and default is defined by pe'
                          + 'rformance parameter.'
                            ;
              }
            }
          }
          leaf learn-priority {
            description 'Interface learn priority.'
                        ;
            type enumeration {
              enum default {
                value 0 ;
                description 'Default priority.'
                            ;
              }
              enum lower {
                value 1 ;
                description 'Lower priority.'
                            ;
              }
              enum normal {
                value 2 ;
                description 'Normal priority.'
                            ;
              }
              enum higher {
                value 3 ;
                description 'Higher priority.'
                            ;
              }
            }
            default default ;
          }
          leaf exceed-limit-action {
            description 'The action when MAC entries is exceeding the maximum.'
                        ;
            type enumeration {
              enum forward {
                value 0 ;
                description Forward. ;
              }
              enum drop {
                value 1 ;
                description Drop. ;
              }
              enum shutdown {
                value 2 ;
                description 'Shutdown interface.'
                            ;
              }
            }
            default forward ;
          }
          leaf safe-mode-policy {
            description 'Safe mode policy.'
                        ;
            type enumeration {
              enum disable {
                value 0 ;
                description 'Disable the policy.'
                            ;
              }
              enum enable-alarm {
                value 1 ;
                description 'Alarm when the MAC move is illegal.'
                            ;
              }
              enum enable-block {
                value 2 ;
                description 'Block the interface when the MAC move is illegal.'
                            ;
              }
              enum enable-shutdown {
                value 3 ;
                description 'Shutdown the interface when the MAC move is illega'
                          + 'l.'
                            ;
              }
              enum enable-no-alarm {
                value 4 ;
                description 'Not alarm when the MAC move is illegal.'
                            ;
              }
            }
            default disable ;
          }
          leaf to-permanent-enable {
            description 'Whether dynamic MAC can turn into permanent.'
                        ;
            type enumeration {
              enum disable {
                value 0 ;
                description 'Disable change.'
                            ;
              }
              enum enable {
                value 1 ;
                description 'Enable change.'
                            ;
              }
            }
            default disable ;
          }
          leaf learn-disable-action {
            description 'Action when leaning MAC is disabled.'
                        ;
            type enumeration {
              enum forward {
                value 0 ;
                description Forward. ;
              }
              enum drop {
                value 1 ;
                description Drop. ;
              }
            }
            default forward ;
          }
          leaf mac-update-notify {
            description 'Notify switch of MAC update.'
                        ;
            type enumeration {
              enum disable {
                value 0 ;
                description 'Disable notify.'
                            ;
              }
              enum enable {
                value 1 ;
                description 'Enable notify.'
                            ;
              }
            }
            default disable ;
          }
          leaf dampening-policy {
            description 'Dampening policy when MAC moves.'
                        ;
            type enumeration {
              enum none {
                value 0 ;
                description 'No policy.'
                            ;
              }
              enum shutdown {
                value 1 ;
                description 'Shutdown policy.'
                            ;
              }
            }
            default none ;
          }
          leaf dampening-timeout {
            description 'Dampening timeout when MAC moves.'
                        ;
            type uint32 {
              range 0..300 {
                description '0-300 senconds, 0 means infinite.'
                            ;
              }
            }
            units second ;
            default 60 ;
          }
        }
      }
      container vlan-config {
        description 'MAC VLAN configuration.'
                    ;
        list mac-vlan-config {
          description 'MAC VLAN configuration.'
                      ;
          key vlan-id ;
          leaf vlan-id {
            description 'VLAN ID.'
                        ;
            type uint16 {
              range 1..4094 {
                description 'VLAN ID must be in this range.'
                            ;
              }
            }
          }
          leaf learn-enable {
            description 'MAC learn configuration.'
                        ;
            type enumeration {
              enum disable {
                value 0 ;
                description 'Disable MAC learn.'
                            ;
              }
              enum enable {
                value 1 ;
                description 'Enable MAC learn.'
                            ;
              }
            }
            default enable ;
          }
          leaf max-mac-num {
            description 'Maximum MAC entries.'
                        ;
            type uint32 {
              range 1..4294967295 {
                description 'Minimum is 1. Maximum and default is defined by pe'
                          + 'rformance parameter.'
                            ;
              }
            }
          }
          leaf exceed-limit-action {
            description 'The action when MAC entries is exceeding the maximum.'
                        ;
            type enumeration {
              enum forward {
                value 0 ;
                description Forward. ;
              }
              enum drop {
                value 1 ;
                description Drop. ;
              }
            }
            default forward ;
          }
          leaf learn-disable-action {
            description 'Action when leaning MAC is disabled.'
                        ;
            type enumeration {
              enum forward {
                value 0 ;
                description Forward. ;
              }
              enum drop {
                value 1 ;
                description Drop. ;
              }
            }
            default forward ;
          }
        }
      }
      container forbidden-mac {
        description 'Forbidden MAC configuration.'
                    ;
        list mac-forbidden-mac {
          description 'Forbidden MAC configuration.'
                      ;
          key session-id ;
          leaf session-id {
            description 'Session ID.'
                        ;
            type uint32 {
              range 1..256 {
                description 'Session ID must be in this range.'
                            ;
              }
            }
          }
          leaf mac-address {
            description 'MAC address.'
                        ;
            type ncd:mac-address ;
            mandatory true ;
          }
        }
      }
      container forbidden-bind-port {
        description 'Forbidden interface of learning MAC.'
                    ;
        list mac-forbidden-bind-port {
          description 'Forbidden interface of learning MAC.'
                      ;
          key 'if-name session-id'
              ;
          leaf if-name {
            description 'Interface name.'
                        ;
            type ncd:ifname {
              length 1..31 {
                description 'The length of interface name.'
                            ;
              }
            }
          }
          leaf session-id {
            description 'Session ID.'
                        ;
            type uint32 {
              range 1..256 {
                description 'Session ID must be in this range.'
                            ;
              }
            }
          }
        }
      }
    }
  }
  container operation {
    description 'Operation of MAC.'
                ;
    config false ;
    container mac {
      description 'Operation of MAC.'
                  ;
      container delete-vpls-dynamic-macs {
        description 'Delete VPLS dynamic MAC entries.'
                    ;
        list delete-vpls-dynamic-mac {
          description 'Delete VPLS dynamic MAC entries.'
                      ;
          key instace-name ;
          leaf instace-name {
            description 'VPLS instance name.'
                        ;
            type string {
              length 1..32 {
                description 'The length of VPLS instance name.'
                            ;
              }
            }
          }
          leaf vlan-id {
            description 'VLAN ID.'
                        ;
            type uint16 {
              range 1..4094 {
                description 'VLAN ID.'
                            ;
              }
            }
          }
          leaf mac-address {
            description 'MAC address.'
                        ;
            type ncd:mac-address ;
          }
          leaf if-name {
            description 'Interface name.'
                        ;
            type ncd:ifname {
              length 1..31 {
                description 'The length of interface name.'
                            ;
              }
            }
          }
        }
      }
      container to-statics {
        description 'To-static dynamic MAC address.'
                    ;
        list to-static {
          description 'To-static dynamic MAC address.'
                      ;
          key to-static-flag ;
          leaf to-static-flag {
            description 'To-static flag.'
                        ;
            type enumeration {
              enum enable {
                value 7 ;
                description 'To-static MAC item.'
                            ;
              }
              enum disable {
                value 8 ;
                description 'No to-static MAC item.'
                            ;
              }
            }
          }
          leaf if-name {
            description 'Interface name.'
                        ;
            type ncd:ifname {
              length 1..31 {
                description 'The length of interface name.'
                            ;
              }
            }
          }
          leaf mac-address {
            description 'MAC address.'
                        ;
            type ncd:mac-address ;
          }
        }
      }
      container delete-normal-no-config-mac {
        description 'Delete no-config MAC entries.'
                    ;
        leaf if-name {
          description 'Interface name.'
                      ;
          type ncd:ifname {
            length 1..31 {
              description 'The length of interface name.'
                          ;
            }
          }
        }
        leaf vlan-id {
          description 'VLAN ID.'
                      ;
          type uint16 {
            range 1..4094 {
              description 'VLAN ID must be in this range.'
                          ;
            }
          }
        }
        leaf mac-address {
          description 'MAC address.'
                      ;
          type ncd:mac-address ;
        }
        leaf nickname {
          description 'Nickname of TRILL MAC.'
                      ;
          type uint16 {
            range 1..65471 {
              description 'Nickname must be in this range.'
                          ;
            }
          }
        }
      }
      container delete-vxlan-no-config-mac {
        description 'Delete no-config VXLAN MAC.'
                    ;
        status obsolete ;
        leaf mac-address {
          description 'MAC address.'
                      ;
          type ncd:mac-address ;
        }
        leaf vlan-id {
          description 'VLAN ID.'
                      ;
          status obsolete ;
          type uint16 {
            range 1..4094 {
              description 'VLAN ID must be in this range.'
                          ;
            }
          }
        }
        leaf if-name {
          description 'Interface name.'
                      ;
          type ncd:ifname {
            length 1..31 {
              description 'The length of interface name.'
                          ;
            }
          }
        }
        leaf vxlan-id {
          description 'VXLAN ID.'
                      ;
          type uint32 {
            range 1..16777215 {
              description 'VXLAN ID range.'
                          ;
            }
          }
        }
      }
      container learn-priority-policy {
        description 'Set policies of learn priority.'
                    ;
        presence learn-priority-policy ;
        leaf if-name {
          description 'Interface name.'
                      ;
          type ncd:ifname {
            length 1..31 {
              description 'The length of interface name.'
                          ;
            }
          }
          mandatory true ;
        }
        leaf no-shutdown {
          description 'Bring the interface to up.'
                      ;
          type empty ;
          mandatory true ;
        }
      }
    }
  }
}
