/*
Copyright (C) 2020 Huawei Technologies Co., Ltd. All rights reserved.
*/
module huawei-mplsoam-fwd-notif {
  yang-version 1;
  namespace "urn:huawei:yang:huawei-mplsoam-fwd-notif";
  prefix mplsoam-fwd-notif;
  import ietf-inet-types {
    prefix inet;
  }
  import huawei-l2vpn {
    prefix l2vpn;
  }
  import huawei-extension {
    prefix ext;
  }
  organization
    "Huawei Technologies Co., Ltd.";
  contact
    "Huawei Industrial Base
    Bantian, Longgang
    Shenzhen 518129
    People's Republic of China
    Website: http://www.huawei.com
    Email: support@huawei.com";
  description
    "Notification of MPLS OAM.";
  revision 2020-04-10 {
    description
      "Initial revision.";
    reference
      "Huawei private.";
  }
  
  ext:task-name "tpoam";
  
  notification oam-tunnel-not-support {
    description
      "MPLS OAM for PW does not support the current public tunnel.";
    leaf vc-id {
      type uint32;
      description
        "Identifier of the layer 2 virtual circuit.";
    }
    leaf vc-type {
      type l2vpn:encapsulation-type;
      description
        "Encapsulation type of a L2VPN instance.";
    }
    leaf peer-addr {
      type inet:ipv4-address-no-zone;
      description
        "Peer IP address.";
    }
  }
  notification oam-tunnel-not-support-resume {
    description
      "The alarm that MPLS OAM for PW does not support the current public tunnel is resumed.";
    leaf vc-id {
      type uint32;
      description
        "Identifier of the layer 2 virtual circuit.";
    }
    leaf vc-type {
      type l2vpn:encapsulation-type;
      description
        "Encapsulation type of a L2VPN instance.";
    }
    leaf peer-addr {
      type inet:ipv4-address-no-zone;
      description
        "Peer IP address.";
    }
  }
}
