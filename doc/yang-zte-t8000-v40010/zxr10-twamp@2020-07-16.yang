module zxr10-twamp {
  namespace 'http://www.zte.com.cn/zxr10/netconf/schema/rosng/twamp'
            ;
  prefix twamp ;
  yang-version 1 ;
  import zxr10-netconf-defs {
    prefix ncd ;
    revision-date 2015-11-09 ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2020-07-16 {
    description '1.Obsolete twamp:state/twamp/twamp-result.'+"\n"
              + '2.Add twamp:state/twamp/twamp-results/twamp-result.'
                ;
  }
  revision 2020-03-11 {
    description '1.Add choice configuration/twamp/connections/connection/ip-add'
              + 'r-family.'+"\n"
              + '2.Change the location of configuration/twamp/connections/conne'
              + 'ction/client-ip.'+"\n"
              + '3.Add node configuration/twamp/connections/connection/server-i'
              + 'pv6.'+"\n"
              + '4.Add node configuration/twamp/connections/connection/client-i'
              + 'pv6.'+"\n"
              + '5.Add choice configuration/twamp/connetcions/connection/sessio'
              + 'ns/session/ip-addr-family.'+"\n"
              + '6.Change the location of configuration/twamp/connetcions/conne'
              + 'ction/sessions/session/receiver-ip'+"\n"
              + '7.Add node configuration/twamp/connetcions/connection/sessions'
              + '/session/sender-ipv6.'+"\n"
              + '8.Add node configuration/twamp/connetcions/connection/sessions'
              + '/session/receiver-ipv6.'+"\n"
              + '9.Add list configuration/twamp/server/client-lists/client-list'
              + '-ipv6.'
                ;
  }
  revision 2019-11-26 {
    description 'Add node configuration/twamp/connections/connection/client-ip.'
                ;
  }
  revision 2019-06-04 {
    description '1. Add state/twamp-result.'
                ;
  }
  revision 2019-05-21 {
    description '1.Add feature delay-statistics-mode.'+"\n"
              + '2.Add configuration/twamp/connetcions/connection/sessions/sess'
              + 'ion/delay-statistics-mode.'
                ;
  }
  revision 2019-04-02 {
    description '1 Modify the upper limit for configuration/twamp/connetcions/c'
              + 'onnection/sessions/session/padding-length which depends on the'
              + ' device.'
                ;
  }
  revision 2019-01-08 {
    description '1.Modify description for configuration/twamp/connetcions/conne'
              + 'ction/sessions/session/sender-port.'+"\n"
              + '2.Modify description for configuration/twamp/connetcions/conne'
              + 'ction/sessions/session/receiver-port.'
                ;
  }
  revision 2018-01-18 {
    description '1.Modify description for twamp-event/twamp-result/connection-i'
              + 'd.'+"\n"
              + '2.Modify description for twamp-event/twamp-result/session-id.'+"\n"
              + '3.Modify description for configuration/twamp/connetcions/conne'
              + 'ction/connection-id.'+"\n"
              + '4.Modify description for configuration/twamp/connetcions/conne'
              + 'ction/sessions/session/session-id.'+"\n"
              + '5.Modify description for operation/twamp/operations/operation/'
              + 'connection-id.'
                ;
  }
  revision 2017-11-30 {
    description 'Add node configuration/twamp/connections/connection/timestamp-'
              + 'format.'
                ;
  }
  revision 2017-02-08 {
    description '1.Modify range for configuration/twamp/server/port.'+"\n"
              + '2.Modify description for configuration/twamp/connections/conne'
              + 'ction/server-port.'+"\n"
              + '3.Modify description for configuration/twamp/server/ignore-vrf'
              + '.'+"\n"
              + '4.Modify description for configuration/twamp/connections/conne'
              + 'ction/sessions/session/sender-port.'
                ;
  }
  revision 2016-09-27 {
    description 'Initial version.'
                ;
  }
  feature ignore-vrf {
    description 'The ignore-vrf status.'
                ;
  }
  feature statistics-interval {
    description 'The statistics interval.'
                ;
  }
  feature send-fast-packet {
    description 'Session send fast test packet.'
                ;
  }
  feature timestamp-format {
    description 'Timestamp format,including PTP and NTP(default:PTP).'
                ;
  }
  feature delay-statistics-mode {
    description 'The delay statistics mode,including bidirection,unidirection a'
              + 'nd both(default:both).'
                ;
  }
  typedef status {
    type enumeration {
      enum enable {
        value 1 ;
        description 'The status is enable.'
                    ;
      }
      enum disable {
        value 0 ;
        description 'The status is disable.'
                    ;
      }
    }
    default disable ;
    description 'The configuration of status,including enable and disable(defau'
              + 'lt:disable).'
                ;
  }
  typedef detecPathType {
    type enumeration {
      enum down {
        value 1 ;
        description 'Down side detect.'
                    ;
      }
      enum up {
        value 2 ;
        description 'Up side detect.'
                    ;
      }
    }
    default down ;
    description 'Detect path type,including down and up(default:down).'
                ;
  }
  container configuration {
    description 'Configuration model information.'
                ;
    container twamp {
      description 'TWAMP configuration.'
                  ;
      container connections {
        description 'Configure TWAMP connection.'
                    ;
        list connection {
          description 'Configure TWAMP connection.'
                      ;
          key connection-id ;
          leaf connection-id {
            description 'The connection ID,the upper limit of this parameter de'
                      + 'pend on the device.'
                        ;
            type uint32 {
              range 1..65535 {
                description 'The value of this parameter ranges from 1 to 65535.'
                            ;
              }
            }
          }
          choice ip-addr-family {
            description 'IP address family.'
                        ;
            mandatory true ;
            case ipv4 {
              description 'IPv4 address.'
                          ;
              leaf server-ip {
                description 'The server IPv4 address.'
                            ;
                type ncd:ipv4-address-none-zero ;
                mandatory true ;
              }
              leaf client-ip {
                description 'The client IPv4 address.'
                            ;
                type ncd:ipv4-address-none-zero ;
              }
            }
            case ipv6 {
              description 'IPv6 address.'
                          ;
              leaf server-ipv6 {
                description 'The server IPv6 address.'
                            ;
                type ncd:ipv6-address ;
                mandatory true ;
              }
              leaf client-ipv6 {
                description 'The client IPv6 address.'
                            ;
                type ncd:ipv6-address ;
              }
              ncd:revise-date 2020-03-11 ;
            }
          }
          leaf server-port {
            description 'The port number of server,ranges from 1025 to 65535,or'
                      + ' 862.'
                        ;
            type uint16 {
              range '862 | 1025..65535'
                    {
                description 'The value of this parameter ranges from 1025 to 65'
                          + '535,or 862(default:862).'
                            ;
              }
            }
            mandatory true ;
          }
          leaf vrf-name {
            description 'The VRF name,the length of this string is from 1 to 32.'
                        ;
            type string {
              length 1..32 {
                description 'The length of this string is from 1 to 32'
                            ;
              }
            }
          }
          leaf retry-count {
            description 'The connection retry count,ranges from 0 to 16(default'
                      + ':10).'
                        ;
            type uint16 {
              range 0..16 {
                description 'The value of this parameter ranges from 0 to 16(de'
                          + 'fault:10).'
                            ;
              }
            }
            default 10 ;
          }
          leaf retry-interval {
            description 'The connection retry interval,ranges from 10s to 900s('
                      + 'default:30s).'
                        ;
            type uint16 {
              range 10..900 {
                description 'The value of this parameter ranges from 10s to 900'
                          + 's(default:30s).'
                            ;
              }
            }
            units s ;
            default 30 ;
          }
          leaf timestamp-format {
            if-feature timestamp-format ;
            description 'Timestamp format,including PTP and NTP(default:NTP).'
                        ;
            type enumeration {
              enum ptp {
                value 1 ;
                description 'PTP format.'
                            ;
              }
              enum ntp {
                value 2 ;
                description 'NTP format.'
                            ;
              }
            }
            default ntp ;
            ncd:revise-date 2017-11-30 ;
          }
          container sessions {
            description 'Configure TWAMP session.'
                        ;
            list session {
              description 'Configure TWAMP session.'
                          ;
              key session-id ;
              leaf session-id {
                description 'The session ID,the upper limit of this parameter d'
                          + 'epend on the device.'
                            ;
                type uint16 {
                  range 1..65535 {
                    description 'The value of this parameter ranges from 1 to 6'
                              + '5535.'
                                ;
                  }
                }
              }
              choice ip-addr-family {
                description 'IP address family.'
                            ;
                mandatory true ;
                case ipv4 {
                  description 'IPv4 address.'
                              ;
                  leaf sender-ip {
                    description 'The sender IPv4 address.'
                                ;
                    type ncd:ipv4-address-none-zero ;
                    mandatory true ;
                  }
                  leaf receiver-ip {
                    description 'The receiver IPv4 address.'
                                ;
                    type ncd:ipv4-address-none-zero ;
                    mandatory true ;
                  }
                }
                case ipv6 {
                  description 'IPv6 address.'
                              ;
                  leaf sender-ipv6 {
                    description 'The sender IPv6 address.'
                                ;
                    type ncd:ipv6-address ;
                    mandatory true ;
                  }
                  leaf receiver-ipv6 {
                    description 'The receiver IPv6 address.'
                                ;
                    type ncd:ipv6-address ;
                    mandatory true ;
                  }
                  ncd:revise-date 2020-03-11 ;
                }
              }
              leaf sender-port {
                description 'The port number of sender,ranges from 1025 to 6553'
                          + '5,or 862.'
                            ;
                type uint16 {
                  range '862 | 1025..65535'
                        {
                    description 'The value of this parameter ranges from 1025 t'
                              + 'o 65535,or 862. the upper limit of this parame'
                              + 'ter depend on the device.'
                                ;
                  }
                }
                mandatory true ;
              }
              leaf receiver-port {
                description 'The port number of receiver,ranges from 1025 to 65'
                          + '535,or 862.'
                            ;
                type uint16 {
                  range '862 | 1025..65535'
                        {
                    description 'The value of this parameter ranges from 1025 t'
                              + 'o 65535, or 862.'
                                ;
                  }
                }
                mandatory true ;
              }
              leaf inbound-interface {
                description 'Inbound interface.'
                            ;
                type ncd:ifname ;
              }
              leaf vrf-name {
                description 'The VRF name,the length of this string is from 1 t'
                          + 'o 32.'
                            ;
                type string {
                  length 1..32 {
                    description 'The length of this string is from 1 to 32.'
                                ;
                  }
                }
              }
              leaf detect-path {
                description 'Detect path type,including down and up(default:dow'
                          + 'n).'
                            ;
                type detecPathType ;
                default down ;
              }
              leaf dscp {
                description 'The DSCP value of packet,ranges from 0 to 63(defau'
                          + 'lt:0).'
                            ;
                type uint8 {
                  range 0..63 {
                    description 'The value of this parameter ranges from 0 to 6'
                              + '3(default:0).'
                                ;
                  }
                }
                default 0 ;
              }
              leaf padding-length {
                description 'The length of padding,the upper limit of this para'
                          + 'meter depends on the device.(default:27bytes).'
                            ;
                type uint16 {
                  range 27..65535 {
                    description 'The value of this parameter ranges from 27byte'
                              + 's to 65535bytes(default:27bytes),the upper lim'
                              + 'it of this parameter depend on the device.'
                                ;
                  }
                }
                units byte ;
                default 27 ;
              }
              leaf time-out {
                description 'Timeout ranges from 1s to 10s(default:5s).Within t'
                          + 'his time,the server needs to reflect the test mess'
                          + 'age, otherwise the message is discarded.'
                            ;
                type uint16 {
                  range 1..10 {
                    description 'The value of this parameter ranges from 1s to '
                              + '10s(default:5s).'
                                ;
                  }
                }
                units s ;
                default 5 ;
              }
              leaf report-interval {
                description 'If it is assigned, it will upsend the result in in'
                          + 'terval of configured value. Otherwise, it does not'
                          + ' upsend until it is stopped.'
                            ;
                type uint32 {
                  range 1..86400 {
                    description 'The value of this parameter ranges from 1s to '
                              + '86400s.'
                                ;
                  }
                }
                units s ;
              }
              container duration-mode {
                description 'Configure duration mode.'
                            ;
                choice duration-mode {
                  description 'Configure duration mode.'
                              ;
                  default continuous ;
                  case continuous {
                    description 'Continuous sending packet mode.In this mode,th'
                              + 'e test packets will always be sent until the u'
                              + 'ser stops.'
                                ;
                    leaf continuous {
                      description 'Continuous sending packet mode.In this mode,'
                                + 'the test packets will always be sent until t'
                                + 'he user stops.'
                                  ;
                      type empty ;
                    }
                  }
                  case packets {
                    description 'The mode of sending packet according to the nu'
                              + 'mber of configuration.In this mode,the test wi'
                              + 'll be stopped until the number of sending pack'
                              + 'et reaches the configured value.'
                                ;
                    leaf send-count {
                      description 'The number of sending packet,ranges from 1 t'
                                + 'o 65535.The test will be stopped until the n'
                                + 'umber of sending packet reaches the configur'
                                + 'ed value.'
                                  ;
                      type uint16 {
                        range 1..65535 {
                          description 'The value of this parameter ranges from '
                                    + '1 to 65535.'
                                      ;
                        }
                      }
                    }
                  }
                  case seconds {
                    description 'The mode of sending packet according to the co'
                              + 'nfiguration of time.In this mode,the test will'
                              + ' be stopped until the time of sending packet r'
                              + 'eaches the configured value.'
                                ;
                    leaf send-time {
                      description 'Sending time of packets,the value of this pa'
                                + 'rameter ranges from 60s to 86400s.The test w'
                                + 'ill be stopped until the time of sending pac'
                                + 'kets reaches the configured value.'
                                  ;
                      type uint32 {
                        range 60..86400 {
                          description 'The value of this parameter ranges from '
                                    + '60s to 86400s.'
                                      ;
                        }
                      }
                      units s ;
                    }
                  }
                }
              }
              container send-interval {
                description 'Configure sending interval.'
                            ;
                choice send-interval {
                  description 'Configure sending interval(default:1s).'
                              ;
                  default second ;
                  case second {
                    description Second. ;
                    leaf seconds {
                      description 'Packet sending interval,ranges from 1 to 60('
                                + 'default:1s).'
                                  ;
                      type uint16 {
                        range 1..60 ;
                      }
                      units s ;
                      default 1 ;
                    }
                  }
                  case millisecond {
                    if-feature send-fast-packet ;
                    description Millisecond. ;
                    leaf milliseconds {
                      description 'Packet sending interval,ranges from 1 to 100'
                                + '0.'
                                  ;
                      type uint16 {
                        range 1..1000 {
                          description 'Send interval.'
                                      ;
                        }
                      }
                      units ms ;
                    }
                  }
                  case microsecond {
                    if-feature send-fast-packet ;
                    description Microsecond. ;
                    leaf microseconds {
                      description 'Packet sending interval,ranges from 50 to 10'
                                + '00.'
                                  ;
                      type uint16 {
                        range 50..1000 {
                          description 'Send interval.'
                                      ;
                        }
                      }
                      units us ;
                    }
                  }
                }
              }
              leaf statistics-interval {
                description 'The statistics interval,ranges from 5s to 60s(defa'
                          + 'ult:15s).'
                            ;
                type uint16 {
                  range 5..60 {
                    description 'The statistics interval,ranges from 5s to 60s('
                              + 'default:15s).'
                                ;
                  }
                }
                units s ;
                default 15 ;
              }
              leaf delay-statistics-mode {
                if-feature delay-statistics-mode ;
                description 'The delay statistics mode,including bidirection,un'
                          + 'idirection and both(default:both).'
                            ;
                type enumeration {
                  enum bidirection {
                    value 1 ;
                    description 'The delay statistics mode is bidirection.'
                                ;
                  }
                  enum unidirection {
                    value 2 ;
                    description 'The delay statistics mode is unidirection.'
                                ;
                  }
                  enum both {
                    value 3 ;
                    description 'The delay statistics mode is both bidirection '
                              + 'and unidirection.'
                                ;
                  }
                }
                default both ;
                ncd:revise-date 2019-05-21 ;
              }
            }
          }
          container proactive-status {
            description 'The proactive status,including start and stop.'
                        ;
            leaf operation {
              description 'The proactive operation type,including start and sto'
                        + 'p.'
                          ;
              type enumeration {
                enum start {
                  value 3 ;
                  description 'Start all sessions.'
                              ;
                }
                enum stop {
                  value 4 ;
                  description 'Stop all sessions.'
                              ;
                }
              }
              default stop ;
            }
          }
        }
      }
      container server {
        description 'Configure TWAMP server.'
                    ;
        leaf server-status {
          description 'The status of TWAMP server,including enable and disable('
                    + 'default:disable).'
                      ;
          type status ;
          default disable ;
        }
        leaf inactivity-timeout {
          description 'Inactivity timeout,ranges from 10s to 1800s(default:900s'
                    + ').'
                      ;
          type uint32 {
            range 10..1800 {
              description 'The value of this parameter ranges from 10s to 1800s'
                        + '(default:900s).'
                          ;
            }
          }
          units s ;
          default 900 ;
        }
        leaf max-connection-duration {
          description 'The maximum duration of connection,ranges from 0h to 24h'
                    + '(default:0).If this node is assigned 0,it means permanen'
                    + 'ce connection unless stopped manually.If it is assigned '
                    + '1h to 24h,it means connection lasting time.'
                      ;
          type uint32 {
            range 0..24 {
              description 'The value of this parameter ranges from 0 to 24h(def'
                        + 'ault:0).'
                          ;
            }
          }
          units h ;
          default 0 ;
        }
        leaf max-connections {
          description 'The maximum number of connections,the minimum value of t'
                    + 'his parameter is 1,the maximum value of this parameter d'
                    + 'epends on the device(default:64).'
                      ;
          type uint32 {
            range 1..64 {
              description 'The min value of this parameter is 1,the upper limit'
                        + ' of this parameter depend on the device(default:64).'
                          ;
            }
          }
          default 64 ;
        }
        leaf max-sessions {
          description 'The maximum number of sessions,the minimum value of this'
                    + ' parameter is 1,the maximum value of this parameter depe'
                    + 'nds on the device(default:128).'
                      ;
          type uint32 {
            range 1..128 {
              description 'The min value of this parameter is 1,the upper limit'
                        + ' of this parameter depend on the device(default:128)'
                        + '.'
                          ;
            }
          }
          default 128 ;
        }
        leaf max-sessions-per-connection {
          description 'The maximum session number of every connection,the minim'
                    + 'um value of this parameter is 1,the maximum value of thi'
                    + 's parameter depends on the device(default:8).'
                      ;
          type uint32 {
            range 1..8 {
              description 'The min value of this parameter is 1,the upper limit'
                        + ' of this parameter depends on the device(default:8).'
                          ;
            }
          }
          default 8 ;
        }
        leaf port {
          description 'The port number of server,ranges from 1025 to 65535,or 8'
                    + '62(default:862).'
                      ;
          type uint16 {
            range '862 | 1025..65535'
                  {
              description 'The value of this parameter ranges from 1025 to 6553'
                        + '5,or 862(default:862).'
                          ;
            }
          }
          default 862 ;
        }
        leaf ignore-vrf {
          if-feature ignore-vrf ;
          description 'The ignore-vrf status,including enable and disable(defau'
                    + 'lt value depend on the device).'
                      ;
          type status ;
          default enable ;
        }
        container client-lists {
          description 'Configure client list.'
                      ;
          leaf list-status {
            description 'The status of client list,including enable and disable'
                      + '(default:disable).'
                        ;
            type status ;
            default disable ;
          }
          list client-list {
            description 'Client white list.'
                        ;
            key client-ipv4 ;
            leaf client-ipv4 {
              description 'IPv4 address of the white list.'
                          ;
              type ncd:ipv4-address-none-zero ;
            }
          }
          list client-list-ipv6 {
            description 'Client white list.'
                        ;
            key client-ipv6 ;
            leaf client-ipv6 {
              description 'IPv6 address of the white list.'
                          ;
              type ncd:ipv6-address ;
            }
            ncd:revise-date 2020-03-11 ;
          }
        }
      }
    }
  }
  container operation {
    config false ;
    description 'TWAMP operations model.'
                ;
    container twamp {
      description 'TWAMP operation model.'
                  ;
      container operations {
        description 'The operation for this test.'
                    ;
        list operation {
          description 'The operation for this test.'
                      ;
          key connection-id ;
          leaf connection-id {
            description 'The connection ID,the upper limit of this parameter de'
                      + 'pend on the device.'
                        ;
            type uint32 {
              range 1..65535 {
                description 'The value of this parameter ranges from 1 to 65535.'
                            ;
              }
            }
          }
          leaf operation {
            description 'The operation type,including start and stop.'
                        ;
            type enumeration {
              enum start {
                value 3 ;
                description 'Start all sessions.'
                            ;
              }
              enum stop {
                value 4 ;
                description 'Stop all sessions.'
                            ;
              }
            }
          }
        }
      }
    }
  }
  container state {
    config false ;
    container twamp {
      container twamp-result {
        status obsolete {
          ncd:revise-date 2020-07-16 ;
        }
        list twamp-result {
          description 'The test result of TWAMP.'
                      ;
          key 'connection-id session-id'
              ;
          leaf connection-id {
            description 'The connection ID,the upper limit of this parameter de'
                      + 'pend on the device.'
                        ;
            type uint32 {
              range 1..65535 {
                description 'The value of this parameter ranges from 1 to 65535.'
                            ;
              }
            }
          }
          leaf session-id {
            description 'The session ID,the upper limit of this parameter depen'
                      + 'd on the device.'
                        ;
            type uint16 {
              range 1..65535 {
                description 'The value of this parameter ranges from 1 to 65535.'
                            ;
              }
            }
          }
          leaf packet-send-number {
            description 'The count of sending packets.'
                        ;
            type uint32 {
              range 0..4294967295 {
                description 'The range of sending packet number.'
                            ;
              }
            }
          }
          leaf packet-receive-number {
            description 'The count of receiving packets.'
                        ;
            type uint32 {
              range 0..4294967295 {
                description 'The range of receiving packet number.'
                            ;
              }
            }
          }
          leaf packet-loss-number {
            description 'The count of lossing packets.'
                        ;
            type uint32 {
              range 0..4294967295 {
                description 'The range of packe lossing number.'
                            ;
              }
            }
          }
          leaf packet-loss-ratio {
            description 'The packet loss ratio,precision is 1/1000000.'
                        ;
            type uint32 {
              range 0..4294967295 {
                description 'The range of packet lossing ratio.'
                            ;
              }
            }
          }
          leaf two-way-time-delay {
            description 'Two way delay.'
                        ;
            type uint64 ;
            units ns ;
          }
          leaf two-way-min-delay {
            description 'The minimum of two way delay.'
                        ;
            type uint64 ;
            units ns ;
          }
          leaf two-way-max-delay {
            description 'The maximum of two way delay.'
                        ;
            type uint64 ;
            units ns ;
          }
          leaf two-way-avg-delay {
            description 'The average of two way delay.'
                        ;
            type uint64 ;
            units ns ;
          }
          leaf two-way-delay-jitter {
            description 'Delay jitter of two way packet .'
                        ;
            type uint64 ;
            units ns ;
          }
          leaf two-way-min-jitter {
            description 'The minimum delay jitter of two way packet .'
                        ;
            type uint64 ;
            units ns ;
          }
          leaf two-way-max-jitter {
            description 'The maximum delay jitter of two way packet .'
                        ;
            type uint64 ;
            units ns ;
          }
          leaf two-way-avg-jitter {
            description 'The average delay jitter of two way packet .'
                        ;
            type uint64 ;
            units ns ;
          }
          leaf forward-time-delay {
            description 'The forward packet delay.'
                        ;
            type uint64 ;
            units ns ;
          }
          leaf forward-min-delay {
            description 'The minimum of forward packet delay.'
                        ;
            type uint64 ;
            units ns ;
          }
          leaf forward-max-delay {
            description 'The maximum of forward packet delay.'
                        ;
            type uint64 ;
            units ns ;
          }
          leaf forward-avg-delay {
            description 'The average of forward packet delay.'
                        ;
            type uint64 ;
            units ns ;
          }
          leaf forward-delay-jitter {
            description 'Delay jitter of the forward packet.'
                        ;
            type uint64 ;
            units ns ;
          }
          leaf forward-min-jitter {
            description 'The minimum of delay jitter of the forward packet.'
                        ;
            type uint64 ;
            units ns ;
          }
          leaf forward-max-jitter {
            description 'The maximum of delay jitter of the forward packet.'
                        ;
            type uint64 ;
            units ns ;
          }
          leaf forward-avg-jitter {
            description 'The average of delay jitter of the forward packet.'
                        ;
            type uint64 ;
            units ns ;
          }
          leaf reverse-time-delay {
            description 'The reverse packet delay.'
                        ;
            type uint64 ;
            units ns ;
          }
          leaf reverse-min-delay {
            description 'The minimum of reverse packet delay.'
                        ;
            type uint64 ;
            units ns ;
          }
          leaf reverse-max-delay {
            description 'The maximum of reverse packet delay.'
                        ;
            type uint64 ;
            units ns ;
          }
          leaf reverse-avg-delay {
            description 'The average of reverse packet delay.'
                        ;
            type uint64 ;
            units ns ;
          }
          leaf reverse-delay-jitter {
            description 'The reverse packet delay jitter.'
                        ;
            type uint64 ;
            units ns ;
          }
          leaf reverse-min-jitter {
            description 'The minimum of delay jitter of the reverse packet.'
                        ;
            type uint64 ;
            units ns ;
          }
          leaf reverse-max-jitter {
            description 'The maximum of delay jitter of the reverse packet.'
                        ;
            type uint64 ;
            units ns ;
          }
          leaf reverse-avg-jitter {
            description 'The average of delay jitter of the reverse packet.'
                        ;
            type uint64 ;
            units ns ;
          }
        }
      }
      container twamp-results {
        list twamp-result {
          description 'The test result of TWAMP.'
                      ;
          key 'connection-id session-id'
              ;
          leaf connection-id {
            description 'The connection ID,the upper limit of this parameter de'
                      + 'pend on the device.'
                        ;
            type uint32 {
              range 1..65535 {
                description 'The value of this parameter ranges from 1 to 65535.'
                            ;
              }
            }
          }
          leaf session-id {
            description 'The session ID,the upper limit of this parameter depen'
                      + 'd on the device.'
                        ;
            type uint16 {
              range 1..65535 {
                description 'The value of this parameter ranges from 1 to 65535.'
                            ;
              }
            }
          }
          leaf packet-send-number {
            description 'The count of sending packets.'
                        ;
            type uint32 {
              range 0..4294967295 {
                description 'The range of sending packet number.'
                            ;
              }
            }
          }
          leaf packet-receive-number {
            description 'The count of receiving packets.'
                        ;
            type uint32 {
              range 0..4294967295 {
                description 'The range of receiving packet number.'
                            ;
              }
            }
          }
          leaf packet-loss-number {
            description 'The count of lossing packets.'
                        ;
            type uint32 {
              range 0..4294967295 {
                description 'The range of packe lossing number.'
                            ;
              }
            }
          }
          leaf packet-loss-ratio {
            description 'The packet loss ratio,precision is 1/1000000.'
                        ;
            type uint32 {
              range 0..4294967295 {
                description 'The range of packet lossing ratio.'
                            ;
              }
            }
          }
          leaf two-way-time-delay {
            description 'Two way delay.'
                        ;
            type uint64 ;
            units ns ;
          }
          leaf two-way-min-delay {
            description 'The minimum of two way delay.'
                        ;
            type uint64 ;
            units ns ;
          }
          leaf two-way-max-delay {
            description 'The maximum of two way delay.'
                        ;
            type uint64 ;
            units ns ;
          }
          leaf two-way-avg-delay {
            description 'The average of two way delay.'
                        ;
            type uint64 ;
            units ns ;
          }
          leaf two-way-delay-jitter {
            description 'Delay jitter of two way packet .'
                        ;
            type uint64 ;
            units ns ;
          }
          leaf two-way-min-jitter {
            description 'The minimum delay jitter of two way packet .'
                        ;
            type uint64 ;
            units ns ;
          }
          leaf two-way-max-jitter {
            description 'The maximum delay jitter of two way packet .'
                        ;
            type uint64 ;
            units ns ;
          }
          leaf two-way-avg-jitter {
            description 'The average delay jitter of two way packet .'
                        ;
            type uint64 ;
            units ns ;
          }
          leaf forward-time-delay {
            description 'The forward packet delay.'
                        ;
            type uint64 ;
            units ns ;
          }
          leaf forward-min-delay {
            description 'The minimum of forward packet delay.'
                        ;
            type uint64 ;
            units ns ;
          }
          leaf forward-max-delay {
            description 'The maximum of forward packet delay.'
                        ;
            type uint64 ;
            units ns ;
          }
          leaf forward-avg-delay {
            description 'The average of forward packet delay.'
                        ;
            type uint64 ;
            units ns ;
          }
          leaf forward-delay-jitter {
            description 'Delay jitter of the forward packet.'
                        ;
            type uint64 ;
            units ns ;
          }
          leaf forward-min-jitter {
            description 'The minimum of delay jitter of the forward packet.'
                        ;
            type uint64 ;
            units ns ;
          }
          leaf forward-max-jitter {
            description 'The maximum of delay jitter of the forward packet.'
                        ;
            type uint64 ;
            units ns ;
          }
          leaf forward-avg-jitter {
            description 'The average of delay jitter of the forward packet.'
                        ;
            type uint64 ;
            units ns ;
          }
          leaf reverse-time-delay {
            description 'The reverse packet delay.'
                        ;
            type uint64 ;
            units ns ;
          }
          leaf reverse-min-delay {
            description 'The minimum of reverse packet delay.'
                        ;
            type uint64 ;
            units ns ;
          }
          leaf reverse-max-delay {
            description 'The maximum of reverse packet delay.'
                        ;
            type uint64 ;
            units ns ;
          }
          leaf reverse-avg-delay {
            description 'The average of reverse packet delay.'
                        ;
            type uint64 ;
            units ns ;
          }
          leaf reverse-delay-jitter {
            description 'The reverse packet delay jitter.'
                        ;
            type uint64 ;
            units ns ;
          }
          leaf reverse-min-jitter {
            description 'The minimum of delay jitter of the reverse packet.'
                        ;
            type uint64 ;
            units ns ;
          }
          leaf reverse-max-jitter {
            description 'The maximum of delay jitter of the reverse packet.'
                        ;
            type uint64 ;
            units ns ;
          }
          leaf reverse-avg-jitter {
            description 'The average of delay jitter of the reverse packet.'
                        ;
            type uint64 ;
            units ns ;
          }
        }
        ncd:revise-date 2020-07-16 ;
      }
    }
    ncd:revise-date 2019-06-04 ;
  }
  notification twamp-event {
    description 'The test event of FULL TWAMP.'
                ;
    list twamp-result {
      description 'The test result of FULL TWAMP.'
                  ;
      key 'connection-id session-id'
          ;
      leaf connection-id {
        description 'The connection ID,the upper limit of this parameter depend'
                  + ' on the device.'
                    ;
        type uint32 {
          range 1..65535 {
            description 'The value of this parameter ranges from 1 to 65535.'
                        ;
          }
        }
      }
      leaf session-id {
        description 'The session ID,the upper limit of this parameter depend on'
                  + ' the device.'
                    ;
        type uint16 {
          range 1..65535 {
            description 'The value of this parameter ranges from 1 to 65535.'
                        ;
          }
        }
      }
      leaf packet-send-number {
        config false ;
        description 'The count of sending packets.'
                    ;
        type uint32 {
          range 0..4294967295 {
            description 'The range of sending packet number.'
                        ;
          }
        }
      }
      leaf packet-receive-number {
        config false ;
        description 'The count of receiving packets.'
                    ;
        type uint32 {
          range 0..4294967295 {
            description 'The range of receiving packet number.'
                        ;
          }
        }
      }
      leaf packet-loss-number {
        config false ;
        description 'The count of lossing packets.'
                    ;
        type uint32 {
          range 0..4294967295 {
            description 'The range of packe lossing number.'
                        ;
          }
        }
      }
      leaf packet-loss-ratio {
        config false ;
        description 'The packet loss ratio,precision is 1/1000000.'
                    ;
        type uint32 {
          range 0..4294967295 {
            description 'The range of packet lossing ratio.'
                        ;
          }
        }
      }
      leaf two-way-time-delay {
        config false ;
        description 'Two way delay.'
                    ;
        type uint64 ;
        units ns ;
      }
      leaf two-way-min-delay {
        description 'The minimum of two way delay.'
                    ;
        type uint64 ;
        units ns ;
      }
      leaf two-way-max-delay {
        config false ;
        description 'The maximum of two way delay.'
                    ;
        type uint64 ;
        units ns ;
      }
      leaf two-way-avg-delay {
        config false ;
        description 'The average of two way delay.'
                    ;
        type uint64 ;
        units ns ;
      }
      leaf two-way-delay-jitter {
        config false ;
        description 'Delay jitter of two way packet .'
                    ;
        type uint64 ;
        units ns ;
      }
      leaf two-way-min-jitter {
        config false ;
        description 'The minimum delay jitter of two way packet .'
                    ;
        type uint64 ;
        units ns ;
      }
      leaf two-way-max-jitter {
        config false ;
        description 'The maximum delay jitter of two way packet .'
                    ;
        type uint64 ;
        units ns ;
      }
      leaf two-way-avg-jitter {
        config false ;
        description 'The average delay jitter of two way packet .'
                    ;
        type uint64 ;
        units ns ;
      }
      leaf forward-time-delay {
        config false ;
        description 'The forward packet delay.'
                    ;
        type uint64 ;
        units ns ;
      }
      leaf forward-min-delay {
        config false ;
        description 'The minimum of forward packet delay.'
                    ;
        type uint64 ;
        units ns ;
      }
      leaf forward-max-delay {
        config false ;
        description 'The maximum of forward packet delay.'
                    ;
        type uint64 ;
        units ns ;
      }
      leaf forward-avg-delay {
        config false ;
        description 'The average of forward packet delay.'
                    ;
        type uint64 ;
        units ns ;
      }
      leaf forward-delay-jitter {
        config false ;
        description 'Delay jitter of the forward packet.'
                    ;
        type uint64 ;
        units ns ;
      }
      leaf forward-min-jitter {
        config false ;
        description 'The minimum of delay jitter of the forward packet.'
                    ;
        type uint64 ;
        units ns ;
      }
      leaf forward-max-jitter {
        config false ;
        description 'The maximum of delay jitter of the forward packet.'
                    ;
        type uint64 ;
        units ns ;
      }
      leaf forward-avg-jitter {
        config false ;
        description 'The average of delay jitter of the forward packet.'
                    ;
        type uint64 ;
        units ns ;
      }
      leaf reverse-time-delay {
        config false ;
        description 'The reverse packet delay.'
                    ;
        type uint64 ;
        units ns ;
      }
      leaf reverse-min-delay {
        config false ;
        description 'The minimum of reverse packet delay.'
                    ;
        type uint64 ;
        units ns ;
      }
      leaf reverse-max-delay {
        config false ;
        description 'The maximum of reverse packet delay.'
                    ;
        type uint64 ;
        units ns ;
      }
      leaf reverse-avg-delay {
        config false ;
        description 'The average of reverse packet delay.'
                    ;
        type uint64 ;
        units ns ;
      }
      leaf reverse-delay-jitter {
        config false ;
        description 'The reverse packet delay jitter.'
                    ;
        type uint64 ;
        units ns ;
      }
      leaf reverse-min-jitter {
        config false ;
        description 'The minimum of delay jitter of the reverse packet.'
                    ;
        type uint64 ;
        units ns ;
      }
      leaf reverse-max-jitter {
        config false ;
        description 'The maximum of delay jitter of the reverse packet.'
                    ;
        type uint64 ;
        units ns ;
      }
      leaf reverse-avg-jitter {
        config false ;
        description 'The average of delay jitter of the reverse packet.'
                    ;
        type uint64 ;
        units ns ;
      }
    }
  }
}
