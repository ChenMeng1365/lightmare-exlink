module zxr10-qos {
  namespace 'http://www.zte.com.cn/zxr10/netconf/schema/rosng/qos'
            ;
  prefix qos ;
  yang-version 1 ;
  import zxr10-netconf-defs {
    prefix ncd ;
  }
  import zxr10-cps {
    prefix cps ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe QoS services info.It contains sta'
            + 'te and configuration info.'
              ;
  revision 2021-04-18 {
    description 'Support cps-based class-map and policy-map, add nodes:'+"\n"
              + '/qos:configuration/qos:qos/qos:class-map/qos:cps-based;'+"\n"
              + '/qos:configuration/qos:qos/qos:policy-map/qos:cps-based.'
                ;
  }
  revision 2021-04-16 {
    description 'Modify the pattern of packet-length-value node to avoid inputt'
              + 'ing error value:'+"\n"
              + '/configuration/qos/class-map/flowspec-based/class-maps/class-m'
              + 'ap/match/packet-length/packet-length-value.'
                ;
  }
  revision 2021-03-24 {
    description 'Support statistical-group in QoS statistics, add node:'+"\n"
              + '1./qos:configuration/qos:qos/qos:qos-stats/qos:stats-switch/qo'
              + 's:stats-switches/qos:statistics-group;'+"\n"
              + '2./qos:configuration/qos:qos/qos:pw-schedul-stats/qos:stats-sw'
              + 'itches/qos:stats-switch/qos:statistics-group;'+"\n"
              + '3./qos:configuration/qos:qos/qos:pw-schedul-stats/qos:stats-sw'
              + 'itch-ins/qos:stats-switch-in/qos:statistics-group;'+"\n"
              + '4./qos:configuration/qos:qos/qos:bgpad-schedul-stats/qos:stats'
              + '-switches/qos:stats-switch/qos:statistics-group;'+"\n"
              + '5./qos:configuration/qos:qos/qos:qos-schedule/qos:tes;'+"\n"
              + '6./qos:configuration/qos:qos/qos:te-schedul-stats;'+"\n"
              + '7./qos:operation/qos:qos/qos:stats-clear/qos:te-schedules;'+"\n"
              + '8./qos:operation/qos:qos/qos:stats-clear/qos:interfaces;'+"\n"
              + 'Delete features on following nodes:'+"\n"
              + '1./configuration/qos/policy-map/traffic-based/policy-maps/poli'
              + 'cy-map/class-maps/class-map/drop;'+"\n"
              + '2./configuration/qos/policy-map/traffic-based/policy-maps/poli'
              + 'cy-map/class-maps/class-default/drop;'+"\n"
              + '3./configuration/qos/policy-map/traffic-based/policy-maps/poli'
              + 'cy-map/class-maps/class-map/police/mode;'+"\n"
              + '4./configuration/qos/policy-map/traffic-based/policy-maps/poli'
              + 'cy-map/class-maps/class-default/police/mode;'+"\n"
              + '5./configuration/qos/mls-qos-modes/mls-qos-mode/pipe/servclass'
              + '-color;'+"\n"
              + '6./configuration/qos/mls-qos-modes/mls-qos-mode/short-pipe/ser'
              + 'vclass-color.'
                ;
  }
  revision 2021-03-22 {
    description 'Support shape of sub-interface,add node:'+"\n"
              + '/configuration/qos/service-policys/service-policy/shape'
                ;
  }
  revision 2021-03-04 {
    description 'Support statistical-share in PW schedule, add node:'+"\n"
              + '1./qos:configuration/qos:qos/qos:qos-schedule/qos:pws/qos:pw/q'
              + 'os:statistical-share;'+"\n"
              + '2./qos:configuration/qos:qos/qos:qos-schedule/qos:pw-ins/qos:p'
              + 'w-in/qos:statistical-share.'
                ;
  }
  revision 2021-01-25 {
    description '1.Support traffic-based class-map, add nodes:'+"\n"
              + '/qos:configuration/qos:qos/qos:class-map/qos:traffic-based.'+"\n"
              + '2.Support vlan-stacking, add node:'+"\n"
              + '/configuration/qos/policy-map/traffic-based/policy-maps/policy'
              + '-map/class-maps/class-map/vlan-stacking'+"\n"
              + '/configuration/qos/policy-map/traffic-based/policy-maps/policy'
              + '-map/class-maps/class-default/vlan-stacking'+"\n"
              + '3.Support reidrect route-map, add node:'+"\n"
              + '/configuration/qos/policy-map/traffic-based/policy-maps/policy'
              + '-map/class-maps/class-map/redirect/route-map'+"\n"
              + '/configuration/qos/policy-map/traffic-based/policy-maps/policy'
              + '-map/class-maps/class-default/redirect/route-map'+"\n"
              + '4.Support match interface in normal class-map, add nodes:'+"\n"
              + '/qos:configuration/qos:qos/qos:class-map/qos:normal/qos:class-'
              + 'maps/qos:class-map/qos:match/qos:interface.'+"\n"
              + '5. Support ipv4-vxlan-acl and ipv6-vxlan-acl, add nodes:'+"\n"
              + '/qos:configuration/qos:qos/qos:class-map/qos:normal/qos:class-'
              + 'maps/qos:class-map/qos:match/qos:ipv4-vxlan-acls'+"\n"
              + '/qos:configuration/qos:qos/qos:class-map/qos:normal/qos:class-'
              + 'maps/qos:class-map/qos:match/qos:ipv6-vxlan-acls'+"\n"
              + '6. Support qos-global-priority-remark configuration,add node:'+"\n"
              + '/qos:configuration/qos:qos/qos:qos-global-prioritys-remark.'+"\n"
              + '7. Modify the range of node: '+"\n"
              + '/qos:configuration/qos:qos/qos:qos-prioritys-remark/qos:qos-pr'
              + 'iority-remark/qos:priority-type from 1-2 to 1-3, add type MPLS'
              + '-EXP.'+"\n"
              + '8. Support enable-switch of interface priority remark,add node'
              + ':'+"\n"
              + '/qos:configuration/qos:qos/qos:qos-prioritys-remark/qos:qos-pr'
              + 'iority-remark/qos:enable-switch.'+"\n"
              + '9. Support optional pir in rate-limit, some nodes are added:'+"\n"
              + '/qos:configuration/qos:qos/qos:rate-limit/qos:unicasts/qos:uni'
              + 'cast/qos:buket-value-percent;'+"\n"
              + '/qos:configuration/qos:qos/qos:rate-limit/qos:unknown-unicasts'
              + '/qos:unknown-unicast/qos:buket-value-percent;'+"\n"
              + '/qos:configuration/qos:qos/qos:rate-limit/qos:multicasts/qos:m'
              + 'ulticast/qos:buket-value-percent;'+"\n"
              + '/qos:configuration/qos:qos/qos:rate-limit/qos:unknown-multicas'
              + 'ts/qos:unknown-multicast/qos:buket-value-percent;'+"\n"
              + '/qos:configuration/qos:qos/qos:rate-limit/qos:broadcasts/qos:b'
              + 'roadcast/qos:buket-value-percent;'+"\n"
              + '/qos:configuration/qos:qos/qos:rate-limit/qos:localports/qos:l'
              + 'ocalport/qos:buket-value-percent.'+"\n"
              + '10.Change configuration/qos/queue-templates/queue-template/que'
              + 'ue-nos/queue-no/wfq-weight/percentage,use perfmpara as max val'
              + 'ue.'+"\n"
              + 'Change configuration/qos/queue-templates/queue-template/queue-'
              + 'nos/queue-no/priority-level/priority-value,the range is 1-8.'+"\n"
              + 'Add /qos:configuration/qos:qos/qos:queue-templates/qos:queue-t'
              + 'emplate/qos:queue-nos/qos:queue-no/qos:random-detect/qos:weigh'
              + 't.'+"\n"
              + 'Add /qos:configuration/qos:qos/qos:queue-templates/qos:queue-t'
              + 'emplate/qos:queue-nos/qos:queue-no/qos:shape/qos:pir-pbs.'+"\n"
              + 'Add /qos:configuration/qos:qos/qos:queue-templates/qos:queue-t'
              + 'emplate/qos:queue-nos/qos:queue-no/qos:shape/qos:pir-percentag'
              + 'e.'+"\n"
              + '11.Support traffic-policy interface, add nodes:'+"\n"
              + '/configuration/qos/traffic-policy-interfaces/traffic-policy-in'
              + 'terface.'+"\n"
              + '12. Support statistics of traffic policy with feature traffic-'
              + 'policy.'+"\n"
              + 'Add node: /configuration/qos/traffic-policy-stats.'+"\n"
              + '13. Support clear statistics of traffic policy with feature tr'
              + 'affic-policy.'+"\n"
              + 'Add node: /operation/qos/traffic-policy-stats-clear.'+"\n"
              + '14.Support traffic-based policy-map, add nodes:'+"\n"
              + '/configuration/qos/policy-map/traffic-based/policy-maps/policy'
              + '-map/class-maps/class-map/set/dscp'+"\n"
              + '/configuration/qos/policy-map/traffic-based/policy-maps/policy'
              + '-map/class-maps/class-map/set/precedence'+"\n"
              + '/configuration/qos/policy-map/traffic-based/policy-maps/policy'
              + '-map/class-maps/class-map/set/pri-8021p'+"\n"
              + '/configuration/qos/policy-map/traffic-based/policy-maps/policy'
              + '-map/class-maps/class-map/set/mpls-exp'+"\n"
              + '/configuration/qos/policy-map/traffic-based/policy-maps/policy'
              + '-map/class-maps/class-map/set/vlan-id'+"\n"
              + '/configuration/qos/policy-map/traffic-based/policy-maps/policy'
              + '-map/class-maps/class-default/set/dscp'+"\n"
              + '/configuration/qos/policy-map/traffic-based/policy-maps/policy'
              + '-map/class-maps/class-default/set/precedence'+"\n"
              + '/configuration/qos/policy-map/traffic-based/policy-maps/policy'
              + '-map/class-maps/class-default/set/pri-8021p'+"\n"
              + '/configuration/qos/policy-map/traffic-based/policy-maps/policy'
              + '-map/class-maps/class-default/set/mpls-exp'+"\n"
              + '/configuration/qos/policy-map/traffic-based/policy-maps/policy'
              + '-map/class-maps/class-default/set/vlan-id.'+"\n"
              + '15. Support the PW interface diffserv domain template configur'
              + 'ation, add nodes:'+"\n"
              + '/qos:configuration/qos:qos/qos:qos-pw-ds-domains/qos:qos-pw-ds'
              + '-domain/qos:pw-name'+"\n"
              + '/qos:configuration/qos:qos/qos:qos-pw-ds-domains/qos:qos-pw-ds'
              + '-domain/qos:ds-domain-name.'
                ;
  }
  revision 2021-01-18 {
    description '1. Support match service-class range, service-class leaf node '
              + 'are changed to choice-case node, and service-class-range node '
              + 'is added:'+"\n"
              + '/qos:configuration/qos:qos/qos:class-map/qos:normal/qos:class-'
              + 'maps/qos:class-map/qos:match/qos:service-class;'+"\n"
              + '/qos:configuration/qos:qos/qos:class-map/qos:phb-based/qos:cla'
              + 'ss-maps/qos:class-map/qos:match/qos:service-class.'+"\n"
              + '2. Support WRED precedence and weight, add nodes as follows:'+"\n"
              + '/qos:configuration/qos:qos/qos:policy-map/qos:phb-based/qos:po'
              + 'licy-maps/qos:policy-map/qos:class-maps/qos:class-map/qos:rand'
              + 'om-detect/qos:colors/qos:color/qos:threshold;'+"\n"
              + '/qos:configuration/qos:qos/qos:policy-map/qos:phb-based/qos:po'
              + 'licy-maps/qos:policy-map/qos:class-maps/qos:class-map/qos:rand'
              + 'om-detect/qos:precedences;'+"\n"
              + '/qos:configuration/qos:qos/qos:policy-map/qos:phb-based/qos:po'
              + 'licy-maps/qos:policy-map/qos:class-maps/qos:class-map/qos:rand'
              + 'om-detect/qos:weight.'+"\n"
              + '3. Support set service-class color in normal and car-action po'
              + 'licy-map, service-class node is added:'+"\n"
              + '/qos:configuration/qos:qos/qos:policy-map/qos:normal/qos:polic'
              + 'y-maps/qos:policy-map/qos:class-maps/qos:class-map/qos:set/qos'
              + ':service-class;'+"\n"
              + '/qos:configuration/qos:qos/qos:policy-map/qos:normal/qos:polic'
              + 'y-maps/qos:policy-map/qos:class-maps/qos:class-default/qos:set'
              + '/qos:service-class;'+"\n"
              + '/qos:configuration/qos:qos/qos:policy-map/qos:car-action/qos:p'
              + 'olicy-maps/qos:policy-map/qos:class-maps/qos:class-map/qos:set'
              + '/qos:service-class/qos:color-type;'+"\n"
              + '/qos:configuration/qos:qos/qos:policy-map/qos:car-action/qos:p'
              + 'olicy-maps/qos:policy-map/qos:class-maps/qos:class-default/qos'
              + ':set/qos:service-class/qos:color-type.'+"\n"
              + '4. Support share group ID in service policy, add node:'+"\n"
              + '/qos:configuration/qos:qos/qos:service-policys/qos:service-pol'
              + 'icy/qos:share-group.'+"\n"
              + '5. Support statistical-share in traffic-shape, add node:'+"\n"
              + '/qos:configuration/qos:qos/qos:traffic-shapes/qos:traffic-shap'
              + 'e/qos:statistical-share;'+"\n"
              + '/qos:configuration/qos:qos/qos:traffic-shape-dirs/qos:traffic-'
              + 'shape-dir/qos:statistical-share;'+"\n"
              + '6. Support PW ingress in QoS schedule, add node:'+"\n"
              + '/qos:configuration/qos:qos/qos:qos-schedule/qos:pw-ins;'+"\n"
              + '/qos:configuration/qos:qos/qos:pw-schedule-stats/qos:stats-swi'
              + 'tch-ins;'+"\n"
              + '/qos:operation/qos:qos/qos:stats-clear/qos:pw-in-schedules.'+"\n"
              + '7. In order to describing traffic-based policy map, a new node'
              + ' is added as follows:'+"\n"
              + '/qos:configuration/qos:qos/qos:policy-map/qos:traffic-based/qo'
              + 's:policy-maps/qos:policy-map/qos:pmap-description.'
                ;
  }
  revision 2021-01-11 {
    description '1. Support scheduling policy for BGP-AD.'+"\n"
              + 'Add node: /configuration/qos/qos-schedule/bgp-ads.'+"\n"
              + '2. Support statistics of scheduling policy for BGP-AD.'+"\n"
              + 'Add node: /configuration/qos/bgpad-schedule-stats.'+"\n"
              + '3. Support clear statistics of scheduling policy for BGP-AD.'+"\n"
              + 'Add node: /operation/qos/stats-clear/bgpad-schedules.'+"\n"
              + '4. Support match child for cmap phb-based.'+"\n"
              + '/configuration/qos/class-map/phb-based/class-maps/class-map/ma'
              + 'tch/child.'+"\n"
              + '5. Support service policy for pmap phb-based.'+"\n"
              + '/configuration/qos/policy-map/phb-based/policy-maps/policy-map'
              + '/class-maps/class-map/service-policy.'+"\n"
              + '/configuration/qos/policy-map/phb-based/policy-maps/policy-map'
              + '/class-maps/class-default/service-policy.'+"\n"
              + '6. Support drop function of traffic-based policy-map, add node'
              + ':'+"\n"
              + '/configuration/qos/policy-map/traffic-based/policy-maps/policy'
              + '-map/class-maps/class-map/drop'+"\n"
              + '/configuration/qos/policy-map/traffic-based/policy-maps/policy'
              + '-map/class-maps/class-default/drop.'
                ;
  }
  revision 2020-12-23 {
    description '1. Support ipv6-mixed-acl, add node:'+"\n"
              + '/configuration/qos/class-map/normal/class-maps/class-map/match'
              + '/ipv6-mixed-acls.'+"\n"
              + '2. Support traffic-based policy-map, add node:'+"\n"
              + '/configuration/qos/policy-map/traffic-based.'+"\n"
              + '3. Support cir and pir percentage, add node:'+"\n"
              + '/configuration/qos/rate-limit/unicasts/unicast/cir-percentage'+"\n"
              + '/configuration/qos/rate-limit/unicasts/unicast/pir-percentage'+"\n"
              + '/configuration/qos/rate-limit/unknown-unicasts/unknown-unicast'
              + '/cir-percentage'+"\n"
              + '/configuration/qos/rate-limit/unknown-unicasts/unknown-unicast'
              + '/pir-percentage'+"\n"
              + '/configuration/qos/rate-limit/multicasts/multicast/cir-percent'
              + 'age'+"\n"
              + '/configuration/qos/rate-limit/multicasts/multicast/pir-percent'
              + 'age'+"\n"
              + '/configuration/qos/rate-limit/unknown-multicasts/unknown-multi'
              + 'cast/cir-percentage'+"\n"
              + '/configuration/qos/rate-limit/unknown-multicasts/unknown-multi'
              + 'cast/pir-percentage'+"\n"
              + '/configuration/qos/rate-limit/broadcasts/broadcast/cir-percent'
              + 'age'+"\n"
              + '/configuration/qos/rate-limit/broadcasts/broadcast/pir-percent'
              + 'age'+"\n"
              + '/configuration/qos/rate-limit/unknowns/unknown/cir-percentage'+"\n"
              + '/configuration/qos/rate-limit/unknowns/unknown/pir-percentage'+"\n"
              + '/configuration/qos/rate-limit/localports/localport/cir-percent'
              + 'age'+"\n"
              + '/configuration/qos/rate-limit/localports/localport/pir-percent'
              + 'age'+"\n"
              + '/configuration/qos/rate-limit/dscps/dscp/cir-percentage'+"\n"
              + '/configuration/qos/rate-limit/dscps/dscp/pir-percentage'+"\n"
              + '/configuration/qos/rate-limit/precedences/precedence/cir-perce'
              + 'ntage'+"\n"
              + '/configuration/qos/rate-limit/precedences/precedence/pir-perce'
              + 'ntage'+"\n"
              + '/configuration/qos/rate-limit/mpls-exps/mpls-exp/cir-percentag'
              + 'e'+"\n"
              + '/configuration/qos/rate-limit/mpls-exps/mpls-exp/pir-percentag'
              + 'e'+"\n"
              + '/configuration/qos/rate-limit/inner-vlans/inner-vlan/cir-perce'
              + 'ntage'+"\n"
              + '/configuration/qos/rate-limit/inner-vlans/inner-vlan/pir-perce'
              + 'ntage'+"\n"
              + '/configuration/qos/rate-limit/outer-vlans/outer-vlan/cir-perce'
              + 'ntage'+"\n"
              + '/configuration/qos/rate-limit/outer-vlans/outer-vlan/pir-perce'
              + 'ntage'+"\n"
              + '/configuration/qos/rate-limit/multi-vlans/multi-vlan/cir-perce'
              + 'ntage'+"\n"
              + '/configuration/qos/rate-limit/multi-vlans/multi-vlan/pir-perce'
              + 'ntage'+"\n"
              + '/configuration/qos/rate-limit/inner-8021ps/inner-8021p/cir-per'
              + 'centage'+"\n"
              + '/configuration/qos/rate-limit/inner-8021ps/inner-8021p/pir-per'
              + 'centage'+"\n"
              + '/configuration/qos/rate-limit/outer-8021ps/outer-8021p/cir-per'
              + 'centage'+"\n"
              + '/configuration/qos/rate-limit/outer-8021ps/outer-8021p/pir-per'
              + 'centage'+"\n"
              + '/configuration/qos/rate-limit/multi-8021ps/multi-8021p/cir-per'
              + 'centage'+"\n"
              + '/configuration/qos/rate-limit/multi-8021ps/multi-8021p/pir-per'
              + 'centage'+"\n"
              + '/configuration/qos/rate-limit/qos-groups/qos-group/cir-percent'
              + 'age'+"\n"
              + '/configuration/qos/rate-limit/qos-groups/qos-group/pir-percent'
              + 'age'+"\n"
              + '/configuration/qos/rate-limit/access-lists/access-list/cir-per'
              + 'centage'+"\n"
              + '/configuration/qos/rate-limit/access-lists/access-list/pir-per'
              + 'centage'
                ;
  }
  revision 2020-12-02 {
    description 'Support flowspec redirect tunnel-id, add node:'+"\n"
              + '/configuration/qos/policy-map/flowspec-based/policy-maps/polic'
              + 'y-map/class-maps/class-map/redirect-tunnel-id'+"\n"
              + 'Obsolete flowspec redirect rsvp-te and sr-te, obsolete node:'+"\n"
              + '/configuration/qos/policy-map/flowspec-based/policy-maps/polic'
              + 'y-map/class-maps/class-map/redirect-rsvp-te'+"\n"
              + '/configuration/qos/policy-map/flowspec-based/policy-maps/polic'
              + 'y-map/class-maps/class-map/redirect-sr-te'
                ;
  }
  revision 2020-11-11 {
    description 'Support WRED threshold percentage config in queue-template.'+"\n"
              + '1 Add choice threshold:'+"\n"
              + '/configuration/qos/queue-templates/queue-template/queue-nos/qu'
              + 'eue-no/random-detect/color/green/threshold;'+"\n"
              + '/configuration/qos/queue-templates/queue-template/queue-nos/qu'
              + 'eue-no/random-detect/color/yellow/threshold;'+"\n"
              + '/configuration/qos/queue-templates/queue-template/queue-nos/qu'
              + 'eue-no/random-detect/color/red/threshold.'+"\n"
              + '2 Move min-threshode and max-threshold to new case threshold-v'
              + 'alue:'+"\n"
              + '/configuration/qos/queue-templates/queue-template/queue-nos/qu'
              + 'eue-no/random-detect/color/green/min-threshold;'+"\n"
              + '/configuration/qos/queue-templates/queue-template/queue-nos/qu'
              + 'eue-no/random-detect/color/green/max-threshold;'+"\n"
              + '/configuration/qos/queue-templates/queue-template/queue-nos/qu'
              + 'eue-no/random-detect/color/yellow/min-threshold;'+"\n"
              + '/configuration/qos/queue-templates/queue-template/queue-nos/qu'
              + 'eue-no/random-detect/color/yellow/max-threshold;'+"\n"
              + '/configuration/qos/queue-templates/queue-template/queue-nos/qu'
              + 'eue-no/random-detect/color/red/min-threshold;'+"\n"
              + '/configuration/qos/queue-templates/queue-template/queue-nos/qu'
              + 'eue-no/random-detect/color/red/max-threshold.'
                ;
  }
  revision 2020-11-02 {
    description 'Set cir-percentage node mandatory true:'+"\n"
              + '/configuration/qos/policy-map/normal/policy-maps/policy-map/cl'
              + 'ass-maps/class-map/police/cir-pir-percentage/cir-percentage;'+"\n"
              + '/configuration/qos/policy-map/normal/policy-maps/policy-map/cl'
              + 'ass-maps/class-default/police/cir-pir-percentage/cir-percentag'
              + 'e.'
                ;
  }
  revision 2020-10-20 {
    description '1. Support redirect next-hop ipv6-address color and prefix-sid'
              + ', add node:'+"\n"
              + '/configuration/qos/policy-map/flowspec-based/policy-maps/polic'
              + 'y-map/class-maps/class-map/redirect-nexthop/next-hop/ipv6-addr'
              + 'ess/ipv6-address/ipaddr-nexthop/color-sid.'
                ;
  }
  revision 2020-08-25 {
    description 'Support H-QoS switch fabric policy bind based on interface:'+"\n"
              + '/configuration/qos/switch-fabrics/interfaces.'
                ;
  }
  revision 2020-07-17 {
    description '1. Support redirect next-hop ipv6-address, add node:'+"\n"
              + '/configuration/qos/policy-map/flowspec-based/policy-maps/polic'
              + 'y-map/class-maps/class-map/redirect-nexthop/next-hop/ipv6-addr'
              + 'ess.'+"\n"
              + '2. Support copy in redirect next-hop ip-address, add node:'+"\n"
              + '/configuration/qos/policy-map/flowspec-based/policy-maps/polic'
              + 'y-map/class-maps/class-map/redirect-nexthop/next-hop/ip-addres'
              + 's/ip-address/copy.'
                ;
  }
  revision 2020-06-23 {
    description 'Support set service-class of policy-map car-action-type, add n'
              + 'odes:'+"\n"
              + '/configuration/qos/policy-map/car-action/policy-maps/policy-ma'
              + 'p/class-maps/class-map/police/conform-action/service-class-val'
              + 'ue'+"\n"
              + '/configuration/qos/policy-map/car-action/policy-maps/policy-ma'
              + 'p/class-maps/class-map/police/exceed-action/service-class-valu'
              + 'e'+"\n"
              + '/configuration/qos/policy-map/car-action/policy-maps/policy-ma'
              + 'p/class-maps/class-map/police/violate-action/service-class-val'
              + 'ue'+"\n"
              + '/configuration/qos/policy-map/car-action/policy-maps/policy-ma'
              + 'p/class-maps/class-default/police/conform-action/service-class'
              + '-value'+"\n"
              + '/configuration/qos/policy-map/car-action/policy-maps/policy-ma'
              + 'p/class-maps/class-default/police/exceed-action/service-class-'
              + 'value'+"\n"
              + '/configuration/qos/policy-map/car-action/policy-maps/policy-ma'
              + 'p/class-maps/class-default/police/violate-action/service-class'
              + '-value'
                ;
  }
  revision 2020-06-18 {
    description 'In order to describing policy map, class map, rate limit and f'
              + 'low behavior application, some new nodes are added as follows:'
              + ''+"\n"
              + '1./qos:configuration/qos:qos/qos:class-map/qos:normal/qos:clas'
              + 's-maps/qos:class-map/qos:cmap-description;'+"\n"
              + '2./qos:configuration/qos:qos/qos:class-map/qos:phb-based/qos:c'
              + 'lass-maps/qos:class-map/qos:cmap-description;'+"\n"
              + '3./qos:configuration/qos:qos/qos:class-map/qos:sub-interface-b'
              + 'ased/qos:class-maps/qos:class-map/qos:cmap-description;'+"\n"
              + '4./qos:configuration/qos:qos/qos:class-map/qos:flowspec-based/'
              + 'qos:class-maps/qos:class-map/qos:cmap-description;'+"\n"
              + '5./qos:configuration/qos:qos/qos:class-map/qos:flow-feature/qo'
              + 's:class-maps/qos:class-map/qos:cmap-description;'+"\n"
              + '6./qos:configuration/qos:qos/qos:policy-map/qos:normal/qos:pol'
              + 'icy-maps/qos:policy-map/qos:pmap-description;'+"\n"
              + '7./qos:configuration/qos:qos/qos:policy-map/qos:phb-based/qos:'
              + 'policy-maps/qos:policy-map/qos:pmap-description;'+"\n"
              + '8./qos:configuration/qos:qos/qos:policy-map/qos:sub-interface-'
              + 'based/qos:policy-maps/qos:policy-map/qos:pmap-description;'+"\n"
              + '9./qos:configuration/qos:qos/qos:policy-map/qos:flowspec-based'
              + '/qos:policy-maps/qos:policy-map/qos:pmap-description;'+"\n"
              + '10./qos:configuration/qos:qos/qos:policy-map/qos:flow-behavior'
              + '/qos:policy-maps/qos:policy-map/qos:pmap-description;'+"\n"
              + '11./qos:configuration/qos:qos/qos:rate-limit/qos:unicasts/qos:'
              + 'unicast/qos:rate-limit-desc;'+"\n"
              + '12./qos:configuration/qos:qos/qos:rate-limit/qos:unknown-unica'
              + 'sts/qos:unknown-unicast/qos:rate-limit-desc;'+"\n"
              + '13./qos:configuration/qos:qos/qos:rate-limit/qos:multicasts/qo'
              + 's:multicast/qos:rate-limit-desc;'+"\n"
              + '14./qos:configuration/qos:qos/qos:rate-limit/qos:unknown-multi'
              + 'casts/qos:unknown-multicast/qos:rate-limit-desc;'+"\n"
              + '15./qos:configuration/qos:qos/qos:rate-limit/qos:broadcasts/qo'
              + 's:broadcast/qos:rate-limit-desc;'+"\n"
              + '16./qos:configuration/qos:qos/qos:rate-limit/qos:unknowns/qos:'
              + 'unknown/qos:rate-limit-desc;'+"\n"
              + '17./qos:configuration/qos:qos/qos:rate-limit/qos:localports/qo'
              + 's:localport/qos:rate-limit-desc;'+"\n"
              + '18./qos:configuration/qos:qos/qos:rate-limit/qos:dscps/qos:dsc'
              + 'p/qos:rate-limit-desc;'+"\n"
              + '19./qos:configuration/qos:qos/qos:rate-limit/qos:precedences/q'
              + 'os:precedence/qos:rate-limit-desc;'+"\n"
              + '20./qos:configuration/qos:qos/qos:rate-limit/qos:mpls-exps/qos'
              + ':mpls-exp/qos:rate-limit-desc;'+"\n"
              + '21./qos:configuration/qos:qos/qos:rate-limit/qos:inner-vlans/q'
              + 'os:inner-vlan/qos:rate-limit-desc;'+"\n"
              + '22./qos:configuration/qos:qos/qos:rate-limit/qos:outer-vlans/q'
              + 'os:outer-vlan/qos:rate-limit-desc;'+"\n"
              + '23./qos:configuration/qos:qos/qos:rate-limit/qos:multi-vlans/q'
              + 'os:multi-vlan/qos:rate-limit-desc;'+"\n"
              + '24./qos:configuration/qos:qos/qos:rate-limit/qos:inner-8021ps/'
              + 'qos:inner-8021p/qos:rate-limit-desc;'+"\n"
              + '25./qos:configuration/qos:qos/qos:rate-limit/qos:outer-8021ps/'
              + 'qos:outer-8021p/qos:rate-limit-desc;'+"\n"
              + '26./qos:configuration/qos:qos/qos:rate-limit/qos:multi-8021ps/'
              + 'qos:multi-8021p/qos:rate-limit-desc;'+"\n"
              + '27./qos:configuration/qos:qos/qos:rate-limit/qos:qos-groups/qo'
              + 's:qos-group/qos:rate-limit-desc;'+"\n"
              + '28./qos:configuration/qos:qos/qos:rate-limit/qos:access-lists/'
              + 'qos:access-list/qos:rate-limit-desc;'+"\n"
              + '29./qos:configuration/qos:qos/qos:flow-behavior-application/qo'
              + 's:flow-behavior-apply-global/qos:flow-behavior-apply-desc;'+"\n"
              + '30./qos:configuration/qos:qos/qos:flow-behavior-application/qo'
              + 's:flow-behavior-apply-vrfs/qos:flow-behavior-apply-vrf/qos:flo'
              + 'w-behavior-apply-desc.'
                ;
  }
  revision 2020-06-09 {
    description 'Support percentage of CIR and PIR, add nodes:'+"\n"
              + '/configuration/qos/policy-map/normal/policy-maps/policy-map/cl'
              + 'ass-maps/class-map/police/cir-pir-percentage'+"\n"
              + '/configuration/qos/policy-map/normal/policy-maps/policy-map/cl'
              + 'ass-maps/class-default/police/cir-pir-percentage'
                ;
  }
  revision 2020-06-02 {
    description 'Support network header length of traffic-shape, add nodes:'+"\n"
              + '/configuration/qos/traffic-shapes/traffic-shape/network-header'
              + '-len'+"\n"
              + '/configuration/qos/traffic-shape-dirs/traffic-shape-dir/networ'
              + 'k-header-len'
                ;
  }
  revision 2020-05-18 {
    description 'Support set service-class, add nodes:'+"\n"
              + '/configuration/qos/rate-limit/unicasts/unicast/conform-action/'
              + 'set-service-class-transmit'+"\n"
              + '/configuration/qos/rate-limit/unicasts/unicast/exceed-action/s'
              + 'et-service-class-transmit'+"\n"
              + '/configuration/qos/rate-limit/unicasts/unicast/violate-action/'
              + 'set-service-class-transmit'+"\n"
              + '/configuration/qos/rate-limit/unknown-unicasts/unknown-unicast'
              + '/conform-action/set-service-class-transmit'+"\n"
              + '/configuration/qos/rate-limit/unknown-unicasts/unknown-unicast'
              + '/exceed-action/set-service-class-transmit'+"\n"
              + '/configuration/qos/rate-limit/unknown-unicasts/unknown-unicast'
              + '/violate-action/set-service-class-transmit'+"\n"
              + '/configuration/qos/rate-limit/multicasts/multicast/conform-act'
              + 'ion/set-service-class-transmit'+"\n"
              + '/configuration/qos/rate-limit/multicasts/multicast/exceed-acti'
              + 'on/set-service-class-transmit'+"\n"
              + '/configuration/qos/rate-limit/multicasts/multicast/violate-act'
              + 'ion/set-service-class-transmit'+"\n"
              + '/configuration/qos/rate-limit/unknown-multicasts/unknown-multi'
              + 'cast/conform-action/set-service-class-transmit'+"\n"
              + '/configuration/qos/rate-limit/unknown-multicasts/unknown-multi'
              + 'cast/exceed-action/set-service-class-transmit'+"\n"
              + '/configuration/qos/rate-limit/unknown-multicasts/unknown-multi'
              + 'cast/violate-action/set-service-class-transmit'+"\n"
              + '/configuration/qos/rate-limit/broadcasts/broadcast/conform-act'
              + 'ion/set-service-class-transmit'+"\n"
              + '/configuration/qos/rate-limit/broadcasts/broadcast/exceed-acti'
              + 'on/set-service-class-transmit'+"\n"
              + '/configuration/qos/rate-limit/broadcasts/broadcast/violate-act'
              + 'ion/set-service-class-transmit'+"\n"
              + '/configuration/qos/rate-limit/unknowns/unknown/conform-action/'
              + 'set-service-class-transmit'+"\n"
              + '/configuration/qos/rate-limit/unknowns/unknown/exceed-action/s'
              + 'et-service-class-transmit'+"\n"
              + '/configuration/qos/rate-limit/unknowns/unknown/violate-action/'
              + 'set-service-class-transmit'+"\n"
              + '/configuration/qos/rate-limit/localports/localport/conform-act'
              + 'ion/set-service-class-transmit'+"\n"
              + '/configuration/qos/rate-limit/localports/localport/exceed-acti'
              + 'on/set-service-class-transmit'+"\n"
              + '/configuration/qos/rate-limit/localports/localport/violate-act'
              + 'ion/set-service-class-transmit'+"\n"
              + '/configuration/qos/rate-limit/dscps/dscp/conform-action/set-se'
              + 'rvice-class-transmit'+"\n"
              + '/configuration/qos/rate-limit/dscps/dscp/exceed-action/set-ser'
              + 'vice-class-transmit'+"\n"
              + '/configuration/qos/rate-limit/dscps/dscp/violate-action/set-se'
              + 'rvice-class-transmit'+"\n"
              + '/configuration/qos/rate-limit/precedences/precedence/conform-a'
              + 'ction/set-service-class-transmit'+"\n"
              + '/configuration/qos/rate-limit/precedences/precedence/exceed-ac'
              + 'tion/set-service-class-transmit'+"\n"
              + '/configuration/qos/rate-limit/precedences/precedence/violate-a'
              + 'ction/set-service-class-transmit'+"\n"
              + '/configuration/qos/rate-limit/mpls-exps/mpls-exp/conform-actio'
              + 'n/set-service-class-transmit'+"\n"
              + '/configuration/qos/rate-limit/mpls-exps/mpls-exp/exceed-action'
              + '/set-service-class-transmit'+"\n"
              + '/configuration/qos/rate-limit/mpls-exps/mpls-exp/violate-actio'
              + 'n/set-service-class-transmit'+"\n"
              + '/configuration/qos/rate-limit/inner-vlans/inner-vlan/conform-a'
              + 'ction/set-service-class-transmit'+"\n"
              + '/configuration/qos/rate-limit/inner-vlans/inner-vlan/exceed-ac'
              + 'tion/set-service-class-transmit'+"\n"
              + '/configuration/qos/rate-limit/inner-vlans/inner-vlan/violate-a'
              + 'ction/set-service-class-transmit'+"\n"
              + '/configuration/qos/rate-limit/outer-vlans/outer-vlan/conform-a'
              + 'ction/set-service-class-transmit'+"\n"
              + '/configuration/qos/rate-limit/outer-vlans/outer-vlan/exceed-ac'
              + 'tion/set-service-class-transmit'+"\n"
              + '/configuration/qos/rate-limit/outer-vlans/outer-vlan/violate-a'
              + 'ction/set-service-class-transmit'+"\n"
              + '/configuration/qos/rate-limit/multi-vlans/multi-vlan/conform-a'
              + 'ction/set-service-class-transmit'+"\n"
              + '/configuration/qos/rate-limit/multi-vlans/multi-vlan/exceed-ac'
              + 'tion/set-service-class-transmit'+"\n"
              + '/configuration/qos/rate-limit/multi-vlans/multi-vlan/violate-a'
              + 'ction/set-service-class-transmit'+"\n"
              + '/configuration/qos/rate-limit/inner-8021ps/inner-8021p/conform'
              + '-action/set-service-class-transmit'+"\n"
              + '/configuration/qos/rate-limit/inner-8021ps/inner-8021p/exceed-'
              + 'action/set-service-class-transmit'+"\n"
              + '/configuration/qos/rate-limit/inner-8021ps/inner-8021p/violate'
              + '-action/set-service-class-transmit'+"\n"
              + '/configuration/qos/rate-limit/outer-8021ps/outer-8021p/conform'
              + '-action/set-service-class-transmit'+"\n"
              + '/configuration/qos/rate-limit/outer-8021ps/outer-8021p/exceed-'
              + 'action/set-service-class-transmit'+"\n"
              + '/configuration/qos/rate-limit/outer-8021ps/outer-8021p/violate'
              + '-action/set-service-class-transmit'+"\n"
              + '/configuration/qos/rate-limit/multi-8021ps/multi-8021p/conform'
              + '-action/set-service-class-transmit'+"\n"
              + '/configuration/qos/rate-limit/multi-8021ps/multi-8021p/exceed-'
              + 'action/set-service-class-transmit'+"\n"
              + '/configuration/qos/rate-limit/multi-8021ps/multi-8021p/violate'
              + '-action/set-service-class-transmit'+"\n"
              + '/configuration/qos/rate-limit/qos-groups/qos-group/conform-act'
              + 'ion/set-service-class-transmit'+"\n"
              + '/configuration/qos/rate-limit/qos-groups/qos-group/exceed-acti'
              + 'on/set-service-class-transmit'+"\n"
              + '/configuration/qos/rate-limit/qos-groups/qos-group/violate-act'
              + 'ion/set-service-class-transmit'+"\n"
              + '/configuration/qos/rate-limit/access-lists/access-list/conform'
              + '-action/set-service-class-transmit'+"\n"
              + '/configuration/qos/rate-limit/access-lists/access-list/exceed-'
              + 'action/set-service-class-transmit'+"\n"
              + '/configuration/qos/rate-limit/access-lists/access-list/violate'
              + '-action/set-service-class-transmit'
                ;
  }
  revision 2020-04-06 {
    description 'Support latency time threshold, bandwidth threshold and drop r'
              + 'ate threshold, add nodes:'+"\n"
              + '/configuration/qos/policy-maps/class-maps/class-map/latency-ti'
              + 'me-threshold;'+"\n"
              + '/configuration/qos/policy-maps/class-maps/class-map/bandwidth-'
              + 'threshold;'+"\n"
              + '/configuration/qos/policy-maps/class-maps/class-map/drop-rate-'
              + 'threshold;'+"\n"
              + '/configuration/qos/policy-maps/class-maps/class-default/latenc'
              + 'y-time-threshold;'+"\n"
              + '/configuration/qos/policy-maps/class-maps/class-default/bandwi'
              + 'dth-threshold;'+"\n"
              + '/configuration/qos/policy-maps/class-maps/class-default/drop-r'
              + 'ate-threshold;'
                ;
  }
  revision 2020-03-24 {
    description 'Support global TTL, add node:'+"\n"
              + '/configuration/qos/ttl-mode-global'
                ;
  }
  revision 2020-03-05 {
    description 'Support IPv6 vxlan, add node:'+"\n"
              + '/configuration/qos/class-map/flow-feature/class-maps/class-map'
              + '/match/vxlan-ipv6'+"\n"
              + '/configuration/qos/policy-map/flow-behavior/policy-maps/policy'
              + '-map/class-maps/class-map/set/vxlan/ipv6'
                ;
  }
  revision 2020-02-03 {
    description 'Support flowspec IPv6, add node:'+"\n"
              + '/configuration/qos/class-map/flowspec-based/class-maps/class-m'
              + 'ap/match/flow-label'+"\n"
              + '/configuration/qos/class-map/flowspec-based/class-maps/class-m'
              + 'ap/match/destination-ipv6-addr'+"\n"
              + '/configuration/qos/class-map/flowspec-based/class-maps/class-m'
              + 'ap/match/source-ipv6-addr'+"\n"
              + '/configuration/qos/class-map/flowspec-based/class-maps/class-m'
              + 'ap/match/ipv6-icmp-code'+"\n"
              + '/configuration/qos/class-map/flowspec-based/class-maps/class-m'
              + 'ap/match/ipv6-icmp-type'+"\n"
              + '/configuration/qos/class-map/flowspec-based/class-maps/class-m'
              + 'ap/match/next-header'+"\n"
              + '/configuration/qos/policy-map/flowspec-based/policy-maps/polic'
              + 'y-map/class-maps/class-map/redirect-rsvp-te'+"\n"
              + '/configuration/qos/policy-map/flowspec-based/policy-maps/polic'
              + 'y-map/class-maps/class-map/redirect-sr-te'+"\n"
              + 'Add enumeration value to follow node:'+"\n"
              + '/configuration/qos/class-map/flowspec-based/class-maps/class-m'
              + 'ap/match/dscps/dscp/ip-type'+"\n"
              + '/configuration/qos/flowspec/address-family-ips/address-family-'
              + 'ip/ip-type'+"\n"
              + '/configuration/qos/flowspec/address-family-vrfs/address-family'
              + '-vrf/ip-type'
                ;
  }
  revision 2019-12-10 {
    description 'Suppport ipv4-mixed-acl and ipv6-mixed-acl,nodes modified as f'
              + 'ollow:'+"\n"
              + '/configuration/qos/rate-limit/access-lists/access-list/acl-typ'
              + 'e'
                ;
  }
  revision 2019-10-28 {
    description 'Support the configuration of token bucket ID,add new leaf as f'
              + 'ollows:'+"\n"
              + '/configuration/qos/rate-limit/unicasts/unicast/token-bucket-id'
              + ''+"\n"
              + '/configuration/qos/rate-limit/unknown-unicasts/unknown-unicast'
              + '/token-bucket-id'+"\n"
              + '/configuration/qos/rate-limit/multicasts/multicast/token-bucke'
              + 't-id'+"\n"
              + '/configuration/qos/rate-limit/unknown-multicasts/unknown-multi'
              + 'cast/token-bucket-id'+"\n"
              + '/configuration/qos/rate-limit/broadcasts/broadcast/token-bucke'
              + 't-id'+"\n"
              + '/configuration/qos/rate-limit/unknowns/unknown/token-bucket-id'
              + ''+"\n"
              + '/configuration/qos/rate-limit/localports/localport/token-bucke'
              + 't-id'+"\n"
              + '/configuration/qos/rate-limit/dscps/dscp/token-bucket-id'+"\n"
              + '/configuration/qos/rate-limit/precedences/precedence/token-buc'
              + 'ket-id'+"\n"
              + '/configuration/qos/rate-limit/mpls-exps/mpls-exp/token-bucket-'
              + 'id'+"\n"
              + '/configuration/qos/rate-limit/inner-vlans/inner-vlan/token-buc'
              + 'ket-id'+"\n"
              + '/configuration/qos/rate-limit/outer-vlans/outer-vlan/token-buc'
              + 'ket-id'+"\n"
              + '/configuration/qos/rate-limit/multi-vlans/multi-vlan/token-buc'
              + 'ket-id'+"\n"
              + '/configuration/qos/rate-limit/inner-8021ps/inner-8021p/token-b'
              + 'ucket-id'+"\n"
              + '/configuration/qos/rate-limit/outer-8021ps/outer-8021p/token-b'
              + 'ucket-id'+"\n"
              + '/configuration/qos/rate-limit/multi-8021ps/multi-8021p/token-b'
              + 'ucket-id'+"\n"
              + '/configuration/qos/rate-limit/qos-groups/qos-group/token-bucke'
              + 't-id'+"\n"
              + '/configuration/qos/rate-limit/access-lists/access-list/token-b'
              + 'ucket-id'
                ;
  }
  revision 2019-09-03 {
    description 'Remove mandatory attribute of these nodes:'+"\n"
              + '/configuration/qos/policy-map/normal/policy-maps/policy-map/cl'
              + 'ass-maps/class-map/police/cbs'+"\n"
              + '/configuration/qos/policy-map/normal/policy-maps/policy-map/cl'
              + 'ass-maps/class-map/police/pir-pbs/pbs'+"\n"
              + '/configuration/qos/policy-map/normal/policy-maps/policy-map/cl'
              + 'ass-maps/class-default/police/cbs'+"\n"
              + '/configuration/qos/policy-map/normal/policy-maps/policy-map/cl'
              + 'ass-maps/class-default/police/pir-pbs/pbs'+"\n"
              + '/configuration/qos/policy-map/car-action/policy-maps/policy-ma'
              + 'p/class-maps/class-map/police/cbs'+"\n"
              + '/configuration/qos/policy-map/car-action/policy-maps/policy-ma'
              + 'p/class-maps/class-map/police/pbs'+"\n"
              + '/configuration/qos/policy-map/car-action/policy-maps/policy-ma'
              + 'p/class-maps/class-default/police/cbs'+"\n"
              + '/configuration/qos/policy-map/car-action/policy-maps/policy-ma'
              + 'p/class-maps/class-default/police/pbs'+"\n"
              + '/configuration/qos/policy-map/phb-based/policy-maps/policy-map'
              + '/class-maps/class-map/police/cbs'+"\n"
              + '/configuration/qos/policy-map/phb-based/policy-maps/policy-map'
              + '/class-maps/class-map/police/pir-pbs/pbs'+"\n"
              + '/configuration/qos/policy-map/phb-based/policy-maps/policy-map'
              + '/class-maps/class-default/police/cbs'+"\n"
              + '/configuration/qos/policy-map/phb-based/policy-maps/policy-map'
              + '/class-maps/class-default/police/pir-pbs/pbs'+"\n"
              + '/configuration/qos/policy-map/sub-interface-based/policy-maps/'
              + 'policy-map/class-maps/class-map/police/cbs'+"\n"
              + '/configuration/qos/policy-map/sub-interface-based/policy-maps/'
              + 'policy-map/class-maps/class-map/police/pir-pbs/pbs'+"\n"
              + '/configuration/qos/policy-map/sub-interface-based/policy-maps/'
              + 'policy-map/class-maps/class-default/police/cbs'+"\n"
              + '/configuration/qos/policy-map/sub-interface-based/policy-maps/'
              + 'policy-map/class-maps/class-default/police/pir-pbs/pbs'
                ;
  }
  revision 2019-08-19 {
    description 'Support the configuration of queue value and queue cache time,'
              + 'add new container as follows:'+"\n"
              + '/configuration/qos/policy-map/normal/policy-maps/policy-map/cl'
              + 'ass-maps/class-map/queue-limit/queue-value/queue-value'+"\n"
              + '/configuration/qos/policy-map/normal/policy-maps/policy-map/cl'
              + 'ass-maps/class-map/queue-limit/queue-cache-time/queue-cache-ti'
              + 'me'+"\n"
              + '/configuration/qos/policy-map/normal/policy-maps/policy-map/cl'
              + 'ass-maps/class-default/queue-limit/queue-value/queue-value'+"\n"
              + '/configuration/qos/policy-map/normal/policy-maps/policy-map/cl'
              + 'ass-maps/class-default/queue-limit/queue-cache-time/queue-cach'
              + 'e-time'
                ;
  }
  revision 2019-08-05 {
    description 'Support WRED percentage.'+"\n"
              + 'Add new container as follows:'+"\n"
              + '/configuration/qos/policy-map/normal/policy-maps/policy-map/cl'
              + 'ass-maps/class-map/random-detect/colors/color/threshold-percen'
              + 'tage'+"\n"
              + '/configuration/qos/policy-map/normal/policy-maps/policy-map/cl'
              + 'ass-maps/class-map/random-detect/precedences/precedence/thresh'
              + 'old-percentage'+"\n"
              + '/configuration/qos/policy-map/normal/policy-maps/policy-map/cl'
              + 'ass-maps/class-default/random-detect/colors/color/threshold-pe'
              + 'rcentage'+"\n"
              + '/configuration/qos/policy-map/normal/policy-maps/policy-map/cl'
              + 'ass-maps/class-default/random-detect/precedences/precedence/th'
              + 'reshold-percentage'+"\n"
              + '/configuration/qos/policy-map/phb-based/policy-maps/policy-map'
              + '/class-maps/class-map/random-detect/colors/color/threshold-per'
              + 'centage'+"\n"
              + '/configuration/qos/policy-map/phb-based/policy-maps/policy-map'
              + '/class-maps/class-default/random-detect/colors/color/threshold'
              + '-percentage'+"\n"
              + 'Obsolete nodes as follows:'+"\n"
              + '/configuration/qos/policy-map/phb-based/policy-maps/policy-map'
              + '/class-maps/class-map/random-detect/colors/color/mim-threshold'
              + ''+"\n"
              + '/configuration/qos/policy-map/phb-based/policy-maps/policy-map'
              + '/class-maps/class-map/random-detect/colors/color/max-threshold'
              + ''+"\n"
              + '/configuration/qos/policy-map/phb-based/policy-maps/policy-map'
              + '/class-maps/class-default/random-detect/colors/color/min-thres'
              + 'hold'+"\n"
              + '/configuration/qos/policy-map/phb-based/policy-maps/policy-map'
              + '/class-maps/class-default/random-detect/colors/color/max-thres'
              + 'hold'
                ;
  }
  revision 2019-06-27 {
    description 'Support set next-hop ipv6-address, node modified as follows:'+"\n"
              + '/configuration/qos/policy-map/flow-behavior/policy-maps/policy'
              + '-map/class-maps/class-map/set/next-hop'
                ;
  }
  revision 2019-06-13 {
    description '1.Support the multiple level qos of service-policy, add new en'
              + 'um node:'+"\n"
              + '/configuration/qos/service-policys/service-policy/bound-type'+"\n"
              + '2.Support WRED of queue template, add new container as follows'
              + ':'+"\n"
              + '/configuration/qos/queue-templates/queue-template/queue-nos/qu'
              + 'eue-no/random-detecet'+"\n"
              + '3.Support shape percentage of queue template, node modified as'
              + ' follows:'+"\n"
              + '/configuration/qos/queue-templates/queue-template/queue-nos/qu'
              + 'eue-no/shape'+"\n"
              + '4.Complement the queue depth of queue template, node modified '
              + 'as follows:'+"\n"
              + '/configuration/qos/queue-templates/queue-template/queue-nos/qu'
              + 'eue-no/queue-limit/queue-depth'
                ;
  }
  revision 2019-06-11 {
    description 'Complement the queue depth,nodes modified as follows:'+"\n"
              + '/configuration/qos/policy-map/normal/policy-maps/policy-map/cl'
              + 'ass-maps/class-map/queue-limit/queue-depth.'+"\n"
              + '/configuration/qos/policy-map/normal/policy-maps/policy-map/cl'
              + 'ass-maps/class-default/queue-limit/queue-depth.'
                ;
  }
  revision 2019-04-15 {
    description '1.Support to configure class-map flow-feature, add new contain'
              + 'ers as follows:'+"\n"
              + '/configuration/qos/class-map/flow-feature.'+"\n"
              + '2.Support to configure policy-map flow-behavior, add new conta'
              + 'iners as follows:'+"\n"
              + '/configuration/qos/policy-map/flow-behavior.'
                ;
  }
  revision 2018-09-19 {
    description '1.Support to configure set actions for policy-map car-action-b'
              + 'ased, add new containers as follows:'+"\n"
              + '/configuration/qos/policy-map/car-action/policy-maps/policy-ma'
              + 'p/class-maps/class-map/set.'+"\n"
              + '/configuration/qos/policy-map/car-action/policy-maps/policy-ma'
              + 'p/class-maps/class-default/set.'+"\n"
              + '2.Support to configure bound-type for DS-domian, add new leaf '
              + 'as follows:'+"\n"
              + '/configuration/qos/qos-ds-domains/qos-ds-domain/bound-type'
                ;
  }
  revision 2018-08-30 {
    description 'Support to configure queue template, add new containers as fol'
              + 'lows:'+"\n"
              + '/configuration/qos/queue-templates.'+"\n"
              + '/configuration/qos/queue-interfaces.'
                ;
  }
  revision 2018-08-18 {
    description '1.Support to configure the type of priority remarked by QoS,ad'
              + 'd new containers as follows:'+"\n"
              + '/configuration/qos/qos-prioritys-remark.'+"\n"
              + '2.Support to configure WRED(Weighted Random Early Detection) i'
              + 'nformation under phb-based mode,notes modified as follows:'+"\n"
              + '/configuration/qos/policy-map/phb-based/policy-maps/policy-map'
              + '/class-maps/class-map/random-detect'+"\n"
              + '/configuration/qos/policy-map/phb-based/policy-maps/policy-map'
              + '/class-maps/class-default/random-detect.'
                ;
  }
  revision 2017-09-16 {
    description '1.Extended value range of partial nodes, notes modified as fol'
              + 'lows:'+"\n"
              + '/configuration/qos/policy-map/*/policy-maps/policy-map/class-m'
              + 'aps/class-map/random-detect/precedences/precedence/min-thresho'
              + 'ld'+"\n"
              + '/configuration/qos/policy-map/*/policy-maps/policy-map/class-m'
              + 'aps/class-map/random-detect/precedences/precedence/max-thresho'
              + 'ld'+"\n"
              + '/configuration/qos/policy-map/*/policy-maps/policy-map/class-m'
              + 'aps/class-default/random-detect/precedences/precedence/min-thr'
              + 'eshold'+"\n"
              + '/configuration/qos/policy-map/*/policy-maps/policy-map/class-m'
              + 'aps/class-default/random-detect/precedences/precedence/max-thr'
              + 'eshold'+"\n"
              + '/configuration/qos/policy-map/*/policy-maps/policy-map/class-m'
              + 'aps/class-map/police/cir'+"\n"
              + '/configuration/qos/policy-map/*/policy-maps/policy-map/class-m'
              + 'aps/class-map/police/cbs'+"\n"
              + '/configuration/qos/policy-map/*/policy-maps/policy-map/class-m'
              + 'aps/class-map/police/pir-pbs/pir'+"\n"
              + '/configuration/qos/policy-map/*/policy-maps/policy-map/class-m'
              + 'aps/class-map/police/pir-pbs/pbs'+"\n"
              + '/configuration/qos/policy-map/*/policy-maps/policy-map/class-m'
              + 'aps/class-default/police/cir'+"\n"
              + '/configuration/qos/policy-map/*/policy-maps/policy-map/class-m'
              + 'aps/class-default/police/cbs'+"\n"
              + '/configuration/qos/policy-map/*/policy-maps/policy-map/class-m'
              + 'aps/class-default/police/pir-pbs/pir'+"\n"
              + '/configuration/qos/policy-map/*/policy-maps/policy-map/class-m'
              + 'aps/class-default/police/pir-pbs/pbs'+"\n"
              + '"*" means normal, car-action, phb-based, sub-interface-based, '
              + 'switch-fabric-based'+"\n"
              + '/configuration/qos/rate-limit/*s/*/cir'+"\n"
              + '/configuration/qos/rate-limit/*s/*/cbs'+"\n"
              + '/configuration/qos/rate-limit/*s/*/pir'+"\n"
              + '/configuration/qos/rate-limit/*s/*/pbs'+"\n"
              + '"*" means unicast, multicast, broadcast, unknown, localport, d'
              + 'scp, precedence, mpls-exp, inner-vlan,'+"\n"
              + '    outer-vlan, multi-vlan, inner-8021p, outer-8021p, multi-80'
              + '21p, qos-group, access-list'
                ;
  }
  revision 2017-06-12 {
    description '1.Support to configure address family for flowspec, add new co'
              + 'ntainers as follows:'+"\n"
              + '/configuration/qos/flowspec.'+"\n"
              + '2.Support configuration H-QoS class and policy map related bas'
              + 'ed on the pattern of flowspec,add new containers as follows:'+"\n"
              + 'typedef:qos-port-range.'+"\n"
              + '/configuration/qos/class-map/flowspec-based'+"\n"
              + '/configuration/qos/policy-map/flowspec-based.'+"\n"
              + '3.Support to specify service-type and effect-order of class-ma'
              + 'p, add new containers as follows:'+"\n"
              + '/configuration/qos/class-map/normal/class-maps/class-map/servi'
              + 'ce-type'+"\n"
              + '/configuration/qos/class-map/normal/class-maps/class-map/servi'
              + 'ce-type/effect-order.'+"\n"
              + '4.Support to configure PQ and LLQ of policy-map car-action-bas'
              + 'ed, add new containers as follows:'+"\n"
              + '/configuration/qos/policy-map/car-action/policy-maps/policy-ma'
              + 'p/class-maps/class-map/priority-level'+"\n"
              + '/configuration/qos/policy-map/car-action/policy-maps/policy-ma'
              + 'p/class-maps/class-map/priority-llq'+"\n"
              + '/configuration/qos/policy-map/car-action/policy-maps/policy-ma'
              + 'p/class-maps/class-default/priority-level'+"\n"
              + '/configuration/qos/policy-map/car-action/policy-maps/policy-ma'
              + 'p/class-maps/class-default/priority-llq.'
                ;
  }
  revision 2017-04-14 {
    description 'These if_features support M6000-S as follows:'+"\n"
              + 'switch-fabric-mode'+"\n"
              + 'policy-action-wred-color'+"\n"
              + 'qos-vni-instance'+"\n"
              + 'traffic-shape-dir'
                ;
  }
  revision 2017-02-20 {
    description 'Support set service function chaining, new notes added as foll'
              + 'ows:'+"\n"
              + '/configuration/qos/policy-map/normal/policy-maps/policy-map/cl'
              + 'ass-maps/class-map/set/vlan-id'+"\n"
              + '/configuration/qos/policy-map/normal/policy-maps/policy-map/cl'
              + 'ass-maps/class-map/set/service-query'+"\n"
              + '/configuration/qos/policy-map/normal/policy-maps/policy-map/cl'
              + 'ass-maps/class-map/set/interface'+"\n"
              + '/configuration/qos/policy-map/normal/policy-maps/policy-map/cl'
              + 'ass-maps/class-default/set/vlan-id'+"\n"
              + '/configuration/qos/policy-map/normal/policy-maps/policy-map/cl'
              + 'ass-maps/class-default/set/service-query'+"\n"
              + '/configuration/qos/policy-map/normal/policy-maps/policy-map/cl'
              + 'ass-maps/class-default/set/interface'+"\n"
              + '/configuration/qos/class-map/normal/class-maps/class-map/match'
              + '/ipv4-mixed-acls'
                ;
  }
  revision 2017-01-16 {
    description 'Support set interface traffic shape on the specific direction '
              + ', new notes added as follows:'+"\n"
              + '/configuration/qos/traffic-shape-dirs'
                ;
  }
  revision 2017-01-10 {
    description 'Support set inner and outer flag of set 8021p, new notes added'
              + ' as follows:'+"\n"
              + '/configuration/qos/policy-map/normal/policy-maps/policy-map/cl'
              + 'ass-maps/class-map/set/pri-8021p/set-value/inner-outer'+"\n"
              + '/configuration/qos/policy-map/normal/policy-maps/policy-map/cl'
              + 'ass-maps/class-map/set/pri-8021p/inherit/inner-outer'+"\n"
              + '/configuration/qos/policy-map/normal/policy-maps/policy-map/cl'
              + 'ass-maps/class-default/set/pri-8021p/set-value/inner-outer'+"\n"
              + '/configuration/qos/policy-map/normal/policy-maps/policy-map/cl'
              + 'ass-maps/class-default/set/pri-8021p/inherit/inner-outer'+"\n"
              + '/configuration/qos/rate-limit/unicasts/unicast/conform-action/'
              + 'set-8021p-transmit/inner-outer'+"\n"
              + '/configuration/qos/rate-limit/unknown-unicasts/unknown-unicast'
              + '/conform-action/set-8021p-transmit/inner-outer'+"\n"
              + '/configuration/qos/rate-limit/multicasts/multicast/conform-act'
              + 'ion/set-8021p-transmit/inner-outer'+"\n"
              + '/configuration/qos/rate-limit/unknown-multicasts/unknown-multi'
              + 'cast/conform-action/set-8021p-transmit/inner-outer'+"\n"
              + '/configuration/qos/rate-limit/broadcasts/broadcast/conform-act'
              + 'ion/set-8021p-transmit/inner-outer'+"\n"
              + '/configuration/qos/rate-limit/unknowns/unknown/conform-action/'
              + 'set-8021p-transmit/inner-outer'+"\n"
              + '/configuration/qos/rate-limit/localports/localport/conform-act'
              + 'ion/set-8021p-transmit/inner-outer'+"\n"
              + '/configuration/qos/rate-limit/dscps/dscp/conform-action/set-80'
              + '21p-transmit/inner-outer'+"\n"
              + '/configuration/qos/rate-limit/precedences/precedence/conform-a'
              + 'ction/set-8021p-transmit/inner-outer'+"\n"
              + '/configuration/qos/rate-limit/mpls-exps/mpls-exp/conform-actio'
              + 'n/set-8021p-transmit/inner-outer'+"\n"
              + '/configuration/qos/rate-limit/inner-vlans/inner-vlan/conform-a'
              + 'ction/set-8021p-transmit/inner-outer'+"\n"
              + '/configuration/qos/rate-limit/outer-vlans/outer-vlan/conform-a'
              + 'ction/set-8021p-transmit/inner-outer'+"\n"
              + '/configuration/qos/rate-limit/multi-vlans/multi-vlan/conform-a'
              + 'ction/set-8021p-transmit/inner-outer'+"\n"
              + '/configuration/qos/rate-limit/inner-8021ps/inner-8021p/conform'
              + '-action/set-8021p-transmit/inner-outer'+"\n"
              + '/configuration/qos/rate-limit/outer-8021ps/outer-8021p/conform'
              + '-action/set-8021p-transmit/inner-outer'+"\n"
              + '/configuration/qos/rate-limit/multi-8021ps/multi-8021p/conform'
              + '-action/set-8021p-transmit/inner-outer'+"\n"
              + '/configuration/qos/rate-limit/qos-groups/qos-group/conform-act'
              + 'ion/set-8021p-transmit/inner-outer'+"\n"
              + '/configuration/qos/rate-limit/access-lists/access-list/conform'
              + '-action/set-8021p-transmit/inner-outer'+"\n"
              + '/configuration/qos/rate-limit/unicasts/unicast/exceed-action/s'
              + 'et-8021p-transmit/inner-outer'+"\n"
              + '/configuration/qos/rate-limit/unknown-unicasts/unknown-unicast'
              + '/exceed-action/set-8021p-transmit/inner-outer'+"\n"
              + '/configuration/qos/rate-limit/multicasts/multicast/exceed-acti'
              + 'on/set-8021p-transmit/inner-outer'+"\n"
              + '/configuration/qos/rate-limit/unknown-multicasts/unknown-multi'
              + 'cast/exceed-action/set-8021p-transmit/inner-outer'+"\n"
              + '/configuration/qos/rate-limit/broadcasts/broadcast/exceed-acti'
              + 'on/set-8021p-transmit/inner-outer'+"\n"
              + '/configuration/qos/rate-limit/unknowns/unknown/exceed-action/s'
              + 'et-8021p-transmit/inner-outer'+"\n"
              + '/configuration/qos/rate-limit/localports/localport/exceed-acti'
              + 'on/set-8021p-transmit/inner-outer'+"\n"
              + '/configuration/qos/rate-limit/dscps/dscp/exceed-action/set-802'
              + '1p-transmit/inner-outer'+"\n"
              + '/configuration/qos/rate-limit/precedences/precedence/exceed-ac'
              + 'tion/set-8021p-transmit/inner-outer'+"\n"
              + '/configuration/qos/rate-limit/mpls-exps/mpls-exp/exceed-action'
              + '/set-8021p-transmit/inner-outer'+"\n"
              + '/configuration/qos/rate-limit/inner-vlans/inner-vlan/exceed-ac'
              + 'tion/set-8021p-transmit/inner-outer'+"\n"
              + '/configuration/qos/rate-limit/outer-vlans/outer-vlan/exceed-ac'
              + 'tion/set-8021p-transmit/inner-outer'+"\n"
              + '/configuration/qos/rate-limit/multi-vlans/multi-vlan/exceed-ac'
              + 'tion/set-8021p-transmit/inner-outer'+"\n"
              + '/configuration/qos/rate-limit/inner-8021ps/inner-8021p/exceed-'
              + 'action/set-8021p-transmit/inner-outer'+"\n"
              + '/configuration/qos/rate-limit/outer-8021ps/outer-8021p/exceed-'
              + 'action/set-8021p-transmit/inner-outer'+"\n"
              + '/configuration/qos/rate-limit/multi-8021ps/multi-8021p/exceed-'
              + 'action/set-8021p-transmit/inner-outer'+"\n"
              + '/configuration/qos/rate-limit/qos-groups/qos-group/exceed-acti'
              + 'on/set-8021p-transmit/inner-outer'+"\n"
              + '/configuration/qos/rate-limit/access-lists/access-list/exceed-'
              + 'action/set-8021p-transmit/inner-outer'+"\n"
              + '/configuration/qos/rate-limit/unicasts/unicast/violate-action/'
              + 'set-8021p-transmit/inner-outer'+"\n"
              + '/configuration/qos/rate-limit/unknown-unicasts/unknown-unicast'
              + '/violate-action/set-8021p-transmit/inner-outer'+"\n"
              + '/configuration/qos/rate-limit/multicasts/multicast/violate-act'
              + 'ion/set-8021p-transmit/inner-outer'+"\n"
              + '/configuration/qos/rate-limit/unknown-multicasts/unknown-multi'
              + 'cast/violate-action/set-8021p-transmit/inner-outer'+"\n"
              + '/configuration/qos/rate-limit/broadcasts/broadcast/violate-act'
              + 'ion/set-8021p-transmit/inner-outer'+"\n"
              + '/configuration/qos/rate-limit/unknowns/unknown/violate-action/'
              + 'set-8021p-transmit/inner-outer'+"\n"
              + '/configuration/qos/rate-limit/localports/localport/violate-act'
              + 'ion/set-8021p-transmit/inner-outer'+"\n"
              + '/configuration/qos/rate-limit/dscps/dscp/violate-action/set-80'
              + '21p-transmit/inner-outer'+"\n"
              + '/configuration/qos/rate-limit/precedences/precedence/violate-a'
              + 'ction/set-8021p-transmit/inner-outer'+"\n"
              + '/configuration/qos/rate-limit/mpls-exps/mpls-exp/violate-actio'
              + 'n/set-8021p-transmit/inner-outer'+"\n"
              + '/configuration/qos/rate-limit/inner-vlans/inner-vlan/violate-a'
              + 'ction/set-8021p-transmit/inner-outer'+"\n"
              + '/configuration/qos/rate-limit/outer-vlans/outer-vlan/violate-a'
              + 'ction/set-8021p-transmit/inner-outer'+"\n"
              + '/configuration/qos/rate-limit/multi-vlans/multi-vlan/violate-a'
              + 'ction/set-8021p-transmit/inner-outer'+"\n"
              + '/configuration/qos/rate-limit/inner-8021ps/inner-8021p/violate'
              + '-action/set-8021p-transmit/inner-outer'+"\n"
              + '/configuration/qos/rate-limit/outer-8021ps/outer-8021p/violate'
              + '-action/set-8021p-transmit/inner-outer'+"\n"
              + '/configuration/qos/rate-limit/multi-8021ps/multi-8021p/violate'
              + '-action/set-8021p-transmit/inner-outer'+"\n"
              + '/configuration/qos/rate-limit/qos-groups/qos-group/violate-act'
              + 'ion/set-8021p-transmit/inner-outer'+"\n"
              + '/configuration/qos/rate-limit/access-lists/access-list/violate'
              + '-action/set-8021p-transmit/inner-outer'
                ;
  }
  revision 2016-12-20 {
    description '1.Support priority(MPLS-EXP,DSCP,802.1p) range configuration, '
              + 'mapped to Per Hop Behavior, and in order to compatible with pr'
              + 'evious versions, add new priority(MPLS-EXP,DSCP,802.1p) single'
              + ' configuration containers, discard the old containers in this '
              + 'version, new notes added as follows:'+"\n"
              + '/configuration/qos/diffserv/ds-domains/ds-domain/map/pri-8021p'
              + '-singles'+"\n"
              + '/configuration/qos/diffserv/ds-domains/ds-domain/map/pri-8021p'
              + '-ranges'+"\n"
              + '/configuration/qos/diffserv/ds-domains/ds-domain/map/mpls-exp-'
              + 'singles'+"\n"
              + '/configuration/qos/diffserv/ds-domains/ds-domain/map/mpls-exp-'
              + 'ranges'+"\n"
              + '/configuration/qos/diffserv/ds-domains/ds-domain/map/ipv4-dscp'
              + '-singles'+"\n"
              + '/configuration/qos/diffserv/ds-domains/ds-domain/map/ipv4-dscp'
              + '-ranges'+"\n"
              + '/configuration/qos/diffserv/ds-domains/ds-domain/map/ipv6-dscp'
              + '-singles'+"\n"
              + '/configuration/qos/diffserv/ds-domains/ds-domain/map/ipv6-dscp'
              + '-ranges.'+"\n"
              + 'discard notes as follows:'+"\n"
              + '/configuration/qos/diffserv/ds-domains/ds-domain/map/pri-8021p'
              + 's'+"\n"
              + '/configuration/qos/diffserv/ds-domains/ds-domain/map/mpls-exps'
              + ''+"\n"
              + '/configuration/qos/diffserv/ds-domains/ds-domain/map/ipv4-dscp'
              + 's'+"\n"
              + '/configuration/qos/diffserv/ds-domains/ds-domain/map/ipv6-dscp'
              + 's'
                ;
  }
  revision 2016-07-20 {
    description 'Modify switch-fabric '+"\n"
              + '/configuration/qos/switch-fabric/normals/normal/mode          '
              + 'delete switch-port type'+"\n"
              + '/configuration/qos/switch-fabric/subslots/group1s/group1/mode '
              + 'delete switch-port type'+"\n"
              + '/configuration/qos/switch-fabric/subslots/group2s/group2/mode '
              + 'delete switch-port type'+"\n"
              + '/configuration/qos/switch-fabric/subslots/ports/port/mode     '
              + 'add switch-port type'
                ;
  }
  revision 2016-06-30 {
    description '1.Support setting dscp inherit-from pay-load 8021p'+"\n"
              + 'add new type pay-load 8021p to inherit-type:'+"\n"
              + '/configuration/qos/policy-map/normal/policy-maps/class-maps/cl'
              + 'ass-map/set/dscp/inherit/inherit-type'+"\n"
              + '/configuration/qos/policy-map/normal/policy-maps/class-default'
              + '/set/dscp/inherit/inherit-type'+"\n"
              + '2.Support binding policy-map to vni-instance'+"\n"
              + 'add new containers as follow:'+"\n"
              + '/configuration/qos/vni-instances/vni-instance'
                ;
  }
  revision 2016-05-03 {
    description '1.Support PW schedule statistic switch, and support to clear P'
              + 'W schedule statistic data, add new containers as follows:'+"\n"
              + '/configuration/qos/pw-schedule-stats/stats-switches'+"\n"
              + '/operation/qos/stats-clear/pw-schedules'
                ;
  }
  revision 2015-11-04 {
    description '1. Support VNI (VXLAN Network Identifier) for class-map match '
              + 'item, add new nodes as follow:'+"\n"
              + 'container  /qos:configuration/qos:qos/qos:class-map/qos:normal'
              + '/qos:class-maps/qos:class-map/qos:match/qos:vni'+"\n"
              + '2. Support the switch of QoS flow statistics, add new nodes as'
              + ' follow:'+"\n"
              + 'container  /qos:configuration/qos:qos/qos:qos-stats'
                ;
  }
  revision 2015-10-28 {
    description '1.Support matching unknown-multicast, unknown-unicast for rate'
              + ' limit, add new containers as follows:'+"\n"
              + '/configuration/qos/rate-limit/unknown-unicasts'+"\n"
              + '/configuration/qos/rate-limit/unknown-multicasts'
                ;
  }
  revision 2015-04-15 {
    description '1.In order to compatible with previous versions, add a new con'
              + 'tainer [qos-policy-exs], discard the old container [qos-policy'
              + 's] in this version, modify as follows,'+"\n"
              + 'discard the container:'+"\n"
              + '  /configuration/qos/qos-policys'+"\n"
              + 'the new container:'+"\n"
              + '  /configuration/qos/qos-policy-exs'
                ;
  }
  revision 2015-03-31 {
    description '1.In order to support graphical display for NM, add new contai'
              + 'ner notes as follow:'+"\n"
              + '  container: /configuration/qos/class-map/class-map-id'+"\n"
              + '  container: /configuration/qos/policy-map/policy-map-id'
                ;
  }
  revision 2015-03-27 {
    description '1.Expand the max range value (10G modified to 100G) of rate,re'
              + 'fering to traffic-shape, modifying as follows:'+"\n"
              + '/configuration/qos/traffic-shapes/traffic-shape/rate'
                ;
  }
  revision 2015-02-09 {
    description '1.Modify to support [not] opposite range flag for class-map ma'
              + 'tch DSCP/PRECEDENCE item, add new nodes as follow:'+"\n"
              + '  leaf: /configuration/qos/class-map/normal/class-maps/class-m'
              + 'ap/match/dscps/dscp/not'+"\n"
              + '  leaf: /configuration/qos/class-map/normal/class-maps/class-m'
              + 'ap/match/precedences/precedence/not'+"\n"
              + '  '+"\n"
              + '2.modify to convert removing queue-schedule[container] to rese'
              + 'tting priority-level/wfq-weight, set DELETE2RESET OperationCha'
              + 'ngeType for the path notes as follow:'+"\n"
              + '  container: /configuration/qos/qos-schedules/interfaces/inter'
              + 'face/schedule/sche-group/queue-schedule'+"\n"
              + '  choice: /configuration/qos/qos-schedules/interfaces/interfac'
              + 'e/schedule/sche-group/queue-schedule/queue-schedule'+"\n"
              + '  case: /configuration/qos/qos-schedules/interfaces/interface/'
              + 'schedule/sche-group/queue-schedule/queue-schedule/pq'+"\n"
              + '  case: /configuration/qos/qos-schedules/interfaces/interface/'
              + 'schedule/sche-group/queue-schedule/queue-schedule/wfq'+"\n"
              + '  '+"\n"
              + '  container: /configuration/qos/qos-schedules/pws/pw/schedule/'
              + 'sche-group/queue-schedule'+"\n"
              + '  choice: /configuration/qos/qos-schedules/pws/pw/schedule/sch'
              + 'e-group/queue-schedule/queue-schedule'+"\n"
              + '  case: /configuration/qos/qos-schedules/pws/pw/schedule/sche-'
              + 'group/queue-schedule/queue-schedule/pq'+"\n"
              + '  case: /configuration/qos/qos-schedules/pws/pw/schedule/sche-'
              + 'group/queue-schedule/queue-schedule/wfq'
                ;
  }
  revision 2014-10-20 {
    description "1.'.'as illegal named character ,modify all node names involvi"
              + "ng 802.1p, specific as follows:
\n   -802.1p       convert to "
              + " -8021p   e.g. in-802.1p-value  convert to in-8021p-value;
\n "
              + "  _802.1p-value convert to  value-8021p;
\n   _802.1p       co"
              + "nvert to  pri-8021p;
\n   enum 802.1p   convert to  enum 8021p"
              + ";
\n2. WRED,police and car support unit selection, add new nod"
              + "es as follow:
\nAdd typedef: qos-rate-unit-type,qos-bucket-uni"
              + "t-type,qos-threshold-unit-type
\nAdd unit selection nodes:
\n/"
              + "configuration/qos/policy-map/*/policy-maps/policy-map/class-ma"
              + "ps/class-map/random-detect/precedences/precedence/min-threshol"
              + "d-unit
\n/configuration/qos/policy-map/*/policy-maps/policy-ma"
              + "p/class-maps/class-map/random-detect/precedences/precedence/ma"
              + "x-threshold-unit
\n/configuration/qos/policy-map/*/policy-maps"
              + "/policy-map/class-maps/class-default/random-detect/precedences"
              + "/precedence/min-threshold-unit
\n/configuration/qos/policy-map"
              + "/*/policy-maps/policy-map/class-maps/class-default/random-dete"
              + "ct/precedences/precedence/max-threshold-unit
\n/configuration/"
              + "qos/policy-map/*/policy-maps/policy-map/class-maps/class-map/p"
              + "olice/cir-unit
\n/configuration/qos/policy-map/*/policy-maps/p"
              + "olicy-map/class-maps/class-map/police/cbs-unit
\n/configuratio"
              + "n/qos/policy-map/*/policy-maps/policy-map/class-maps/class-map"
              + "/police/pir-pbs/pir-unit
\n/configuration/qos/policy-map/*/pol"
              + "icy-maps/policy-map/class-maps/class-map/police/pir-pbs/pbs-un"
              + "it
\n/configuration/qos/policy-map/*/policy-maps/policy-map/cl"
              + "ass-maps/class-default/police/cir-unit
\n/configuration/qos/po"
              + "licy-map/*/policy-maps/policy-map/class-maps/class-default/pol"
              + "ice/cbs-unit
\n/configuration/qos/policy-map/*/policy-maps/pol"
              + "icy-map/class-maps/class-default/police/pir-pbs/pir-unit
\n/co"
              + "nfiguration/qos/policy-map/*/policy-maps/policy-map/class-maps"
              + "/class-default/police/pir-pbs/pbs-unit
\n\"*\" means normal, c"
              + "ar-action, phb-based, sub-interface-based, switch-fabric-based"
              + "
\n/configuration/qos/rate-limit/*s/*/cir-unit
\n/configuratio"
              + "n/qos/rate-limit/*s/*/pir-unit
\n\"*\" means unicast, multicas"
              + "t, broadcast, unknown, localport, dscp, precedence, mpls-exp, "
              + "inner-vlan,
\n    outer-vlan, multi-vlan, inner-8021p, outer-8"
              + "021p,multi-8021p, qos-group, access-list
\n3. Car supports the"
              + " configuration of inner and outer MPLS-EXP:
\n/configuration/q"
              + "os/policy-map/car-action/policy-maps/policy-map/class-maps/cla"
              + "ss-map/police/conform-action/ca-mpls-exp/mpls-label-type
\n/co"
              + "nfiguration/qos/policy-map/car-action/policy-maps/policy-map/c"
              + "lass-maps/class-map/police/conform-action/ca-multi-exp-transmi"
              + "t
\n/configuration/qos/policy-map/car-action/policy-maps/polic"
              + "y-map/class-maps/class-map/police/exceed-action/ea-mpls-exp/mp"
              + "ls-label-type
\n/configuration/qos/policy-map/car-action/polic"
              + "y-maps/policy-map/class-maps/class-map/police/exceed-action/ea"
              + "-multi-exp-transmit
\n/configuration/qos/policy-map/car-action"
              + "/policy-maps/policy-map/class-maps/class-map/police/violate-ac"
              + "tion/va-mpls-exp/mpls-label-type
\n/configuration/qos/policy-m"
              + "ap/car-action/policy-maps/policy-map/class-maps/class-map/poli"
              + "ce/violate-action/va-multi-exp-transmit
\n/configuration/qos/p"
              + "olicy-map/car-action/policy-maps/policy-map/class-maps/class-d"
              + "efault/police/conform-action/ca-mpls-exp/mpls-label-type
\n/co"
              + "nfiguration/qos/policy-map/car-action/policy-maps/policy-map/c"
              + "lass-maps/class-default/police/conform-action/ca-multi-exp-tra"
              + "nsmit
\n/configuration/qos/policy-map/car-action/policy-maps/p"
              + "olicy-map/class-maps/class-default/police/exceed-action/ea-mpl"
              + "s-exp/mpls-label-type
\n/configuration/qos/policy-map/car-acti"
              + "on/policy-maps/policy-map/class-maps/class-default/police/exce"
              + "ed-action/ea-multi-exp-transmit
\n/configuration/qos/policy-ma"
              + "p/car-action/policy-maps/policy-map/class-maps/class-default/p"
              + "olice/violate-action/va-mpls-exp/mpls-label-type
\n/configurat"
              + "ion/qos/policy-map/car-action/policy-maps/policy-map/class-map"
              + "s/class-default/police/violate-action/va-multi-exp-transmit
\n"
              + "/configuration/qos/rate-limit/*s/*/conform-action/ca-mpls-exp/"
              + "set-exp-transmit/mpls-label-type
\n/configuration/qos/rate-lim"
              + "it/*s/*/conform-action/ca-multi-exp/set-multi-exp-transmit
\n/"
              + "configuration/qos/rate-limit/*s/*/exceed-action/ea-mpls-exp/se"
              + "t-exp-transmit/mpls-label-type
\n/configuration/qos/rate-limit"
              + "/*s/*/exceed-action/ea-multi-exp/set-multi-exp-transmit
\n/con"
              + "figuration/qos/rate-limit/*s/*/violate-action/va-mpls-exp/set-"
              + "exp-transmit/mpls-label-type
\n/configuration/qos/rate-limit/*"
              + "s/*/violate-action/va-multi-exp/set-multi-exp-transmit
\n\"*\""
              + " means unicast, multicast, broadcast, unknown, localport, dscp"
              + ", precedence, mpls-exp, inner-vlan,
\n    outer-vlan, multi-vl"
              + "an, inner-8021p, outer-8021p, multi-8021p, qos-group, access-l"
              + "ist
\n4. Modify the configuration of switch-fabrics:
\n/config"
              + "uration/qos/switch-fabrics/normals/normal
\n/configuration/qos"
              + "/switch-fabrics/subslots/subslot
\n/configuration/qos/switch-f"
              + "abrics/subslots/group1s/group1
\n/configuration/qos/switch-fab"
              + "rics/subslots/group2s/group2\n/configuration/qos/switch-fabric"
              + "s/subslots/ports/port
\n5. Modify the configuration of qos-dot"
              + "1p, support cvlan-out, add new nodes as follow:
\n/configurati"
              + "on/qos/qos-dot1p/cvlan-outs/cvlan-outs"
                ;
  }
  revision 2014-04-30 {
    description 'Initial version'
                ;
  }
  feature phb-mode {
    description 'Support configuration H-QoS class and policy map related based'
              + ' on the pattern of PHB'
                ;
  }
  feature sub-interface-mode {
    description 'Support configuration H-QoS class and policy map related based'
              + ' on the pattern of sub-interface'
                ;
  }
  feature switch-fabric-mode {
    description 'Support configuration H-QoS class and policy map related based'
              + ' on the pattern of switch-fabric'
                ;
  }
  feature car-action-mode {
    description 'Support configuration H-QoS policy map related based on the pa'
              + 'ttern of car-action'
                ;
  }
  feature normal-mode {
    description 'Support configuration H-QoS class and policy map related based'
              + ' on normal pattern'
                ;
  }
  feature diffserv {
    description 'Support the configuration of differentiated Services'
                ;
  }
  feature qos-ds-domains {
    description 'Configure the used diffserv domain template'
                ;
  }
  feature qos-prioritys {
    description 'Configure the type of priority trusted by QoS'
                ;
  }
  feature qos-schedule {
    description 'Support scheduling policy for a certain transmitting entity'
                ;
  }
  feature switch-fabric {
    description 'Configure H-QoS switch fabric policy bind'
                ;
  }
  feature traffic-shape {
    description 'Support configuration traffic shape related'
                ;
  }
  feature service-policy {
    description 'Support configuration about binding H-QoS policys to the inter'
              + 'face'
                ;
  }
  feature class-match-dscp-ex {
    description 'Support to set DSCP value as match criteria in PHB mode'
                ;
  }
  feature class-match-link-acl {
    description 'Support to configure link ACL as match criteria'
                ;
  }
  feature class-match-protocol {
    description 'Support to configure DPI protocol as match criteria'
                ;
  }
  feature policy-action-drop {
    description 'Support to configure policy action, such as drop'
                ;
  }
  feature policy-action-shape {
    description 'Support to configure policy action, such as shape'
                ;
  }
  feature policy-action-wred-color {
    description 'Support to configure policy action, such as WRED based on color'
                ;
  }
  feature policy-action-set-label {
    description 'Support to configure policy action, such as set, specify MPLS-'
              + 'EXP label position'
                ;
  }
  feature policy-action-set-multi-exp {
    description 'Support to configure policy action, such as set multiple MPLS-'
              + 'EXP'
                ;
  }
  feature qos-car-mode {
    description 'Support color mode information, such as Color-Blind and Color-'
              + 'Aware mode'
                ;
  }
  feature qos-vni-instance {
    description 'Support configuration about binding H-QoS policys to the vni-i'
              + 'nstance'
                ;
  }
  feature traffic-shape-dir {
    description 'Support configuration interface traffic shape on the specific '
              + 'direction'
                ;
  }
  feature qos-prioritys-remark {
    description 'Configure the type of priority remarked by QoS'
                ;
  }
  feature policy-action-rediret-route-map {
    description 'Support to configure policy action, such as redirect route-map'
                ;
  }
  feature policy-action-vlan-stacking {
    description 'Support to configure policy action, such as vlan-stacking'
                ;
  }
  feature qos-global-prioritys-remark {
    description 'Configure the type of global priority and the global modificat'
              + 'ion enable switch of QoS.'
                ;
  }
  feature ds-interf-priority-remark-enable {
    description 'Configure the interface priority modification is enabled or di'
              + 'sable.'
                ;
  }
  feature car-buket-value-percent {
    description 'Support cir, pir, cbs and pbs, both in numerical form and perc'
              + 'entage form.'
                ;
  }
  feature traffic-policy {
    description 'Support configuration about binding QoS policys to the interfa'
              + 'ce'
                ;
  }
  feature qos-pw-ds-domains {
    description 'Configure the used diffserv domain template by PW interface.'
                ;
  }
  typedef qos-dscp-bitmap {
    type ncd:bitmap {
      pattern '(((((([1-9][0-9]{0,0})|0|([1-5][0-9]{1,1})|(6[0-2])|63)-(([1-9]['
            + '0-9]{0,0})|0|([1-5][0-9]{1,1})|(6[0-2])|63))|(([1-9][0-9]{0,0})|'
            + '0|([1-5][0-9]{1,1})|(6[0-2])|63)),){0,3}(((([1-9][0-9]{0,0})|0|('
            + '[1-5][0-9]{1,1})|(6[0-2])|63)-(([1-9][0-9]{0,0})|0|([1-5][0-9]{1'
            + ',1})|(6[0-2])|63))|(([1-9][0-9]{0,0})|0|([1-5][0-9]{1,1})|(6[0-2'
            + '])|63)){1,1})'
              {
        description 'Configure DSCP in range mode, support single DSCP value or'
                  + ' range(max num:4;spacing mark:,) in <0-63>.'
                    ;
      }
    }
    description 'The definition of QoS dscp in range mode, support single DSCP '
              + 'value or range(max num:4;spacing mark:,) in <0-63>. For exampl'
              + 'e,"6,10-30,40,50-60",etc.'
                ;
  }
  typedef qos-prec-bitmap {
    type ncd:bitmap {
      pattern '(((([0-7]-[0-7])|[0-7]),){0,3}(([0-7]-[0-7])|([0-7])){1,1})'
              {
        description 'Configure IP-Precedence in range mode, support single prec'
                  + 'edence value or range(max num:4;spacing mark:,) in <0-7>.'
                    ;
      }
    }
    description 'The definition of QoS IP-Precedence in range mode, support sin'
              + 'gle precedence value or range(max num:4;spacing mark:,) in <0-'
              + '7>. For example,"0,4-7",etc.'
                ;
  }
  typedef qos-vlan-bitmap {
    type ncd:bitmap {
      pattern '(((((([1-9][0-9]{1,2})|([2-9][0-9]{0,0})|1|([1-3][0-9]{3,3})|(40'
            + '[0-8][0-9]{1,1})|(409[0-3])|4094)-(([1-9][0-9]{1,2})|([2-9][0-9]'
            + '{0,0})|1|([1-3][0-9]{3,3})|(40[0-8][0-9]{1,1})|(409[0-3])|4094))'
            + '|(([1-9][0-9]{1,2})|([2-9][0-9]{0,0})|1|([1-3][0-9]{3,3})|(40[0-'
            + '8][0-9]{1,1})|(409[0-3])|4094)),){0,3}(((([1-9][0-9]{1,2})|([2-9'
            + '][0-9]{0,0})|1|([1-3][0-9]{3,3})|(40[0-8][0-9]{1,1})|(409[0-3])|'
            + '4094)-(([1-9][0-9]{1,2})|([2-9][0-9]{0,0})|1|([1-3][0-9]{3,3})|('
            + '40[0-8][0-9]{1,1})|(409[0-3])|4094))|(([1-9][0-9]{1,2})|([2-9][0'
            + '-9]{0,0})|1|([1-3][0-9]{3,3})|(40[0-8][0-9]{1,1})|(409[0-3])|409'
            + '4)){1,1})'
              {
        description 'Configure VLAN in range mode, support single VLAN value or'
                  + ' range(max num:4;spacing mark:,) in <1-4094>.'
                    ;
      }
    }
    description 'The definition of QoS VLAN in range mode, support single VLAN '
              + 'value or range(max num:4;spacing mark:,) in <1-4094>. For exam'
              + 'ple,"1-300,400,450-500",etc.'
                ;
  }
  typedef qos-mpls-bitmap {
    type ncd:bitmap {
      pattern '(((([0-7]-[0-7])|[0-7]),){0,3}(([0-7]-[0-7])|([0-7])){1,1})'
              {
        description 'Configure MPLS-EXP in range mode, support single MPLS-EXP '
                  + 'value or range(max num:4;spacing mark:,) in <0-7>.'
                    ;
      }
    }
    description 'The definition of QoS MPLS-EXP in range mode, support single M'
              + 'PLS-EXP value or range(max num:4;spacing mark:,) in <0-7>. For'
              + ' example,"0,3-5,7",etc.'
                ;
  }
  typedef qos-8021p-bitmap {
    type ncd:bitmap {
      pattern '(((([0-7]-[0-7])|[0-7]),){0,3}(([0-7]-[0-7])|([0-7])){1,1})'
              {
        description 'Configure 802.1p in range mode, support single 802.1p valu'
                  + 'e or range(max num:4;spacing mark:,) in <0-7>.'
                    ;
      }
    }
    description 'The definition of QoS 802.1p in range mode, support single 802'
              + '.1p value or range(max num:4;spacing mark:,) in <0-7>. For exa'
              + 'mple,"0,3-5,7",etc.'
                ;
  }
  typedef qos-vlan-range {
    type ncd:range {
      pattern '(((((([1-9][0-9]{1,2})|([2-9][0-9]{0,0})|1|([1-3][0-9]{3,3})|(40'
            + '[0-8][0-9]{1,1})|(409[0-3])|4094)-(([1-9][0-9]{1,2})|([2-9][0-9]'
            + '{0,0})|1|([1-3][0-9]{3,3})|(40[0-8][0-9]{1,1})|(409[0-3])|4094))'
            + '|(([1-9][0-9]{1,2})|([2-9][0-9]{0,0})|1|([1-3][0-9]{3,3})|(40[0-'
            + '8][0-9]{1,1})|(409[0-3])|4094)),){0,3}(((([1-9][0-9]{1,2})|([2-9'
            + '][0-9]{0,0})|1|([1-3][0-9]{3,3})|(40[0-8][0-9]{1,1})|(409[0-3])|'
            + '4094)-(([1-9][0-9]{1,2})|([2-9][0-9]{0,0})|1|([1-3][0-9]{3,3})|('
            + '40[0-8][0-9]{1,1})|(409[0-3])|4094))|(([1-9][0-9]{1,2})|([2-9][0'
            + '-9]{0,0})|1|([1-3][0-9]{3,3})|(40[0-8][0-9]{1,1})|(409[0-3])|409'
            + '4)){1,1})'
              {
        description 'Configure VLAN in range mode, support single VLAN value or'
                  + ' range(max num:4;spacing mark:,) in <1-4094>.'
                    ;
      }
    }
    description 'The definition of QoS VLAN in range mode, support single VLAN '
              + 'value or range(max num:4;spacing mark:,) in <1-4094>. For exam'
              + 'ple,"1-300,400,450-500",etc.'
                ;
  }
  typedef qos-service-class {
    type enumeration {
      enum be {
        value 1 ;
        description 'Best effort'
                    ;
      }
      enum af1 {
        value 2 ;
        description 'Assured forwarding class 1'
                    ;
      }
      enum af2 {
        value 3 ;
        description 'Assured forwarding class 2'
                    ;
      }
      enum af3 {
        value 4 ;
        description 'Assured forwarding class 3'
                    ;
      }
      enum af4 {
        value 5 ;
        description 'Assured forwarding class 4'
                    ;
      }
      enum ef {
        value 6 ;
        description 'Expedited forward'
                    ;
      }
      enum cs6 {
        value 7 ;
        description 'Internetwork control service class'
                    ;
      }
      enum cs7 {
        value 8 ;
        description 'Network control service class'
                    ;
      }
    }
    description 'The definition of server class of PHB info, see below:'+"\n"
              + '             be (1) Best effort'+"\n"
              + '             af1(2) Assured forwarding class 1'+"\n"
              + '             af2(3) Assured forwarding class 2'+"\n"
              + '             af3(4) Assured forwarding class 3'+"\n"
              + '             af4(5) Assured forwarding class 4'+"\n"
              + '             ef (6) Expedited forward'+"\n"
              + '             cs6(7) Internetwork control service class'+"\n"
              + '             cs7(8) Network control service class'
                ;
  }
  typedef qos-color-type {
    type enumeration {
      enum green {
        value 1 ;
        description 'Green packets'
                    ;
      }
      enum yellow {
        value 2 ;
        description 'Yellow packets'
                    ;
      }
      enum red {
        value 3 ;
        description 'Red packets'
                    ;
      }
    }
    description 'The definition of color type of PHB info, see below:'+"\n"
              + '             green  (1) Green packets'+"\n"
              + '             yellow (2) Yellow packets'+"\n"
              + '             red    (3) Red packets'
                ;
  }
  typedef qos-reserved-words {
    type enumeration {
      enum default {
        value 0 ;
        description 'Match packets with default dscp (000000)'
                    ;
      }
      enum af11 {
        value 10 ;
        description 'Match packets with AF11 dscp (001010)'
                    ;
      }
      enum af12 {
        value 12 ;
        description 'Match packets with AF12 dscp (001100)'
                    ;
      }
      enum af13 {
        value 14 ;
        description 'Match packets with AF13 dscp (001110)'
                    ;
      }
      enum af21 {
        value 18 ;
        description 'Match packets with AF21 dscp (010010)'
                    ;
      }
      enum af22 {
        value 20 ;
        description 'Match packets with AF22 dscp (010100)'
                    ;
      }
      enum af23 {
        value 22 ;
        description 'Match packets with AF23 dscp (010110)'
                    ;
      }
      enum af31 {
        value 26 ;
        description 'Match packets with AF31 dscp (011010)'
                    ;
      }
      enum af32 {
        value 28 ;
        description 'Match packets with AF32 dscp (011100)'
                    ;
      }
      enum af33 {
        value 30 ;
        description 'Match packets with AF33 dscp (011110)'
                    ;
      }
      enum af41 {
        value 34 ;
        description 'Match packets with AF41 dscp (100010)'
                    ;
      }
      enum af42 {
        value 36 ;
        description 'Match packets with AF42 dscp (100100)'
                    ;
      }
      enum af43 {
        value 38 ;
        description 'Match packets with AF43 dscp (100110)'
                    ;
      }
      enum ef {
        value 46 ;
        description 'Match packets with EF dscp (101110)'
                    ;
      }
      enum cs1 {
        value 8 ;
        description 'Match packets with CS1(precedence 1) dscp (001000)'
                    ;
      }
      enum cs2 {
        value 16 ;
        description 'Match packets with CS2(precedence 2) dscp (010000)'
                    ;
      }
      enum cs3 {
        value 24 ;
        description 'Match packets with CS3(precedence 3) dscp (011000)'
                    ;
      }
      enum cs4 {
        value 32 ;
        description 'Match packets with CS4(precedence 4) dscp (100000)'
                    ;
      }
      enum cs5 {
        value 40 ;
        description 'Match packets with CS5(precedence 5) dscp (101000)'
                    ;
      }
      enum cs6 {
        value 48 ;
        description 'Match packets with CS6(precedence 6) dscp (110000)'
                    ;
      }
      enum cs7 {
        value 56 ;
        description 'Match packets with CS7(precedence 7) dscp (111000)'
                    ;
      }
    }
    description 'The definition of resserved words of DSCP info ,see below:'+"\n"
              + '      default(0) Match packets with default dscp (000000)     '
              + ' '+"\n"
              + '      af11(10)   Match packets with AF11 dscp (001010)        '
              + '                        '+"\n"
              + '      af12(12)   Match packets with AF12 dscp (001100)        '
              + '                        '+"\n"
              + '      af13(14)   Match packets with AF13 dscp (001110)        '
              + '                        '+"\n"
              + '      af21(18)   Match packets with AF21 dscp (010010)        '
              + '                        '+"\n"
              + '      af22(20)   Match packets with AF22 dscp (010100)        '
              + '                        '+"\n"
              + '      af23(22)   Match packets with AF23 dscp (010110)        '
              + '                        '+"\n"
              + '      af31(26)   Match packets with AF31 dscp (011010)        '
              + '                        '+"\n"
              + '      af32(28)   Match packets with AF32 dscp (011100)        '
              + '                        '+"\n"
              + '      af33(30)   Match packets with AF33 dscp (011110)        '
              + '                        '+"\n"
              + '      af41(34)   Match packets with AF41 dscp (100010)        '
              + '                        '+"\n"
              + '      af42(36)   Match packets with AF42 dscp (100100)        '
              + '                        '+"\n"
              + '      af43(38)   Match packets with AF43 dscp (100110)   '+"\n"
              + '      ef(46)     Match packets with EF dscp (101110)          '
              + '                   '+"\n"
              + '      cs1(8)     Match packets with CS1(precedence 1) dscp (00'
              + '1000)                   '+"\n"
              + '      cs2(16)    Match packets with CS2(precedence 2) dscp (01'
              + '0000)                   '+"\n"
              + '      cs3(24)    Match packets with CS3(precedence 3) dscp (01'
              + '1000)                   '+"\n"
              + '      cs4(32)    Match packets with CS4(precedence 4) dscp (10'
              + '0000)                   '+"\n"
              + '      cs5(40)    Match packets with CS5(precedence 5) dscp (10'
              + '1000)                   '+"\n"
              + '      cs6(48)    Match packets with CS6(precedence 6) dscp (11'
              + '0000)                   '+"\n"
              + '      cs7(56)    Match packets with CS7(precedence 7) dscp (11'
              + '1000)'
                ;
  }
  typedef qos-ip-type {
    type enumeration {
      enum any {
        value 0 ;
        description 'Based on any IP'
                    ;
      }
      enum ipv4 {
        value 1 ;
        description 'Based on IPv4'
                    ;
      }
      enum ipv6 {
        value 2 ;
        description 'Based on IPv6'
                    ;
      }
    }
    description 'Configure based on IP, see below:'+"\n"
              + '      any  Packets based on any IP;'+"\n"
              + '      ipv4 Packets based on IPv4;'+"\n"
              + '      ipv6 Packets based on IPv6;'
                ;
  }
  typedef qos-rate-unit-type {
    type enumeration {
      enum kbps {
        value 1 ;
        description 'Kilobits per second'
                    ;
      }
      enum mbps {
        value 2 ;
        description 'Megabits per second'
                    ;
      }
      enum gbps {
        value 3 ;
        description 'Gigabits per second'
                    ;
      }
    }
    description 'The definition of rate unit of police car info, see below:'+"\n"
              + '             kbps  (1) Kilobits per second'+"\n"
              + '             mbps  (2) Megabits per second'+"\n"
              + '             gbps  (3) Gigabits per second'
                ;
  }
  typedef qos-bucket-unit-type {
    type enumeration {
      enum kb {
        value 1 ;
        description Kilobits ;
      }
      enum mb {
        value 2 ;
        description Megabits ;
      }
      enum gb {
        value 3 ;
        description Gigabits ;
      }
    }
    description 'The definition of bucket unit of police car info, see below:'+"\n"
              + '             kb  (1) Kilobits'+"\n"
              + '             mb  (2) Megabits'+"\n"
              + '             gb  (3) Gigabits'
                ;
  }
  typedef qos-threshold-unit-type {
    type enumeration {
      enum kbytes {
        value 1 ;
        description Kilobytes ;
      }
      enum mbytes {
        value 2 ;
        description Megabytes ;
      }
      enum gbytes {
        value 3 ;
        description Gigabytes ;
      }
    }
    description 'The definition of threshold unit of wred info, see below:'+"\n"
              + '             kb  (1) Kilobytes'+"\n"
              + '             mb  (2) Megabytes'+"\n"
              + '             gb  (3) Gigabytes'
                ;
  }
  typedef qos-direction {
    type enumeration {
      enum input {
        value 1 ;
        description 'input  Attaches to the input flow'
                    ;
      }
      enum output {
        value 2 ;
        description 'output Attaches to the output flow'
                    ;
      }
    }
    description 'The flow direction, as follows,'+"\n"
              + '     input  Attaches to the input flow'+"\n"
              + '     output Attaches to the output flow'
                ;
  }
  typedef qos-port-range {
    type ncd:range {
      pattern '(((((([1-9][0-9]{1,3})|([1-9][0-9]{0,0})|0|([1-5][0-9]{4,4})|(6['
            + '0-4][0-9]{3,3})|(65[0-4][0-9]{2,2})|(655[0-2][0-9]{1,1})|(6553[0'
            + '-4])|65535)-(([1-9][0-9]{1,3})|([1-9][0-9]{0,0})|0|([1-5][0-9]{4'
            + ',4})|(6[0-4][0-9]{3,3})|(65[0-4][0-9]{2,2})|(655[0-2][0-9]{1,1})'
            + '|(6553[0-4])|65535))|(([1-9][0-9]{1,3})|([1-9][0-9]{0,0})|0|([1-'
            + '5][0-9]{4,4})|(6[0-4][0-9]{3,3})|(65[0-4][0-9]{2,2})|(655[0-2][0'
            + '-9]{1,1})|(6553[0-4])|65535)),){0,3}(((([1-9][0-9]{1,3})|([1-9]['
            + '0-9]{0,0})|0|([1-5][0-9]{4,4})|(6[0-4][0-9]{3,3})|(65[0-4][0-9]{'
            + '2,2})|(655[0-2][0-9]{1,1})|(6553[0-4])|65535)-(([1-9][0-9]{1,3})'
            + '|([1-9][0-9]{0,0})|0|([1-5][0-9]{4,4})|(6[0-4][0-9]{3,3})|(65[0-'
            + '4][0-9]{2,2})|(655[0-2][0-9]{1,1})|(6553[0-4])|65535))|(([1-9][0'
            + '-9]{1,3})|([1-9][0-9]{0,0})|0|([1-5][0-9]{4,4})|(6[0-4][0-9]{3,3'
            + '})|(65[0-4][0-9]{2,2})|(655[0-2][0-9]{1,1})|(6553[0-4])|65535)){'
            + '1,1})'
              {
        description 'Configure port in range mode, support single port value or'
                  + ' range(max num:4;spacing mark:,) in <0-65535>.'
                    ;
      }
    }
    description 'The definition of port in range mode, support single port valu'
              + 'e or range(max num:4;spacing mark:,) in <0-65535>. For example'
              + ',"1-300,400,450-500",etc.'
                ;
  }
  typedef qos-rate-unit-type-ex {
    type enumeration {
      enum kbps {
        value 1 ;
        description 'Kilobits per second'
                    ;
      }
      enum mbps {
        value 2 ;
        description 'Megabits per second'
                    ;
      }
      enum gbps {
        value 3 ;
        description 'Gigabits per second'
                    ;
      }
      enum pps {
        value 4 ;
        description 'Packets per second'
                    ;
      }
    }
    description 'The definition of rate unit of police car info, see below:'+"\n"
              + '             kbps  (1) Kilobits per second'+"\n"
              + '             mbps  (2) Megabits per second'+"\n"
              + '             gbps  (3) Gigabits per second'+"\n"
              + '             pps   (4) Packets per second'
                ;
  }
  typedef qos-phb-bitmap {
    type ncd:bitmap {
      pattern '(((([0-7]-[0-7])|[0-7]),){0,3}(([0-7]-[0-7])|([0-7])){1,1})'
              {
        description 'Configure phb in range mode, support single phb value or r'
                  + 'ange(max num:4;spacing mark:,) in <0-7>.'
                    ;
      }
    }
    description 'The definition of phb in range mode, support single phb value '
              + 'or range(max num:4;spacing mark:,) in <0-7>. For example,"0,4-'
              + '7",etc.'
                ;
  }
  container configuration {
    description 'Configuration information'
                ;
    container qos {
      description 'Configuration about QoS'
                  ;
      container class-map {
        description 'Configure H-QoS class map'
                    ;
        container normal {
          if-feature normal-mode ;
          description 'Class map based on normal'
                      ;
          container class-maps {
            description 'Configure H-QoS class map lists'
                        ;
            list class-map {
              description 'Configure H-QoS class map list'
                          ;
              key cmap-name ;
              leaf cmap-name {
                description 'Name of the class map, support 1-31 characters'
                            ;
                type string {
                  length 1..31 {
                    description 'Name of the class map, support 1-31 characters'
                                ;
                  }
                }
              }
              leaf match-relation {
                description 'The type of packets matching, see bellow:         '
                          + '       '+"\n"
                          + '  match-all Packets meet all of the match criteria'
                          + ''+"\n"
                          + '  match-any Packets meet any of the match criteria'
                            ;
                type enumeration {
                  enum match-all {
                    value 1 ;
                    description 'Packets meet all of the match criteria'
                                ;
                  }
                  enum match-any {
                    value 2 ;
                    description 'Packets meet any of the match criteria'
                                ;
                  }
                }
                mandatory true ;
              }
              container service-type {
                description 'service-type, the same value represents the same c'
                          + 'lass-map.'
                            ;
                presence 'To set the service type value'
                         ;
                leaf service-type {
                  description 'The same service type value represents the same '
                            + 'class-map.'
                              ;
                  type uint32 {
                    range 1..255 {
                      description 'The same service type value represents the s'
                                + 'ame class-map.'
                                  ;
                    }
                  }
                  mandatory true ;
                }
                container effect-order {
                  description 'The value specify the class effect order in the '
                            + 'policy map.'
                              ;
                  presence 'To set the effect order value'
                           ;
                  leaf effect-order {
                    description 'The value specify the class effect order in th'
                              + 'e policy map.'
                                ;
                    type uint32 {
                      range 1..255 {
                        description 'The value specify the class effect order i'
                                  + 'n the policy map.'
                                    ;
                      }
                    }
                    mandatory true ;
                  }
                }
                ncd:revise-date 2017-06-12 ;
              }
              container match {
                description 'Configure match criteria for a class map'
                            ;
                container dscps {
                  description 'Select DSCP as match criteria'
                              ;
                  list dscp {
                    description 'Set DSCP value as match criteria'
                                ;
                    key ip-type ;
                    leaf ip-type {
                      description 'Configure DSCP value Based on IP, see below:'
                                + ''+"\n"
                                + '  any  Packets based on any IP;'+"\n"
                                + '  ipv4 Packets based on IPv4;'+"\n"
                                + '  ipv6 Packets based on IPv6;'
                                  ;
                      type qos-ip-type ;
                    }
                    leaf not {
                      description 'Configure the opposite range flag,'+"\n"
                                + '  true  Match opposite range'+"\n"
                                + '  false Match current range'
                                  ;
                      type boolean ;
                      default false ;
                    }
                    leaf dscp-value {
                      description 'Configure QoS dscp in range mode, support si'
                                + 'ngle DSCP value or range(max num:4;spacing m'
                                + 'ark:,) in <0-63>. For example,"6,10-30,40,50'
                                + '-60",etc.'
                                  ;
                      type qos-dscp-bitmap ;
                      mandatory true ;
                    }
                  }
                }
                container dscp-exs {
                  if-feature class-match-dscp-ex ;
                  description 'Set DSCP value as match criteria in PHB mode'
                              ;
                  list dscp-ex {
                    description 'Set DSCP value as match criteria in PHB mode'
                                ;
                    key 'ip-type reserved-words'
                        ;
                    leaf ip-type {
                      description 'Configure DSCP value Based on IP, see below:'
                                + ''+"\n"
                                + '  any  Packets based on any IP;'+"\n"
                                + '  ipv4 Packets based on IPv4;'+"\n"
                                + '  ipv6 Packets based on IPv6;'
                                  ;
                      type qos-ip-type ;
                    }
                    leaf reserved-words {
                      description 'Configure DSCP value in the manner of PHB,se'
                                + 'e below,'+"\n"
                                + 'resserved words:'+"\n"
                                + '  default(0) Match packets with default dscp'
                                + ' (000000)      '+"\n"
                                + '  af11(10)   Match packets with AF11 dscp (0'
                                + '01010)                                '+"\n"
                                + '  af12(12)   Match packets with AF12 dscp (0'
                                + '01100)                                '+"\n"
                                + '  af13(14)   Match packets with AF13 dscp (0'
                                + '01110)                                '+"\n"
                                + '  af21(18)   Match packets with AF21 dscp (0'
                                + '10010)                                '+"\n"
                                + '  af22(20)   Match packets with AF22 dscp (0'
                                + '10100)                                '+"\n"
                                + '  af23(22)   Match packets with AF23 dscp (0'
                                + '10110)                                '+"\n"
                                + '  af31(26)   Match packets with AF31 dscp (0'
                                + '11010)                                '+"\n"
                                + '  af32(28)   Match packets with AF32 dscp (0'
                                + '11100)                                '+"\n"
                                + '  af33(30)   Match packets with AF33 dscp (0'
                                + '11110)                                '+"\n"
                                + '  af41(34)   Match packets with AF41 dscp (1'
                                + '00010)                                '+"\n"
                                + '  af42(36)   Match packets with AF42 dscp (1'
                                + '00100)                                '+"\n"
                                + '  af43(38)   Match packets with AF43 dscp (1'
                                + '00110)   '+"\n"
                                + '  ef(46)     Match packets with EF dscp (101'
                                + '110)                             '+"\n"
                                + '  cs1(8)     Match packets with CS1(preceden'
                                + 'ce 1) dscp (001000)                   '+"\n"
                                + '  cs2(16)    Match packets with CS2(preceden'
                                + 'ce 2) dscp (010000)                   '+"\n"
                                + '  cs3(24)    Match packets with CS3(preceden'
                                + 'ce 3) dscp (011000)                   '+"\n"
                                + '  cs4(32)    Match packets with CS4(preceden'
                                + 'ce 4) dscp (100000)                   '+"\n"
                                + '  cs5(40)    Match packets with CS5(preceden'
                                + 'ce 5) dscp (101000)                   '+"\n"
                                + '  cs6(48)    Match packets with CS6(preceden'
                                + 'ce 6) dscp (110000)                   '+"\n"
                                + '  cs7(56)    Match packets with CS7(preceden'
                                + 'ce 7) dscp (111000)'
                                  ;
                      type qos-reserved-words ;
                    }
                  }
                }
                container precedences {
                  description 'Select IP-Precedence as match criteria'
                              ;
                  list precedence {
                    description 'Set IP Precedence value as match criteria'
                                ;
                    key ip-type ;
                    leaf ip-type {
                      description 'Configure DSCP value Based on IP, see below:'
                                + ''+"\n"
                                + '  any  Packets based on any IP;'+"\n"
                                + '  ipv4 Packets based on IPv4;'+"\n"
                                + '  ipv6 Packets based on IPv6;'
                                  ;
                      type qos-ip-type ;
                    }
                    leaf not {
                      description 'Configure the opposite range flag,'+"\n"
                                + '  true  Match opposite range'+"\n"
                                + '  false Match current range'
                                  ;
                      type boolean ;
                      default false ;
                    }
                    leaf prec-value {
                      description 'Configure QoS IP Precedence in range mode, s'
                                + 'upport single precedence value or range(max '
                                + 'num:4;spacing mark:,) in <0-7>. For example,'
                                + '"0,2-4,7",etc.'
                                  ;
                      type qos-prec-bitmap ;
                      mandatory true ;
                    }
                  }
                }
                container mpls-exp {
                  description 'Select MPLS-EXP as match criteria'
                              ;
                  presence 'Select MPLS-EXP as match criteria'
                           ;
                  leaf mpls-exp-value {
                    description 'Configure QoS MPLS-EXP value in range mode, su'
                              + 'pport single MPLS-EXP value or range(max num:4'
                              + ';spacing mark:,) in <0-7>. For example,"0,2-4,'
                              + '7",etc.'
                                ;
                    type qos-mpls-bitmap ;
                    mandatory true ;
                  }
                }
                container in-vlan {
                  description 'Select inner-VLAN as match criteria'
                              ;
                  presence 'Select inner-VLAN as match criteria'
                           ;
                  leaf vlan-value {
                    description 'Configure inner-VLAN value in range mode, supp'
                              + 'ort single inner-VLAN value or range(max num:4'
                              + ';spacing mark:,) in <1-4094>. For example,"1,3'
                              + '00-400,1000,2000-4000",etc.'
                                ;
                    type qos-vlan-bitmap ;
                    mandatory true ;
                  }
                }
                container out-vlan {
                  description 'Select outer-VLAN as match criteria'
                              ;
                  presence 'Select outer-VLAN as match criteria'
                           ;
                  leaf vlan-value {
                    description 'Configure outer-VLAN value in range mode, supp'
                              + 'ort single outer-VLAN value or range(max num:4'
                              + ';spacing mark:,) in <1-4094>. For example,"1,3'
                              + '00-400,1000,2000-4000",etc.'
                                ;
                    type qos-vlan-bitmap ;
                    mandatory true ;
                  }
                }
                container in-8021p {
                  description 'Select inner 802.1p as match criteria'
                              ;
                  presence 'Select inner 802.1p as match criteria'
                           ;
                  leaf in-8021p-value {
                    description 'Configure inner 802.1p value in range mode, su'
                              + 'pport single 802.1p value or range(max num:4;s'
                              + 'pacing mark:,) in <0-7>. For example,"0,2-4,7"'
                              + ',etc.'
                                ;
                    type qos-8021p-bitmap ;
                    mandatory true ;
                  }
                }
                container out-8021p {
                  description 'Select outer 802.1p as match criteria'
                              ;
                  presence 'Select outer 802.1p as match criteria'
                           ;
                  leaf out-8021p-value {
                    description 'Configure outer 802.1p value in range mode, su'
                              + 'pport single 802.1p value or range(max num:4;s'
                              + 'pacing mark:,) in <0-7>. For example,"0,2-4,7"'
                              + ',etc.'
                                ;
                    type qos-8021p-bitmap ;
                    mandatory true ;
                  }
                }
                container qos-group {
                  description 'Select qos-group as match criteria'
                              ;
                  presence 'Select qos-group as match criteria'
                           ;
                  leaf qos-id {
                    description 'Set qos-group number,support <1-65535>'
                                ;
                    type uint16 {
                      range 1..65535 ;
                    }
                    mandatory true ;
                  }
                }
                container vrf-name {
                  description 'Select vrf-name as match criteria'
                              ;
                  presence 'Select vrf-name as match criteria'
                           ;
                  leaf vrf-name {
                    description 'Set vrf name, support 1-32 characters'
                                ;
                    type string {
                      length 1..32 {
                        description 'Vrf name, support 1-32 characters'
                                    ;
                      }
                    }
                    mandatory true ;
                  }
                }
                container uni-cast {
                  description 'Select unicast as match criteria'
                              ;
                  presence 'Select unicast as match criteria'
                           ;
                  leaf uni-cast {
                    description 'Set unicast as match criteria'
                                ;
                    type empty ;
                    mandatory true ;
                  }
                }
                container multi-cast {
                  description 'Select multicast as match criteria'
                              ;
                  presence 'Select multicast as match criteria'
                           ;
                  leaf multi-cast {
                    description 'Set multicast as match criteria'
                                ;
                    type empty ;
                    mandatory true ;
                  }
                }
                container mac-addr {
                  description 'Select mac-address as match criteria'
                              ;
                  presence 'Select mac-address as match criteria'
                           ;
                  leaf mac-address {
                    description 'Configure mac-address'
                                ;
                    type ncd:mac-address ;
                    mandatory true ;
                  }
                }
                container child {
                  description 'Set the mark of null class'
                              ;
                  presence 'Set the mark of null class'
                           ;
                  leaf child {
                    description 'Set the mark of null class'
                                ;
                    type empty ;
                    mandatory true ;
                  }
                }
                container ipv4-acls {
                  description 'Select IPv4 ACL name as match criteria'
                              ;
                  list ipv4-acl {
                    description 'Set IPv4 ACL name as match criteria'
                                ;
                    key acl-name ;
                    leaf acl-name {
                      description 'Set ipv4-access-list name, support 1-31 char'
                                + 'acters'
                                  ;
                      type string {
                        length 1..31 {
                          description 'Name of ACL, support 1-31 characters'
                                      ;
                        }
                      }
                    }
                  }
                }
                container ipv6-acls {
                  description 'Select IPv6 ACL name as match criteria'
                              ;
                  list ipv6-acl {
                    description 'Set IPv6 ACL name as match criteria'
                                ;
                    key acl-name ;
                    leaf acl-name {
                      description 'Set ipv6-access-list name, support 1-31 char'
                                + 'acters'
                                  ;
                      type string {
                        length 1..31 {
                          description 'Name of ACL, support 1-31 characters'
                                      ;
                        }
                      }
                    }
                  }
                }
                container link-acls {
                  if-feature class-match-link-acl ;
                  description 'Select link ACL name as match criteria'
                              ;
                  list link-acl {
                    description 'Set link ACL name as match criteria'
                                ;
                    key acl-name ;
                    leaf acl-name {
                      description 'Set link-access-list name, support 1-31 char'
                                + 'acters'
                                  ;
                      type string {
                        length 1..31 {
                          description 'Name of ACL, support 1-31 characters'
                                      ;
                        }
                      }
                    }
                  }
                }
                container vpws {
                  description 'Select VPWS instance name as match criteria'
                              ;
                  presence 'Select VPWS instance name as match criteria'
                           ;
                  leaf vpws-name {
                    description 'Set VPWS instance name, support 1-32 characters'
                                ;
                    type string {
                      length 1..32 {
                        description 'VPWS instance name, support 1-32 characters'
                                    ;
                      }
                    }
                    mandatory true ;
                  }
                }
                container vpls {
                  description 'Select VPLS instance name as match criteria'
                              ;
                  presence 'Select VPLS instance name as match criteria'
                           ;
                  leaf vpls-name {
                    description 'Set VPLS instance name, support 1-32 characters'
                                ;
                    type string {
                      length 1..32 {
                        description 'VPLS instance name, support 1-32 characters'
                                    ;
                      }
                    }
                    mandatory true ;
                  }
                }
                container service-class {
                  if-feature phb-mode ;
                  description 'Select PHB as match criteria'
                              ;
                  presence 'Select PHB as match criteria'
                           ;
                  choice value-or-range {
                    description 'Select PHB value or range as match criteria.'
                                ;
                    case value {
                      description 'Select PHB value as match criteria.'
                                  ;
                      leaf service-class {
                        description 'Select service class of PHB info, see belo'
                                  + 'w:'+"\n"
                                  + '  be  Best effort'+"\n"
                                  + '  af1 Assured forwarding class 1'+"\n"
                                  + '  af2 Assured forwarding class 2'+"\n"
                                  + '  af3 Assured forwarding class 3'+"\n"
                                  + '  af4 Assured forwarding class 4'+"\n"
                                  + '  ef  Expedited forward'+"\n"
                                  + '  cs6 Internetwork control service class'+"\n"
                                  + '  cs7 Network control service class'
                                    ;
                        type qos-service-class ;
                        mandatory true ;
                      }
                    }
                    case range {
                      description 'Select PHB range as match criteria.'
                                  ;
                      container range {
                        description 'Select PHB range as match criteria.'
                                    ;
                        leaf service-class-range {
                          description 'Configure service class in range mode, s'
                                    + 'upport value or range(max num:4;spacing '
                                    + 'mark:,) in <0-7>. For example,"0,2-4,7",'
                                    + 'etc. The values of service class are as '
                                    + 'follow:'+"\n"
                                    + '  be  Best effort (0)'+"\n"
                                    + '  af1 Assured forwarding class 1 (1)'+"\n"
                                    + '  af2 Assured forwarding class 2 (2)'+"\n"
                                    + '  af3 Assured forwarding class 3 (3)'+"\n"
                                    + '  af4 Assured forwarding class 4 (4)'+"\n"
                                    + '  ef  Expedited forward (5)'+"\n"
                                    + '  cs6 Internetwork control service class'
                                    + ' (6)'+"\n"
                                    + '  cs7 Network control service class (7)'
                                      ;
                          type qos-phb-bitmap ;
                          mandatory true ;
                        }
                      }
                      ncd:revise-date 2021-01-18 ;
                    }
                  }
                }
                container protocol {
                  if-feature class-match-protocol ;
                  description 'Select protocol as match criteria'
                              ;
                  container unclassifieds {
                    description 'Match unclassified category'
                                ;
                    list unclassified {
                      description 'Set protocol in unclassified category'
                                  ;
                      key prodpi-id ;
                      leaf prodpi-id {
                        description 'Unclassified category, see below:'+"\n"
                                  + 'unknown  Unclassified category, UNKNOWN, P'
                                  + 'ID 1'
                                    ;
                        type enumeration {
                          enum unknown {
                            value 1 ;
                            description 'Unclassified category, UNKNOWN, PID 1'
                                        ;
                          }
                        }
                      }
                    }
                  }
                  container emails {
                    description 'Match electronic mail category'
                                ;
                    list email {
                      description 'Select protocol in electronic mail category'
                                  ;
                      key prodpi-id ;
                      leaf prodpi-id {
                        description 'Set protocol in electronic mail category, '
                                  + 'see below:'+"\n"
                                  + ' pop3     EMAIL category, POP3, PID 2'+"\n"
                                  + ' smtp     EMAIL category, SMTP, PID 13 '+"\n"
                                  + ' smtp-ssl EMAIL category, SMTP-SSL, PID 15'
                                  + ''+"\n"
                                  + ' imap     EMAIL category, IMAP, PID 16'+"\n"
                                  + ' imap-ssl EMAIL category, IMAP-SSL, PID 30'
                                  + '8'+"\n"
                                  + ' pop3-ssl EMAIL category, POP3-SSL, PID 31'
                                  + '0'
                                    ;
                        type enumeration {
                          enum pop3 {
                            value 2 ;
                            description 'EMAIL category, POP3, PID 2'
                                        ;
                          }
                          enum smtp {
                            value 13 ;
                            description 'EMAIL category, SMTP, PID 13'
                                        ;
                          }
                          enum smtp-ssl {
                            value 15 ;
                            description 'EMAIL category, SMTP-SSL, PID 15'
                                        ;
                          }
                          enum imap {
                            value 16 ;
                            description 'EMAIL category, IMAP, PID 16'
                                        ;
                          }
                          enum imap-ssl {
                            value 308 ;
                            description 'EMAIL category, IMAP-SSL, PID 308'
                                        ;
                          }
                          enum pop3-ssl {
                            value 310 ;
                            description 'EMAIL category, POP3-SSL, PID 310'
                                        ;
                          }
                        }
                      }
                    }
                  }
                  container ims {
                    description 'Match instant messaging category'
                                ;
                    list im {
                      description 'Select protocol in instant messaging category'
                                  ;
                      key prodpi-id ;
                      leaf prodpi-id {
                        description 'Set protocol in instant messaging category'
                                  + ', see below:'+"\n"
                                  + 'gtalk           IM category, GTALK, PID 4'+"\n"
                                  + 'ali-wangwang    IM category, ALI-WANGWANG,'
                                  + ' PID 21'+"\n"
                                  + 'msn             IM category, MSN, PID 35 '+"\n"
                                  + 'yahoo-messenger IM category, YAHOO-MESSENG'
                                  + 'ER, PID 92'+"\n"
                                  + 'qq              IM category, QQ, PID 107'+"\n"
                                  + 'fetion          IM category, FETION, PID 2'
                                  + '39'
                                    ;
                        type enumeration {
                          enum gtalk {
                            value 4 ;
                            description 'IM category, GTALK, PID 4'
                                        ;
                          }
                          enum ali-wangwang {
                            value 21 ;
                            description 'IM category, ALI-WANGWANG, PID 21'
                                        ;
                          }
                          enum msn {
                            value 35 ;
                            description 'IM category, MSN, PID 35'
                                        ;
                          }
                          enum yahoo-messenger {
                            value 92 ;
                            description 'IM category, YAHOO-MESSENGER, PID 92'
                                        ;
                          }
                          enum qq {
                            value 107 ;
                            description 'IM category, QQ, PID 107'
                                        ;
                          }
                          enum fetion {
                            value 239 ;
                            description 'IM category, FETION, PID 239'
                                        ;
                          }
                        }
                      }
                    }
                  }
                  container terminals {
                    description 'Match terminal category'
                                ;
                    list terminal {
                      description 'Select protocol in terminal category'
                                  ;
                      key prodpi-id ;
                      leaf prodpi-id {
                        description 'Set protocol in terminal category,  see be'
                                  + 'low: '+"\n"
                                  + 'ssh    TERMINAL category, SSH, PID 39'+"\n"
                                  + 'telnet TERMINAL category, TELNET, PID 47 '+"\n"
                                  + 'ms-rdp TERMINAL category, MS-RDP, PID 101'
                                    ;
                        type enumeration {
                          enum ssh {
                            value 39 ;
                            description 'TERMINAL category, SSH, PID 39'
                                        ;
                          }
                          enum telnet {
                            value 47 ;
                            description 'TERMINAL category, TELNET, PID 47'
                                        ;
                          }
                          enum ms-rdp {
                            value 101 ;
                            description 'TERMINAL category, MS-RDP, PID 101'
                                        ;
                          }
                        }
                      }
                    }
                  }
                  container networks {
                    description 'Match network category'
                                ;
                    list network {
                      description 'Select protocol in network category'
                                  ;
                      key prodpi-id ;
                      leaf prodpi-id {
                        description 'Set protocol in network category, see belo'
                                  + 'w:'+"\n"
                                  + 'netbios  NETWORK category, NETBIOS, PID 53'
                                  + ''+"\n"
                                  + 'ntp      NETWORK category, NTP, PID 86'+"\n"
                                  + 'syslog   NETWORK category, SYSLOG, PID 91'+"\n"
                                  + 'radius   NETWORK category, RADIUS, PID 100'
                                  + ''+"\n"
                                  + 'dns      NETWORK category, DNS, PID 109'+"\n"
                                  + 'snmp     NETWORK category, SNMP, PID 185'
                                    ;
                        type enumeration {
                          enum netbios {
                            value 53 ;
                            description 'NETWORK category, NETBIOS, PID 53'
                                        ;
                          }
                          enum ntp {
                            value 86 ;
                            description 'NETWORK category, NTP, PID 86'
                                        ;
                          }
                          enum syslog {
                            value 91 ;
                            description 'NETWORK category, SYSLOG, PID 91'
                                        ;
                          }
                          enum radius {
                            value 100 ;
                            description 'NETWORK category, RADIUS, PID 100'
                                        ;
                          }
                          enum dns {
                            value 109 ;
                            description 'NETWORK category, DNS, PID 109'
                                        ;
                          }
                          enum snmp {
                            value 185 ;
                            description 'NETWORK category, SNMP, PID 185'
                                        ;
                          }
                        }
                      }
                    }
                  }
                  container p2ps {
                    description 'Match peer-to-peer category'
                                ;
                    list p2p {
                      description 'Select protocol in peer-to-peer category'
                                  ;
                      key prodpi-id ;
                      leaf prodpi-id {
                        description 'Set protocol in peer-to-peer category, see'
                                  + ' below:'+"\n"
                                  + 'edk         P2P category, EDK, PID 83'+"\n"
                                  + 'bt          P2P category, BT, PID 94'+"\n"
                                  + 'thunder     P2P category, THUNDER, PID 96'+"\n"
                                  + 'kad         P2P category, KAD, PID 97'+"\n"
                                  + 'qq-download P2P category, QQ-DOWNLOAD, PID'
                                  + ' 105'+"\n"
                                  + 'dht         P2P category, DHT, PID 169'+"\n"
                                  + 'web-thunder P2P category, WEB-THUNDER, PID'
                                  + ' 234'
                                    ;
                        type enumeration {
                          enum edk {
                            value 83 ;
                            description 'P2P category, EDK, PID 83'
                                        ;
                          }
                          enum bt {
                            value 94 ;
                            description 'P2P category, BT, PID 94'
                                        ;
                          }
                          enum thunder {
                            value 96 ;
                            description 'P2P category, THUNDER, PID 96'
                                        ;
                          }
                          enum kad {
                            value 97 ;
                            description 'P2P category, KAD, PID 97'
                                        ;
                          }
                          enum qq-download {
                            value 105 ;
                            description 'P2P category, QQ-DOWNLOAD, PID 105'
                                        ;
                          }
                          enum dht {
                            value 169 ;
                            description 'P2P category, DHT, PID 169'
                                        ;
                          }
                          enum web-thunder {
                            value 234 ;
                            description 'P2P category, WEB-THUNDER, PID 234'
                                        ;
                          }
                        }
                      }
                    }
                  }
                  container webs {
                    description 'Match world wide web category'
                                ;
                    list web {
                      description 'Select protocol in world wide web category'
                                  ;
                      key prodpi-id ;
                      leaf prodpi-id {
                        description 'Set protocol in world wide web category, s'
                                  + 'ee below:'+"\n"
                                  + 'http          WEB category, HTTP, PID 48'+"\n"
                                  + 'http-range    WEB category, HTTP-RANGE, PI'
                                  + 'D 49'+"\n"
                                  + 'http-proxy    WEB category, HTTP-PROXY, PI'
                                  + 'D 50'+"\n"
                                  + 'http-download WEB category, HTTP-DOWNLOAD,'
                                  + ' PID 51'
                                    ;
                        type enumeration {
                          enum http {
                            value 48 ;
                            description 'WEB category, HTTP, PID 48'
                                        ;
                          }
                          enum http-range {
                            value 49 ;
                            description 'WEB category, HTTP-RANGE, PID 49'
                                        ;
                          }
                          enum http-proxy {
                            value 50 ;
                            description 'WEB category, HTTP-PROXY, PID 50'
                                        ;
                          }
                          enum http-download {
                            value 51 ;
                            description 'WEB category, HTTP-DOWNLOAD, PID 51'
                                        ;
                          }
                        }
                      }
                    }
                  }
                  container filetrans {
                    description 'Match file transfer category'
                                ;
                    list filetran {
                      description 'Select protocol in file transfer category'
                                  ;
                      key prodpi-id ;
                      leaf prodpi-id {
                        description 'Set protocol in file transfer category, se'
                                  + 'e below:'+"\n"
                                  + 'smb          FILETRANS category, SMB, PID '
                                  + '54 '+"\n"
                                  + 'tftp-control FILETRANS category, TFTP-CONT'
                                  + 'ROL, PID 66'+"\n"
                                  + 'tftp-data    FILETRANS category, TFTP-DATA'
                                  + ', PID 67'+"\n"
                                  + 'ftp-control  FILETRANS category, FTP-CONTR'
                                  + 'OL, PID 103'+"\n"
                                  + 'ftp-data     FILETRANS category, FTP-DATA,'
                                  + ' PID 104'
                                    ;
                        type enumeration {
                          enum smb {
                            value 54 ;
                            description 'FILETRANS category, SMB, PID 54'
                                        ;
                          }
                          enum tftp-control {
                            value 66 ;
                            description 'FILETRANS category, TFTP-CONTROL, PID 66'
                                        ;
                          }
                          enum tftp-data {
                            value 67 ;
                            description 'FILETRANS category, TFTP-DATA, PID 67'
                                        ;
                          }
                          enum ftp-control {
                            value 103 ;
                            description 'FILETRANS category, FTP-CONTROL, PID 103'
                                        ;
                          }
                          enum ftp-data {
                            value 104 ;
                            description 'FILETRANS category, FTP-DATA, PID 104'
                                        ;
                          }
                        }
                      }
                    }
                  }
                  container voips {
                    description 'Match voice over internet phone category'
                                ;
                    list voip {
                      description 'Select protocol in voice over internet phone'
                                + ' category'
                                  ;
                      key prodpi-id ;
                      leaf prodpi-id {
                        description 'Set protocol in voice over internet phone '
                                  + 'category, see below:'+"\n"
                                  + 'skype  VOIP category, SKYPE, PID 93'+"\n"
                                  + 'sip    VOIP category, SIP, PID 112'+"\n"
                                  + 'h248   VOIP category, H248, PID 336'
                                    ;
                        type enumeration {
                          enum skype {
                            value 93 ;
                            description 'VOIP category, SKYPE, PID 93'
                                        ;
                          }
                          enum sip {
                            value 112 ;
                            description 'VOIP category, SIP, PID 112'
                                        ;
                          }
                          enum h248 {
                            value 336 ;
                            description 'VOIP category, H248, PID 336'
                                        ;
                          }
                        }
                      }
                    }
                  }
                  container games {
                    description 'Match game category'
                                ;
                    list game {
                      description 'Select protocol in game category'
                                  ;
                      key prodpi-id ;
                      leaf prodpi-id {
                        description 'Set protocol in game category, see below:'+"\n"
                                  + 'qqgame       GAME category, QQGAME, PID 19'
                                  + '0'+"\n"
                                  + 'qq-crossfire GAME category, QQ-CROSSFIRE, '
                                  + 'PID 192 '+"\n"
                                  + 'qq-xuanwu    GAME category, QQ-XUANWU, PID'
                                  + ' 193 '+"\n"
                                  + 'qq-feiche    GAME category, QQ-FEICHE, PID'
                                  + ' 194'+"\n"
                                  + 'qq-huanxiangshijie GAME category, QQ-HUANX'
                                  + 'IANGSHIJIE, PID 201 '+"\n"
                                  + 'qq-fo-ffo    GAME category, QQ-FO-FFO, PID'
                                  + ' 231 '+"\n"
                                  + 'qq-doudizhu  GAME category, QQ-DOUDIZHU, P'
                                  + 'ID 266 '+"\n"
                                  + 'qq-farm      GAME category, QQ-FARM, PID 2'
                                  + '86'
                                    ;
                        type enumeration {
                          enum qqgame {
                            value 190 ;
                            description 'GAME category, QQGAME, PID 190'
                                        ;
                          }
                          enum qq-crossfire {
                            value 192 ;
                            description 'GAME category, QQ-CROSSFIRE, PID 192'
                                        ;
                          }
                          enum qq-xuanwu {
                            value 193 ;
                            description 'GAME category, QQ-XUANWU, PID 193'
                                        ;
                          }
                          enum qq-feiche {
                            value 194 ;
                            description 'GAME category, QQ-FEICHE, PID 194'
                                        ;
                          }
                          enum qq-huanxiangshijie {
                            value 201 ;
                            description 'GAME category, QQ-HUANXIANGSHIJIE, PID 201'
                                        ;
                          }
                          enum qq-fo-ffo {
                            value 231 ;
                            description 'GAME category, QQ-FO-FFO, PID 231'
                                        ;
                          }
                          enum qq-doudizhu {
                            value 266 ;
                            description 'GAME category, QQ-DOUDIZHU, PID 266'
                                        ;
                          }
                          enum qq-farm {
                            value 286 ;
                            description 'GAME category, QQ-FARM, PID 286'
                                        ;
                          }
                        }
                      }
                    }
                  }
                  container softwares {
                    description 'Match software category'
                                ;
                    list software {
                      description 'Select protocol in software category'
                                  ;
                      key prodpi-id ;
                      leaf prodpi-id {
                        description 'Set protocol in software category, see bel'
                                  + 'ow:'+"\n"
                                  + 'windows-update SOFTWARE category, WINDOWS-'
                                  + 'UPDATE, PID 20'
                                    ;
                        type enumeration {
                          enum windows-update {
                            value 20 ;
                            description 'SOFTWARE category, WINDOWS-UPDATE, PID 20'
                                        ;
                          }
                        }
                      }
                    }
                  }
                  container secures {
                    description 'Match secure category'
                                ;
                    list secure {
                      description 'Select protocol in secure category'
                                  ;
                      key prodpi-id ;
                      leaf prodpi-id {
                        description 'Set protocol in secure category, see below'
                                  + ':'+"\n"
                                  + 'https  SECURE category, HTTPS, PID 305'
                                    ;
                        type enumeration {
                          enum https {
                            value 305 ;
                            description 'SECURE category, HTTPS, PID 305'
                                        ;
                          }
                        }
                      }
                    }
                  }
                  container webvideos {
                    description 'Match webvideo category'
                                ;
                    list webvideo {
                      description 'Select protocol in webvideo category'
                                  ;
                      key prodpi-id ;
                      leaf prodpi-id {
                        description 'Set protocol in webvideo category, see bel'
                                  + 'ow:'+"\n"
                                  + 'qq-multimedia  WEBVIDEO category, QQ-MULTI'
                                  + 'MEDIA, PID 106'+"\n"
                                  + 'msn-video      WEBVIDEO category, MSN-VIDE'
                                  + 'O, PID 145'
                                    ;
                        type enumeration {
                          enum qq-multimedia {
                            value 106 ;
                            description 'WEBVIDEO category, QQ-MULTIMEDIA, PID 106'
                                        ;
                          }
                          enum msn-video {
                            value 145 ;
                            description 'WEBVIDEO category, MSN-VIDEO, PID 145'
                                        ;
                          }
                        }
                      }
                    }
                  }
                  container streamings {
                    description 'Match streaming category'
                                ;
                    list streaming {
                      description 'Select protocol in streaming category'
                                  ;
                      key prodpi-id ;
                      leaf prodpi-id {
                        description 'Set protocol in streaming category, see be'
                                  + 'low:'+"\n"
                                  + 'thunder-kankan  STREAMING category, THUNDE'
                                  + 'R-KANKAN, PID 70'+"\n"
                                  + 'ppstream        STREAMING category, PPSTRE'
                                  + 'AM, PID 75'+"\n"
                                  + 'pplive          STREAMING category, PPLIVE'
                                  + ', PID 113'
                                    ;
                        type enumeration {
                          enum thunder-kankan {
                            value 70 ;
                            description 'STREAMING category, THUNDER-KANKAN, PID 70'
                                        ;
                          }
                          enum ppstream {
                            value 75 ;
                            description 'STREAMING category, PPSTREAM, PID 75'
                                        ;
                          }
                          enum pplive {
                            value 113 ;
                            description 'STREAMING category, PPLIVE, PID 113'
                                        ;
                          }
                        }
                      }
                    }
                  }
                }
                container vni {
                  description 'To select VNI (VXLAN Network Identifier) as matc'
                            + 'h criteria'
                              ;
                  presence 'To select VNI as match criteria'
                           ;
                  leaf vni-range1-start {
                    description 'The starting-value of the first VNI range'
                                ;
                    type uint32 {
                      range 1..16777215 ;
                    }
                    mandatory true ;
                  }
                  leaf vni-range1-end {
                    description 'The ending-value of the first VNI range'
                                ;
                    type uint32 {
                      range 1..16777215 ;
                    }
                    mandatory true ;
                  }
                  container vni-range2 {
                    description 'To select the second VNI range'
                                ;
                    presence 'The configuration of the second VNI range'
                             ;
                    leaf vni-range2-start {
                      description 'The starting-value of the second VNI range'
                                  ;
                      type uint32 {
                        range 1..16777215 ;
                      }
                      mandatory true ;
                    }
                    leaf vni-range2-end {
                      description 'The ending-value of the second VNI range'
                                  ;
                      type uint32 {
                        range 1..16777215 ;
                      }
                      mandatory true ;
                    }
                    container vni-range3 {
                      description 'To select the third VNI range'
                                  ;
                      presence 'The configuration of the third VNI range'
                               ;
                      leaf vni-range3-start {
                        description 'The starting-value of the third VNI range'
                                    ;
                        type uint32 {
                          range 1..16777215 ;
                        }
                        mandatory true ;
                      }
                      leaf vni-range3-end {
                        description 'The ending-value of the third VNI range'
                                    ;
                        type uint32 {
                          range 1..16777215 ;
                        }
                        mandatory true ;
                      }
                      container vni-range4 {
                        description 'To select the fourth VNI range'
                                    ;
                        presence 'The configuration of the fourth VNI range'
                                 ;
                        leaf vni-range4-start {
                          description 'The starting-value of the fourth VNI ran'
                                    + 'ge'
                                      ;
                          type uint32 {
                            range 1..16777215 ;
                          }
                          mandatory true ;
                        }
                        leaf vni-range4-end {
                          description 'The ending-value of the fourth VNI range'
                                      ;
                          type uint32 {
                            range 1..16777215 ;
                          }
                          mandatory true ;
                        }
                      }
                    }
                  }
                  ncd:revise-date 2015-11-04 ;
                }
                container ipv4-mixed-acls {
                  description 'Select IPv4 mixed ACL name as match criteria'
                              ;
                  list ipv4-mixed-acl {
                    description 'Set IPv4 mixed ACL name as match criteria'
                                ;
                    key acl-name ;
                    leaf acl-name {
                      description 'Set ipv4-mixed-access-list name, support 1-3'
                                + '1 characters'
                                  ;
                      type string {
                        length 1..31 {
                          description 'Name of ACL, support 1-31 characters'
                                      ;
                        }
                      }
                    }
                  }
                  ncd:revise-date 2017-02-20 ;
                }
                container ipv6-mixed-acls {
                  description 'Select IPv6 mixed ACL name as match criteria'
                              ;
                  list ipv6-mixed-acl {
                    description 'Set IPv6 mixed ACL name as match criteria'
                                ;
                    key acl-name ;
                    leaf acl-name {
                      description 'Set ipv6-mixed-access-list name, support 1-3'
                                + '1 characters'
                                  ;
                      type string {
                        length 1..31 {
                          description 'Name of ACL, support 1-31 characters'
                                      ;
                        }
                      }
                    }
                  }
                  ncd:revise-date 2020-12-23 ;
                }
                container ipv4-vxlan-acls {
                  description 'Select IPv4 vxlan ACL name as match criteria.'
                              ;
                  list ipv4-vxlan-acl {
                    description 'Set IPv4 vxlan ACL name as match criteria.'
                                ;
                    key acl-name ;
                    leaf acl-name {
                      description 'Set ipv4-vxlan-access-list name, support 1-3'
                                + '1 characters.'
                                  ;
                      type string {
                        length 1..31 {
                          description 'Name of ACL, support 1-31 characters.'
                                      ;
                        }
                      }
                    }
                  }
                  ncd:revise-date 2021-01-25 ;
                }
                container ipv6-vxlan-acls {
                  description 'Select IPv6 vxlan ACL name as match criteria.'
                              ;
                  list ipv6-vxlan-acl {
                    description 'Set IPv6 vxlan ACL name as match criteria.'
                                ;
                    key acl-name ;
                    leaf acl-name {
                      description 'Set ipv6-vxlan-access-list name, support 1-3'
                                + '1 characters.'
                                  ;
                      type string {
                        length 1..31 {
                          description 'Name of ACL, support 1-31 characters.'
                                      ;
                        }
                      }
                    }
                  }
                  ncd:revise-date 2021-01-25 ;
                }
                container interface {
                  description 'Select interface name as match criteria'
                              ;
                  presence 'Select interface name as match criteria'
                           ;
                  leaf if-name {
                    description 'Set interface name'
                                ;
                    type ncd:ifname {
                      length 1..31 {
                        description 'Name of the interface, support 1-31 charac'
                                  + 'ters'
                                    ;
                      }
                    }
                    mandatory true ;
                  }
                  ncd:revise-date 2021-01-25 ;
                }
              }
              container cmap-description {
                description 'Description of a class map, support 1-79 character'
                          + 's.'
                            ;
                presence 'Specify description of class map'
                         ;
                leaf cmap-description {
                  description 'Description of a class map, support 1-79 charact'
                            + 'ers.'
                              ;
                  type ncd:string-with-blank {
                    length 1..79 {
                      description 'Description of a class map, support 1-79 cha'
                                + 'racters.'
                                  ;
                    }
                  }
                  mandatory true ;
                }
                ncd:revise-date 2020-06-18 ;
              }
            }
          }
        }
        container phb-based {
          if-feature phb-mode ;
          description 'Class map based on phb'
                      ;
          container class-maps {
            description 'Configure H-QoS class map lists'
                        ;
            list class-map {
              description 'Configure H-QoS class map list'
                          ;
              key cmap-name ;
              leaf cmap-name {
                description 'Name of the class map, support 1-31 characters'
                            ;
                type string {
                  length 1..31 {
                    description 'Name of the class map, support 1-31 characters'
                                ;
                  }
                }
              }
              container match {
                description 'Configure match criteria for a class map'
                            ;
                container service-class {
                  description 'Select PHB as match criteria'
                              ;
                  presence 'Select PHB as match criteria'
                           ;
                  choice value-or-range {
                    description 'Select PHB value or range as match criteria.'
                                ;
                    case value {
                      description 'Select PHB value as match criteria.'
                                  ;
                      leaf service-class {
                        description 'Select service class of PHB info, see belo'
                                  + 'w:'+"\n"
                                  + '  be  Best effort'+"\n"
                                  + '  af1 Assured forwarding class 1'+"\n"
                                  + '  af2 Assured forwarding class 2'+"\n"
                                  + '  af3 Assured forwarding class 3'+"\n"
                                  + '  af4 Assured forwarding class 4'+"\n"
                                  + '  ef  Expedited forward'+"\n"
                                  + '  cs6 Internetwork control service class'+"\n"
                                  + '  cs7 Network control service class'
                                    ;
                        type qos-service-class ;
                        mandatory true ;
                      }
                    }
                    case range {
                      description 'Select PHB range as match criteria.'
                                  ;
                      container range {
                        description 'Select PHB range as match criteria.'
                                    ;
                        leaf service-class-range {
                          description 'Configure service class in range mode, s'
                                    + 'upport value or range(max num:4;spacing '
                                    + 'mark:,) in <0-7>. For example,"0,2-4,7",'
                                    + 'etc. The values of service class are as '
                                    + 'follow:'+"\n"
                                    + '  be  Best effort (0)'+"\n"
                                    + '  af1 Assured forwarding class 1 (1)'+"\n"
                                    + '  af2 Assured forwarding class 2 (2)'+"\n"
                                    + '  af3 Assured forwarding class 3 (3)'+"\n"
                                    + '  af4 Assured forwarding class 4 (4)'+"\n"
                                    + '  ef  Expedited forward (5)'+"\n"
                                    + '  cs6 Internetwork control service class'
                                    + ' (6)'+"\n"
                                    + '  cs7 Network control service class (7)'
                                      ;
                          type qos-phb-bitmap ;
                          mandatory true ;
                        }
                      }
                      ncd:revise-date 2021-01-18 ;
                    }
                  }
                }
                container child {
                  description 'Select child as match criteria'
                              ;
                  presence 'Select child as match criteria'
                           ;
                  leaf child {
                    description 'Set the mark of null class'
                                ;
                    type empty ;
                    mandatory true ;
                  }
                  ncd:revise-date 2021-01-11 ;
                }
              }
              container cmap-description {
                description 'Description of a class map, support 1-79 character'
                          + 's.'
                            ;
                presence 'Specify description of class map'
                         ;
                leaf cmap-description {
                  description 'Description of a class map, support 1-79 charact'
                            + 'ers.'
                              ;
                  type ncd:string-with-blank {
                    length 1..79 {
                      description 'Description of a class map, support 1-79 cha'
                                + 'racters.'
                                  ;
                    }
                  }
                  mandatory true ;
                }
                ncd:revise-date 2020-06-18 ;
              }
            }
          }
        }
        container sub-interface-based {
          if-feature sub-interface-mode ;
          description 'Class map based on sub-interface'
                      ;
          container class-maps {
            description 'Configure H-QoS class map lists'
                        ;
            list class-map {
              description 'Configure H-QoS class map list'
                          ;
              key cmap-name ;
              leaf cmap-name {
                description 'Name of the class map, support 1-31 characters'
                            ;
                type string {
                  length 1..31 {
                    description 'Name of the class map, support 1-31 characters'
                                ;
                  }
                }
              }
              container match {
                description 'Configure match criteria for a class map'
                            ;
                container interface {
                  description 'Select interface name as match criteria'
                              ;
                  presence 'Select interface name as match criteria'
                           ;
                  leaf if-name {
                    description 'Set interface name'
                                ;
                    type ncd:ifname {
                      length 1..31 {
                        description 'Name of the interface, support 1-31 charac'
                                  + 'ters'
                                    ;
                      }
                    }
                    mandatory true ;
                  }
                }
                container localport {
                  description 'Select localport as match criteria'
                              ;
                  presence 'Select localport as match criteria'
                           ;
                  leaf localport {
                    description 'Specify localport as match criteria'
                                ;
                    type empty ;
                    mandatory true ;
                  }
                }
              }
              container cmap-description {
                description 'Description of a class map, support 1-79 character'
                          + 's.'
                            ;
                presence 'Specify description of class map'
                         ;
                leaf cmap-description {
                  description 'Description of a class map, support 1-79 charact'
                            + 'ers.'
                              ;
                  type ncd:string-with-blank {
                    length 1..79 {
                      description 'Description of a class map, support 1-79 cha'
                                + 'racters.'
                                  ;
                    }
                  }
                  mandatory true ;
                }
                ncd:revise-date 2020-06-18 ;
              }
            }
          }
        }
        container switch-fabric-based {
          if-feature switch-fabric-mode ;
          description 'Class map based on switch-fabric'
                      ;
          container class-maps {
            description 'Configure H-QoS class map lists'
                        ;
            list class-map {
              description 'Configure H-QoS class map list'
                          ;
              key cmap-name ;
              leaf cmap-name {
                description 'Name of the class map, support 1-31 characters'
                            ;
                type string {
                  length 1..31 {
                    description 'Name of the class map, support 1-31 characters'
                                ;
                  }
                }
              }
              container match {
                description 'Configure match criteria for a class map'
                            ;
                container precedence {
                  description 'Select IP-Precedence as match criteria'
                              ;
                  presence 'Select IP-Precedence as match criteria'
                           ;
                  leaf prec-value {
                    description 'Configure QoS IP Precedence in range mode, sup'
                              + 'port single precedence value or range(max num:'
                              + '4;spacing mark:,) in <0-7>. For example,"0,2-4'
                              + ',7",etc.'
                                ;
                    type qos-prec-bitmap ;
                    mandatory true ;
                  }
                }
                container mpls-exp {
                  description 'Select MPLS-EXP as match criteria'
                              ;
                  presence 'Select MPLS-EXP as match criteria'
                           ;
                  leaf mpls-exp-value {
                    description 'Configure QoS MPLS-EXP value in range mode, su'
                              + 'pport single MPLS-EXP value or range(max num:4'
                              + ';spacing mark:,) in <0-7>. For example,"0,2-4,'
                              + '7",etc.'
                                ;
                    type qos-mpls-bitmap ;
                    mandatory true ;
                  }
                }
                container uni-cast {
                  description 'Select unicast as match criteria'
                              ;
                  presence 'Select unicast as match criteria'
                           ;
                  leaf uni-cast {
                    description 'Set unicast as match criteria'
                                ;
                    type empty ;
                    mandatory true ;
                  }
                  leaf unicast-priority {
                    description 'Specify the priority of queue, such as high, m'
                              + 'iddle, normal, low.'
                                ;
                    type enumeration {
                      enum high {
                        value 1 ;
                        description 'Specify the high priority queue'
                                    ;
                      }
                      enum middle {
                        value 2 ;
                        description 'Specify the middle priority queue'
                                    ;
                      }
                      enum normal {
                        value 3 ;
                        description 'Specify the normal priority queue'
                                    ;
                      }
                      enum low {
                        value 4 ;
                        description 'Specify the low priority queue'
                                    ;
                      }
                    }
                  }
                }
                container multi-cast {
                  description 'Select multicast as match criteria'
                              ;
                  presence 'Select multicast as match criteria'
                           ;
                  leaf multi-cast {
                    description 'Set multicast as match criteria'
                                ;
                    type empty ;
                    mandatory true ;
                  }
                  leaf multicast-priority {
                    description 'Specify the priority of queue, such as high, m'
                              + 'iddle, normal, low.'
                                ;
                    type enumeration {
                      enum high {
                        value 1 ;
                        description 'Specify the high priority queue'
                                    ;
                      }
                      enum middle {
                        value 2 ;
                        description 'Specify the middle priority queue'
                                    ;
                      }
                      enum normal {
                        value 3 ;
                        description 'Specify the normal priority queue'
                                    ;
                      }
                      enum low {
                        value 4 ;
                        description 'Specify the low priority queue'
                                    ;
                      }
                    }
                  }
                }
                container child {
                  description 'Set the mark of null class'
                              ;
                  presence 'Set the mark of null class'
                           ;
                  leaf child {
                    description 'Set the mark of null class'
                                ;
                    type empty ;
                    mandatory true ;
                  }
                }
              }
            }
          }
        }
        container flowspec-based {
          description 'Class map based on flowspec.'
                      ;
          container class-maps {
            description 'Configure H-QoS class map lists.'
                        ;
            list class-map {
              description 'Configure H-QoS class map list'
                          ;
              key cmap-name ;
              leaf cmap-name {
                description 'Name of the class map, support 1-31 characters'
                            ;
                type string {
                  length 1..31 {
                    description 'Name of the class map, support 1-31 characters'
                                ;
                  }
                }
              }
              container match {
                description 'Configure match criteria for a class map'
                            ;
                container port {
                  description 'Select port as match criteria.'
                              ;
                  presence 'Select port as match criteria'
                           ;
                  leaf port-value {
                    description 'Configure port value in range mode, support si'
                              + 'ngle port value or range(max num:4;spacing mar'
                              + 'k:,) in <0-65535>. For example,"1,300-400,1000'
                              + ',2000-4000",etc.'
                                ;
                    type qos-port-range ;
                    mandatory true ;
                  }
                }
                container destination-port {
                  description 'Select destination-port as match criteria.'
                              ;
                  presence 'Select destination-port as match criteria'
                           ;
                  leaf dst-port-value {
                    description 'Configure destination-port value in range mode'
                              + ', support single destination-port value or ran'
                              + 'ge(max num:4;spacing mark:,) in <0-65535>. For'
                              + ' example,"1,300-400,1000,2000-4000",etc.'
                                ;
                    type qos-port-range ;
                    mandatory true ;
                  }
                }
                container source-port {
                  description 'Select source-port as match criteria.'
                              ;
                  presence 'Select source-port as match criteria'
                           ;
                  leaf src-port-value {
                    description 'Configure soure-port value in range mode, supp'
                              + 'ort single soure-port value or range(max num:4'
                              + ';spacing mark:,) in <0-65535>. For example,"1,'
                              + '300-400,1000,2000-4000",etc.'
                                ;
                    type qos-port-range ;
                    mandatory true ;
                  }
                }
                container fragment-type {
                  description 'Select fragment-type as match criteria.'
                              ;
                  presence 'Select fragment-type as match criteria'
                           ;
                  leaf not {
                    description 'Logical negation of operation,'+"\n"
                              + '  true  Match opposite'+"\n"
                              + '  false Match current.'
                                ;
                    type boolean ;
                    default false ;
                  }
                  leaf match-relation {
                    description 'The rule of matching, see bellow:             '
                              + '   '+"\n"
                              + '  all  Match all of the fragment type'+"\n"
                              + '  any  Match any of the fragment type.'
                                ;
                    type enumeration {
                      enum all {
                        value 0 ;
                        description 'Match all of the fragment type.'
                                    ;
                      }
                      enum any {
                        value 1 ;
                        description 'Match any of the fragment type.'
                                    ;
                      }
                    }
                    mandatory true ;
                  }
                  choice fragment-option {
                    description 'Fragment type.'
                                ;
                    mandatory true ;
                    case fragment {
                      description 'Fragment type.'
                                  ;
                      leaf dont-fragment {
                        description 'Match dont-fragment.'
                                    ;
                        type boolean ;
                        default false ;
                      }
                      leaf first-fragment {
                        description 'Match first-fragment.'
                                    ;
                        type boolean ;
                        default false ;
                      }
                      leaf is-fragment {
                        description 'Match is-fragment.'
                                    ;
                        type boolean ;
                        default false ;
                      }
                      leaf last-fragment {
                        description 'Match last-fragment.'
                                    ;
                        type boolean ;
                        default false ;
                      }
                    }
                  }
                }
                container destination-ipv4-addr {
                  description 'Select destination-address as match criteria.'
                              ;
                  presence 'Select destination-address as match criteria'
                           ;
                  leaf dst-address {
                    description 'Destination address.'
                                ;
                    type ncd:ipv4-address ;
                    mandatory true ;
                  }
                  leaf dst-address-mask {
                    description 'Destination maskcard bits.'
                                ;
                    type ncd:ipv4-mask ;
                    mandatory true ;
                  }
                }
                container source-ipv4-addr {
                  description 'Select source-address as match criteria.'
                              ;
                  presence 'Select source-address as match criteria'
                           ;
                  leaf src-address {
                    description 'Source address.'
                                ;
                    type ncd:ipv4-address ;
                    mandatory true ;
                  }
                  leaf src-address-mask {
                    description 'Source maskcard bits.'
                                ;
                    type ncd:ipv4-mask ;
                    mandatory true ;
                  }
                }
                container dscps {
                  description 'Select DSCP as match criteria'
                              ;
                  list dscp {
                    description 'Set DSCP value as match criteria'
                                ;
                    key ip-type ;
                    leaf ip-type {
                      description 'Configure DSCP value Based on IP, see below:'
                                + ''+"\n"
                                + '  ipv4 Packets based on IPv4;'
                                  ;
                      type enumeration {
                        enum ipv4 {
                          value 1 ;
                          description 'IPv4 type.'
                                      ;
                        }
                        enum ipv6 {
                          value 2 ;
                          description 'IPv6 type.'
                                      ;
                        }
                      }
                    }
                    leaf not {
                      description 'Configure the opposite range flag,'+"\n"
                                + '  true  Match opposite range'+"\n"
                                + '  false Match current range'
                                  ;
                      type boolean ;
                      default false ;
                    }
                    leaf dscp-value {
                      description 'Configure QoS dscp in range mode, support si'
                                + 'ngle DSCP value or range(max num:4;spacing m'
                                + 'ark:,) in <0-63>. For example,"6,10-30,40,50'
                                + '-60",etc.'
                                  ;
                      type qos-dscp-bitmap ;
                      mandatory true ;
                    }
                  }
                }
                container icmp-code {
                  description 'Select icmp-code as match criteria.'
                              ;
                  presence 'Select icmp-code as match criteria'
                           ;
                  leaf icmp-code-value {
                    description 'Configure icmp code in range mode, support sin'
                              + 'gle icmp-code value or range(max num:4;spacing'
                              + ' mark:,) in <0-255>. For example,"6,10-30,40,5'
                              + '0-60",etc.'
                                ;
                    type ncd:bitmap {
                      pattern '(((((([1-9][0-9]{1,1})|([1-9][0-9]{0,0})|0|([1-1'
                            + '][0-9]{2,2})|(2[0-4][0-9]{1,1})|(25[0-4])|255)-('
                            + '([1-9][0-9]{1,1})|([1-9][0-9]{0,0})|0|([1-1][0-9'
                            + ']{2,2})|(2[0-4][0-9]{1,1})|(25[0-4])|255))|(([1-'
                            + '9][0-9]{1,1})|([1-9][0-9]{0,0})|0|([1-1][0-9]{2,'
                            + '2})|(2[0-4][0-9]{1,1})|(25[0-4])|255)),){0,3}((('
                            + '([1-9][0-9]{1,1})|([1-9][0-9]{0,0})|0|([1-1][0-9'
                            + ']{2,2})|(2[0-4][0-9]{1,1})|(25[0-4])|255)-(([1-9'
                            + '][0-9]{1,1})|([1-9][0-9]{0,0})|0|([1-1][0-9]{2,2'
                            + '})|(2[0-4][0-9]{1,1})|(25[0-4])|255))|(([1-9][0-'
                            + '9]{1,1})|([1-9][0-9]{0,0})|0|([1-1][0-9]{2,2})|('
                            + '2[0-4][0-9]{1,1})|(25[0-4])|255)){1,1})'
                              {
                        description 'Configure icmp-code in range mode, support'
                                  + ' single icmp-code value or range(max num:4'
                                  + ';spacing mark:,) in <0-255>.'
                                    ;
                      }
                    }
                    mandatory true ;
                  }
                }
                container icmp-type {
                  description 'Select icmp-type as match criteria.'
                              ;
                  presence 'Select icmp-type as match criteria'
                           ;
                  leaf icmp-type-value {
                    description 'Configure icmp type in range mode, support sin'
                              + 'gle icmp-type value or range(max num:4;spacing'
                              + ' mark:,) in <0-255>. For example,"6,10-30,40,5'
                              + '0-60",etc.'
                                ;
                    type ncd:bitmap {
                      pattern '(((((([1-9][0-9]{1,1})|([1-9][0-9]{0,0})|0|([1-1'
                            + '][0-9]{2,2})|(2[0-4][0-9]{1,1})|(25[0-4])|255)-('
                            + '([1-9][0-9]{1,1})|([1-9][0-9]{0,0})|0|([1-1][0-9'
                            + ']{2,2})|(2[0-4][0-9]{1,1})|(25[0-4])|255))|(([1-'
                            + '9][0-9]{1,1})|([1-9][0-9]{0,0})|0|([1-1][0-9]{2,'
                            + '2})|(2[0-4][0-9]{1,1})|(25[0-4])|255)),){0,3}((('
                            + '([1-9][0-9]{1,1})|([1-9][0-9]{0,0})|0|([1-1][0-9'
                            + ']{2,2})|(2[0-4][0-9]{1,1})|(25[0-4])|255)-(([1-9'
                            + '][0-9]{1,1})|([1-9][0-9]{0,0})|0|([1-1][0-9]{2,2'
                            + '})|(2[0-4][0-9]{1,1})|(25[0-4])|255))|(([1-9][0-'
                            + '9]{1,1})|([1-9][0-9]{0,0})|0|([1-1][0-9]{2,2})|('
                            + '2[0-4][0-9]{1,1})|(25[0-4])|255)){1,1})'
                              {
                        description 'Configure icmp-type in range mode, support'
                                  + ' single icmp-type value or range(max num:4'
                                  + ';spacing mark:,) in <0-255>.'
                                    ;
                      }
                    }
                    mandatory true ;
                  }
                }
                container packet-length {
                  description 'Select packet-length as match criteria.'
                              ;
                  presence 'Select packet-length as match criteria'
                           ;
                  leaf packet-length-value {
                    description 'Configure packet-length in range mode, support'
                              + ' single packet-length value or range(max num:4'
                              + ';spacing mark:,) in <1-65535>. For example,"6,'
                              + '10-30,40,50-60",etc.'
                                ;
                    type ncd:range {
                      pattern '(((([1-9][0-9]{1,3})|([1-9])|([1-5][0-9]{4,4})|('
                            + '6[0-4][0-9]{3,3})|(65[0-4][0-9]{2,2})|(655[0-2]['
                            + '0-9]{1,1})|(6553[0-5]))(-(([1-9][0-9]{1,3})|([1-'
                            + '9])|([1-5][0-9]{4,4})|(6[0-4][0-9]{3,3})|(65[0-4'
                            + '][0-9]{2,2})|(655[0-2][0-9]{1,1})|(6553[0-5]))){'
                            + '0,1})((,)(([1-9][0-9]{1,3})|([1-9])|([1-5][0-9]{'
                            + '4,4})|(6[0-4][0-9]{3,3})|(65[0-4][0-9]{2,2})|(65'
                            + '5[0-2][0-9]{1,1})|(6553[0-5]))(-(([1-9][0-9]{1,3'
                            + '})|([1-9])|([1-5][0-9]{4,4})|(6[0-4][0-9]{3,3})|'
                            + '(65[0-4][0-9]{2,2})|(655[0-2][0-9]{1,1})|(6553[0'
                            + '-5]))){0,1}){0,3})'
                              {
                        description 'Configure packet-length in range mode, sup'
                                  + 'port single packet-length value or range(m'
                                  + 'ax num:4;spacing mark:,) in <1-65535>. For'
                                  + ' example,"6,10-30,40,50-60",etc.'
                                    ;
                      }
                    }
                    mandatory true ;
                  }
                }
                container protocol {
                  description 'Select protocol as match criteria.'
                              ;
                  presence 'Select protocol as match criteria'
                           ;
                  leaf not {
                    description 'Configure the opposite range flag,'+"\n"
                              + '  true  Match opposite range'+"\n"
                              + '  false Match current range'
                                ;
                    type boolean ;
                    default false ;
                  }
                  leaf protocol-value {
                    description 'Configure protocol in range mode, support sing'
                              + 'le protocol value or range(max num:4;spacing m'
                              + 'ark:,) in <0-255>. For example,"6,10-30,40,50-'
                              + '60",etc.'
                                ;
                    type ncd:bitmap {
                      pattern '(((((([1-9][0-9]{1,1})|([1-9][0-9]{0,0})|0|([1-1'
                            + '][0-9]{2,2})|(2[0-4][0-9]{1,1})|(25[0-4])|255)-('
                            + '([1-9][0-9]{1,1})|([1-9][0-9]{0,0})|0|([1-1][0-9'
                            + ']{2,2})|(2[0-4][0-9]{1,1})|(25[0-4])|255))|(([1-'
                            + '9][0-9]{1,1})|([1-9][0-9]{0,0})|0|([1-1][0-9]{2,'
                            + '2})|(2[0-4][0-9]{1,1})|(25[0-4])|255)),){0,3}((('
                            + '([1-9][0-9]{1,1})|([1-9][0-9]{0,0})|0|([1-1][0-9'
                            + ']{2,2})|(2[0-4][0-9]{1,1})|(25[0-4])|255)-(([1-9'
                            + '][0-9]{1,1})|([1-9][0-9]{0,0})|0|([1-1][0-9]{2,2'
                            + '})|(2[0-4][0-9]{1,1})|(25[0-4])|255))|(([1-9][0-'
                            + '9]{1,1})|([1-9][0-9]{0,0})|0|([1-1][0-9]{2,2})|('
                            + '2[0-4][0-9]{1,1})|(25[0-4])|255)){1,1})'
                              {
                        description 'Configure protocol in range mode, support '
                                  + 'single protocol value or range(max num:4;s'
                                  + 'pacing mark:,).'
                                    ;
                      }
                    }
                    mandatory true ;
                  }
                }
                container tcp-flag {
                  description 'Select tcp-flag as match criteria.'
                              ;
                  presence 'Select tcp-flag as match criteria'
                           ;
                  leaf not {
                    description 'Logical negation of operation,'+"\n"
                              + '  true  Match opposite'+"\n"
                              + '  false Match current.'
                                ;
                    type boolean ;
                    default false ;
                  }
                  leaf match-relation {
                    description 'The rule of matching, see bellow:             '
                              + '   '+"\n"
                              + '  all  Match all of the tcp flag'+"\n"
                              + '  any  Match any of the tcp flag.'
                                ;
                    type enumeration {
                      enum all {
                        value 0 ;
                        description 'Match all of the tcp flag.'
                                    ;
                      }
                      enum any {
                        value 1 ;
                        description 'Match any of the tcp flag.'
                                    ;
                      }
                    }
                    mandatory true ;
                  }
                  choice tcp-flag-option {
                    description 'TCP Flag.'
                                ;
                    mandatory true ;
                    case tcp-flag {
                      description 'TCP Flag.'
                                  ;
                      leaf rst {
                        description 'Match on the RST bit.'
                                    ;
                        type boolean ;
                        default false ;
                      }
                      leaf ack {
                        description 'Match on the ACK bit.'
                                    ;
                        type boolean ;
                        default false ;
                      }
                      leaf fin {
                        description 'Match on the FIN bit.'
                                    ;
                        type boolean ;
                        default false ;
                      }
                      leaf syn {
                        description 'Match on the SYN bit.'
                                    ;
                        type boolean ;
                        default false ;
                      }
                      leaf psh {
                        description 'Match on the PSH bit.'
                                    ;
                        type boolean ;
                        default false ;
                      }
                      leaf urg {
                        description 'Match on the URG bit.'
                                    ;
                        type boolean ;
                        default false ;
                      }
                      leaf ece {
                        description 'Match on the ECE bit.'
                                    ;
                        type boolean ;
                        default false ;
                      }
                      leaf cwr {
                        description 'Match on the CWR bit.'
                                    ;
                        type boolean ;
                        default false ;
                      }
                    }
                  }
                }
                container flow-label {
                  description 'Select flow-label as match criteria.'
                              ;
                  presence 'Select flow-label as match criteria'
                           ;
                  leaf flow-label-value {
                    description 'Flow label value.'
                                ;
                    type uint32 {
                      range 0..1048575 ;
                    }
                    mandatory true ;
                  }
                  ncd:revise-date 2020-02-03 ;
                }
                container destination-ipv6-addr {
                  description 'Select IPv6 destination address as match criteri'
                            + 'a.'
                              ;
                  presence 'Select IPv6 destination address as match criteria'
                           ;
                  leaf dst-ipv6-addr {
                    description 'IPv6 destination address.'
                                ;
                    type ncd:ipv6-address ;
                    mandatory true ;
                  }
                  leaf dst-ipv6-addr-prefix {
                    description 'IPv6 destination maskcard length.'
                                ;
                    type ncd:ipv6-mask-length ;
                    mandatory true ;
                  }
                  ncd:revise-date 2020-02-03 ;
                }
                container source-ipv6-addr {
                  description 'Select IPv6 source-address as match criteria.'
                              ;
                  presence 'Select IPv6 source-address as match criteria'
                           ;
                  leaf src-ipv6-addr {
                    description 'IPv6 source address.'
                                ;
                    type ncd:ipv6-address ;
                    mandatory true ;
                  }
                  leaf src-ipv6-addr-prefix {
                    description 'IPv6 source maskcard length.'
                                ;
                    type ncd:ipv6-mask-length ;
                    mandatory true ;
                  }
                  ncd:revise-date 2020-02-03 ;
                }
                container ipv6-icmp-code {
                  description 'Select IPv6 icmp-code as match criteria.'
                              ;
                  presence 'Select IPv6 icmp-code as match criteria'
                           ;
                  leaf icmp-code-value {
                    description 'Configure icmp code in range mode, support sin'
                              + 'gle icmp-code value or range(max num:4;spacing'
                              + ' mark:,) in <0-255>. For example,"6,10-30,40,5'
                              + '0-60",etc.'
                                ;
                    type ncd:bitmap {
                      pattern '(((((([1-9][0-9]{1,1})|([1-9][0-9]{0,0})|0|([1-1'
                            + '][0-9]{2,2})|(2[0-4][0-9]{1,1})|(25[0-4])|255)-('
                            + '([1-9][0-9]{1,1})|([1-9][0-9]{0,0})|0|([1-1][0-9'
                            + ']{2,2})|(2[0-4][0-9]{1,1})|(25[0-4])|255))|(([1-'
                            + '9][0-9]{1,1})|([1-9][0-9]{0,0})|0|([1-1][0-9]{2,'
                            + '2})|(2[0-4][0-9]{1,1})|(25[0-4])|255)),){0,3}((('
                            + '([1-9][0-9]{1,1})|([1-9][0-9]{0,0})|0|([1-1][0-9'
                            + ']{2,2})|(2[0-4][0-9]{1,1})|(25[0-4])|255)-(([1-9'
                            + '][0-9]{1,1})|([1-9][0-9]{0,0})|0|([1-1][0-9]{2,2'
                            + '})|(2[0-4][0-9]{1,1})|(25[0-4])|255))|(([1-9][0-'
                            + '9]{1,1})|([1-9][0-9]{0,0})|0|([1-1][0-9]{2,2})|('
                            + '2[0-4][0-9]{1,1})|(25[0-4])|255)){1,1})'
                              {
                        description 'Configure icmp-code in range mode, support'
                                  + ' single icmp-code value or range(max num:4'
                                  + ';spacing mark:,) in <0-255>.'
                                    ;
                      }
                    }
                    mandatory true ;
                  }
                  ncd:revise-date 2020-02-03 ;
                }
                container ipv6-icmp-type {
                  description 'Select IPv6 icmp-type as match criteria.'
                              ;
                  presence 'Select IPv6 icmp-type as match criteria'
                           ;
                  leaf icmp-type-value {
                    description 'Configure icmp type in range mode, support sin'
                              + 'gle icmp-type value or range(max num:4;spacing'
                              + ' mark:,) in <0-255>. For example,"6,10-30,40,5'
                              + '0-60",etc.'
                                ;
                    type ncd:bitmap {
                      pattern '(((((([1-9][0-9]{1,1})|([1-9][0-9]{0,0})|0|([1-1'
                            + '][0-9]{2,2})|(2[0-4][0-9]{1,1})|(25[0-4])|255)-('
                            + '([1-9][0-9]{1,1})|([1-9][0-9]{0,0})|0|([1-1][0-9'
                            + ']{2,2})|(2[0-4][0-9]{1,1})|(25[0-4])|255))|(([1-'
                            + '9][0-9]{1,1})|([1-9][0-9]{0,0})|0|([1-1][0-9]{2,'
                            + '2})|(2[0-4][0-9]{1,1})|(25[0-4])|255)),){0,3}((('
                            + '([1-9][0-9]{1,1})|([1-9][0-9]{0,0})|0|([1-1][0-9'
                            + ']{2,2})|(2[0-4][0-9]{1,1})|(25[0-4])|255)-(([1-9'
                            + '][0-9]{1,1})|([1-9][0-9]{0,0})|0|([1-1][0-9]{2,2'
                            + '})|(2[0-4][0-9]{1,1})|(25[0-4])|255))|(([1-9][0-'
                            + '9]{1,1})|([1-9][0-9]{0,0})|0|([1-1][0-9]{2,2})|('
                            + '2[0-4][0-9]{1,1})|(25[0-4])|255)){1,1})'
                              {
                        description 'Configure icmp-type in range mode, support'
                                  + ' single icmp-type value or range(max num:4'
                                  + ';spacing mark:,) in <0-255>.'
                                    ;
                      }
                    }
                    mandatory true ;
                  }
                  ncd:revise-date 2020-02-03 ;
                }
                container next-header {
                  description 'Select next-header as match criteria.'
                              ;
                  presence 'Select next-header as match criteria'
                           ;
                  leaf not {
                    description 'Configure the opposite range flag.'
                                ;
                    type empty ;
                  }
                  leaf next-header-value {
                    description 'Configure next-header in range mode, support s'
                              + 'ingle value or range(max num:4;spacing mark:,)'
                              + ' in <0-255>. For example,"6,10-30,40,50-60",et'
                              + 'c.'
                                ;
                    type ncd:bitmap {
                      pattern '(((((([1-9][0-9]{1,1})|([1-9][0-9]{0,0})|0|([1-1'
                            + '][0-9]{2,2})|(2[0-4][0-9]{1,1})|(25[0-4])|255)-('
                            + '([1-9][0-9]{1,1})|([1-9][0-9]{0,0})|0|([1-1][0-9'
                            + ']{2,2})|(2[0-4][0-9]{1,1})|(25[0-4])|255))|(([1-'
                            + '9][0-9]{1,1})|([1-9][0-9]{0,0})|0|([1-1][0-9]{2,'
                            + '2})|(2[0-4][0-9]{1,1})|(25[0-4])|255)),){0,3}((('
                            + '([1-9][0-9]{1,1})|([1-9][0-9]{0,0})|0|([1-1][0-9'
                            + ']{2,2})|(2[0-4][0-9]{1,1})|(25[0-4])|255)-(([1-9'
                            + '][0-9]{1,1})|([1-9][0-9]{0,0})|0|([1-1][0-9]{2,2'
                            + '})|(2[0-4][0-9]{1,1})|(25[0-4])|255))|(([1-9][0-'
                            + '9]{1,1})|([1-9][0-9]{0,0})|0|([1-1][0-9]{2,2})|('
                            + '2[0-4][0-9]{1,1})|(25[0-4])|255)){1,1})'
                              {
                        description 'Configure protocol in range mode, support '
                                  + 'single protocol value or range(max num:4;s'
                                  + 'pacing mark:,).'
                                    ;
                      }
                    }
                    mandatory true ;
                  }
                  ncd:revise-date 2020-02-03 ;
                }
              }
              container cmap-description {
                description 'Description of a class map, support 1-79 character'
                          + 's.'
                            ;
                presence 'Specify description of class map'
                         ;
                leaf cmap-description {
                  description 'Description of a class map, support 1-79 charact'
                            + 'ers.'
                              ;
                  type ncd:string-with-blank {
                    length 1..79 {
                      description 'Description of a class map, support 1-79 cha'
                                + 'racters.'
                                  ;
                    }
                  }
                  mandatory true ;
                }
                ncd:revise-date 2020-06-18 ;
              }
            }
          }
          ncd:revise-date 2017-06-12 ;
        }
        container class-map-id {
          description 'H-QoS class map lists id, only for the query'
                      ;
          container class-maps {
            description 'H-QoS class map lists'
                        ;
            list class-map {
              description 'H-QoS class map list'
                          ;
              key cmap-name ;
              leaf cmap-name {
                description 'Name of the class map, support 1-31 characters'
                            ;
                type string {
                  length 1..31 {
                    description 'Name of the class map, support 1-31 characters'
                                ;
                  }
                }
              }
              leaf cmap-id {
                description 'H-QoS class map lists id'
                            ;
                type uint32 {
                  range 1..4000 {
                    description 'H-QoS class map lists id'
                                ;
                  }
                }
              }
            }
          }
          ncd:revise-date 2015-03-31 ;
        }
        container flow-feature {
          description 'Class map flow feature defination.'
                      ;
          container class-maps {
            description 'Configure H-QoS class map lists.'
                        ;
            list class-map {
              description 'Configure H-QoS class map list'
                          ;
              key cmap-name ;
              leaf cmap-name {
                description 'Name of the class map, support 1-31 characters'
                            ;
                type string {
                  length 1..31 {
                    description 'Name of the class map, support 1-31 characters'
                                ;
                  }
                }
              }
              container effect-order {
                description 'The value specify the class effect order in the po'
                          + 'licy map.'
                            ;
                presence 'To set the effect order value'
                         ;
                leaf effect-order {
                  description 'The value specify the class effect order in the '
                            + 'policy map.'
                              ;
                  type uint32 {
                    range 1..255 {
                      description 'The value specify the class effect order in '
                                + 'the policy map.'
                                  ;
                    }
                  }
                  mandatory true ;
                }
              }
              container match {
                description 'Configure match criteria for a class map'
                            ;
                container destination-port {
                  description 'Select destination-port as match criteria.'
                              ;
                  presence 'Select destination-port as match criteria'
                           ;
                  leaf dst-port-value {
                    description 'Configure destination-port value in range mode'
                              + ', support single destination-port value or ran'
                              + 'ge(max num:4;spacing mark:,) in <0-65535>. For'
                              + ' example,"1,300-400,1000,2000-4000",etc.'
                                ;
                    type qos-port-range ;
                    mandatory true ;
                  }
                }
                container source-port {
                  description 'Select source-port as match criteria.'
                              ;
                  presence 'Select source-port as match criteria'
                           ;
                  leaf src-port-value {
                    description 'Configure soure-port value in range mode, supp'
                              + 'ort single soure-port value or range(max num:4'
                              + ';spacing mark:,) in <0-65535>. For example,"1,'
                              + '300-400,1000,2000-4000",etc.'
                                ;
                    type qos-port-range ;
                    mandatory true ;
                  }
                }
                container destination-ipv4-addr {
                  description 'Select destination-address as match criteria.'
                              ;
                  presence 'Select destination-address as match criteria'
                           ;
                  leaf dst-address {
                    description 'Destination address.'
                                ;
                    type ncd:ipv4-address ;
                    mandatory true ;
                  }
                  leaf dst-address-mask {
                    description 'Destination maskcard bits.'
                                ;
                    type ncd:ipv4-mask ;
                    mandatory true ;
                  }
                }
                container source-ipv4-addr {
                  description 'Select source-address as match criteria.'
                              ;
                  presence 'Select source-address as match criteria'
                           ;
                  leaf src-address {
                    description 'Source address.'
                                ;
                    type ncd:ipv4-address ;
                    mandatory true ;
                  }
                  leaf src-address-mask {
                    description 'Source maskcard bits.'
                                ;
                    type ncd:ipv4-mask ;
                    mandatory true ;
                  }
                }
                container protocol {
                  description 'Select protocol as match criteria.'
                              ;
                  presence 'Select protocol as match criteria'
                           ;
                  leaf not {
                    description 'Configure the opposite range flag,'+"\n"
                              + '  true  Match opposite range'+"\n"
                              + '  false Match current range'
                                ;
                    type boolean ;
                  }
                  leaf protocol-value {
                    description 'Configure protocol in range mode, support sing'
                              + 'le protocol value or range(max num:4;spacing m'
                              + 'ark:,) in <0-255>. For example,"6,10-30,40,50-'
                              + '60",etc.'
                                ;
                    type ncd:bitmap {
                      pattern '(((((([1-9][0-9]{1,1})|([1-9][0-9]{0,0})|0|([1-1'
                            + '][0-9]{2,2})|(2[0-4][0-9]{1,1})|(25[0-4])|255)-('
                            + '([1-9][0-9]{1,1})|([1-9][0-9]{0,0})|0|([1-1][0-9'
                            + ']{2,2})|(2[0-4][0-9]{1,1})|(25[0-4])|255))|(([1-'
                            + '9][0-9]{1,1})|([1-9][0-9]{0,0})|0|([1-1][0-9]{2,'
                            + '2})|(2[0-4][0-9]{1,1})|(25[0-4])|255)),){0,3}((('
                            + '([1-9][0-9]{1,1})|([1-9][0-9]{0,0})|0|([1-1][0-9'
                            + ']{2,2})|(2[0-4][0-9]{1,1})|(25[0-4])|255)-(([1-9'
                            + '][0-9]{1,1})|([1-9][0-9]{0,0})|0|([1-1][0-9]{2,2'
                            + '})|(2[0-4][0-9]{1,1})|(25[0-4])|255))|(([1-9][0-'
                            + '9]{1,1})|([1-9][0-9]{0,0})|0|([1-1][0-9]{2,2})|('
                            + '2[0-4][0-9]{1,1})|(25[0-4])|255)){1,1})'
                              {
                        description 'Configure protocol in range mode, support '
                                  + 'single protocol value or range(max num:4;s'
                                  + 'pacing mark:,).'
                                    ;
                      }
                    }
                    mandatory true ;
                  }
                }
                container destination-ipv6-addr {
                  description 'Select destination-address as match criteria.'
                              ;
                  presence 'Select destination-address as match criteria'
                           ;
                  leaf dst-address {
                    description 'Destination address.'
                                ;
                    type ncd:ipv6-address ;
                    mandatory true ;
                  }
                  leaf dst-address-mask {
                    description 'Destination maskcard bits.'
                                ;
                    type uint8 {
                      range 0..128 {
                        description 'Destination maskcard bits.'
                                    ;
                      }
                    }
                    mandatory true ;
                  }
                }
                container source-ipv6-addr {
                  description 'Select source-address as match criteria.'
                              ;
                  presence 'Select source-address as match criteria'
                           ;
                  leaf src-address {
                    description 'Source address.'
                                ;
                    type ncd:ipv6-address ;
                    mandatory true ;
                  }
                  leaf src-address-mask {
                    description 'Source maskcard bits.'
                                ;
                    type uint8 {
                      range 0..128 {
                        description 'Source maskcard bits.'
                                    ;
                      }
                    }
                    mandatory true ;
                  }
                }
                container interface {
                  description 'Select interface name as match criteria'
                              ;
                  presence 'Select interface name as match criteria'
                           ;
                  leaf if-name {
                    description 'Set interface name'
                                ;
                    type ncd:ifname {
                      length 1..31 {
                        description 'Name of the interface, support 1-31 charac'
                                  + 'ters'
                                    ;
                      }
                    }
                    mandatory true ;
                  }
                }
                container vxlan-ipv4 {
                  description 'Select VXLAN tunnel as match criteria.'
                              ;
                  presence 'Select VXLAN tunnel as match criteria'
                           ;
                  leaf src-address {
                    description 'Source address.'
                                ;
                    type ncd:ipv4-address ;
                    mandatory true ;
                  }
                  leaf dst-address {
                    description 'Destination address.'
                                ;
                    type ncd:ipv4-address ;
                    mandatory true ;
                  }
                }
                container vni {
                  description 'To select VNI (VXLAN Network Identifier) as matc'
                            + 'h criteria'
                              ;
                  presence 'To select VNI as match criteria'
                           ;
                  leaf vni-range1-start {
                    description 'The starting-value of the first VNI range'
                                ;
                    type uint32 {
                      range 1..16777215 ;
                    }
                    mandatory true ;
                  }
                  leaf vni-range1-end {
                    description 'The ending-value of the first VNI range'
                                ;
                    type uint32 {
                      range 1..16777215 ;
                    }
                    mandatory true ;
                  }
                  container vni-range2 {
                    description 'To select the second VNI range'
                                ;
                    presence 'The configuration of the second VNI range'
                             ;
                    leaf vni-range2-start {
                      description 'The starting-value of the second VNI range'
                                  ;
                      type uint32 {
                        range 1..16777215 ;
                      }
                      mandatory true ;
                    }
                    leaf vni-range2-end {
                      description 'The ending-value of the second VNI range'
                                  ;
                      type uint32 {
                        range 1..16777215 ;
                      }
                      mandatory true ;
                    }
                    container vni-range3 {
                      description 'To select the third VNI range'
                                  ;
                      presence 'The configuration of the third VNI range'
                               ;
                      leaf vni-range3-start {
                        description 'The starting-value of the third VNI range'
                                    ;
                        type uint32 {
                          range 1..16777215 ;
                        }
                        mandatory true ;
                      }
                      leaf vni-range3-end {
                        description 'The ending-value of the third VNI range'
                                    ;
                        type uint32 {
                          range 1..16777215 ;
                        }
                        mandatory true ;
                      }
                      container vni-range4 {
                        description 'To select the fourth VNI range'
                                    ;
                        presence 'The configuration of the fourth VNI range'
                                 ;
                        leaf vni-range4-start {
                          description 'The starting-value of the fourth VNI ran'
                                    + 'ge'
                                      ;
                          type uint32 {
                            range 1..16777215 ;
                          }
                          mandatory true ;
                        }
                        leaf vni-range4-end {
                          description 'The ending-value of the fourth VNI range'
                                      ;
                          type uint32 {
                            range 1..16777215 ;
                          }
                          mandatory true ;
                        }
                      }
                    }
                  }
                }
                container vxlan-ipv6 {
                  description 'Select VXLAN tunnel as match criteria.'
                              ;
                  presence 'Select VXLAN tunnel as match criteria'
                           ;
                  leaf src-address {
                    description 'Source address.'
                                ;
                    type ncd:ipv6-address ;
                    mandatory true ;
                  }
                  leaf dst-address {
                    description 'Destination address.'
                                ;
                    type ncd:ipv6-address ;
                    mandatory true ;
                  }
                  ncd:revise-date 2020-03-05 ;
                }
              }
              container cmap-description {
                description 'Description of a class map, support 1-79 character'
                          + 's.'
                            ;
                presence 'Specify description of class map'
                         ;
                leaf cmap-description {
                  description 'Description of a class map, support 1-79 charact'
                            + 'ers.'
                              ;
                  type ncd:string-with-blank {
                    length 1..79 {
                      description 'Description of a class map, support 1-79 cha'
                                + 'racters.'
                                  ;
                    }
                  }
                  mandatory true ;
                }
                ncd:revise-date 2020-06-18 ;
              }
            }
          }
          ncd:revise-date 2019-04-15 ;
        }
        container traffic-based {
          description 'Class map based on traffic'
                      ;
          container class-maps {
            description 'Configure H-QoS class map lists'
                        ;
            list class-map {
              description 'Configure H-QoS class map list'
                          ;
              key cmap-name ;
              leaf cmap-name {
                description 'Name of the class map, support 1-31 characters'
                            ;
                type string {
                  length 1..31 {
                    description 'Name of the class map, support 1-31 characters'
                                ;
                  }
                }
              }
              leaf match-relation {
                description 'The type of packets matching, see bellow:         '
                          + '       '+"\n"
                          + '  match-all Packets meet all of the match criteria'
                          + ''+"\n"
                          + '  match-any Packets meet any of the match criteria'
                            ;
                type enumeration {
                  enum match-all {
                    value 1 ;
                    description 'Packets meet all of the match criteria'
                                ;
                  }
                  enum match-any {
                    value 2 ;
                    description 'Packets meet any of the match criteria'
                                ;
                  }
                }
                mandatory true ;
              }
              container match {
                description 'Configure match criteria for a class map'
                            ;
                container dscps {
                  description 'Select DSCP as match criteria'
                              ;
                  list dscp {
                    description 'Set DSCP value as match criteria'
                                ;
                    key ip-type ;
                    leaf ip-type {
                      description 'Configure DSCP value Based on IP, see below:'
                                + ''+"\n"
                                + '  any  Packets based on any IP;'+"\n"
                                + '  ipv4 Packets based on IPv4;'+"\n"
                                + '  ipv6 Packets based on IPv6;'
                                  ;
                      type qos-ip-type ;
                    }
                    leaf not {
                      description 'Configure the opposite range flag,'+"\n"
                                + '  true  Match opposite range'+"\n"
                                + '  false Match current range'
                                  ;
                      type boolean ;
                      default false ;
                    }
                    leaf dscp-value {
                      description 'Configure QoS dscp in range mode, support si'
                                + 'ngle DSCP value or range(max num:4;spacing m'
                                + 'ark:,) in <0-63>. For example,"6,10-30,40,50'
                                + '-60",etc.'
                                  ;
                      type qos-dscp-bitmap ;
                      mandatory true ;
                    }
                  }
                }
                container dscp-exs {
                  if-feature class-match-dscp-ex ;
                  description 'Set DSCP value as match criteria in PHB mode'
                              ;
                  list dscp-ex {
                    description 'Set DSCP value as match criteria in PHB mode'
                                ;
                    key 'ip-type reserved-words'
                        ;
                    leaf ip-type {
                      description 'Configure DSCP value Based on IP, see below:'
                                + ''+"\n"
                                + '  any  Packets based on any IP;'+"\n"
                                + '  ipv4 Packets based on IPv4;'+"\n"
                                + '  ipv6 Packets based on IPv6;'
                                  ;
                      type qos-ip-type ;
                    }
                    leaf reserved-words {
                      description 'Configure DSCP value in the manner of PHB,se'
                                + 'e below,'+"\n"
                                + 'resserved words:'+"\n"
                                + '  default(0) Match packets with default dscp'
                                + ' (000000)      '+"\n"
                                + '  af11(10)   Match packets with AF11 dscp (0'
                                + '01010)                                '+"\n"
                                + '  af12(12)   Match packets with AF12 dscp (0'
                                + '01100)                                '+"\n"
                                + '  af13(14)   Match packets with AF13 dscp (0'
                                + '01110)                                '+"\n"
                                + '  af21(18)   Match packets with AF21 dscp (0'
                                + '10010)                                '+"\n"
                                + '  af22(20)   Match packets with AF22 dscp (0'
                                + '10100)                                '+"\n"
                                + '  af23(22)   Match packets with AF23 dscp (0'
                                + '10110)                                '+"\n"
                                + '  af31(26)   Match packets with AF31 dscp (0'
                                + '11010)                                '+"\n"
                                + '  af32(28)   Match packets with AF32 dscp (0'
                                + '11100)                                '+"\n"
                                + '  af33(30)   Match packets with AF33 dscp (0'
                                + '11110)                                '+"\n"
                                + '  af41(34)   Match packets with AF41 dscp (1'
                                + '00010)                                '+"\n"
                                + '  af42(36)   Match packets with AF42 dscp (1'
                                + '00100)                                '+"\n"
                                + '  af43(38)   Match packets with AF43 dscp (1'
                                + '00110)   '+"\n"
                                + '  ef(46)     Match packets with EF dscp (101'
                                + '110)                             '+"\n"
                                + '  cs1(8)     Match packets with CS1(preceden'
                                + 'ce 1) dscp (001000)                   '+"\n"
                                + '  cs2(16)    Match packets with CS2(preceden'
                                + 'ce 2) dscp (010000)                   '+"\n"
                                + '  cs3(24)    Match packets with CS3(preceden'
                                + 'ce 3) dscp (011000)                   '+"\n"
                                + '  cs4(32)    Match packets with CS4(preceden'
                                + 'ce 4) dscp (100000)                   '+"\n"
                                + '  cs5(40)    Match packets with CS5(preceden'
                                + 'ce 5) dscp (101000)                   '+"\n"
                                + '  cs6(48)    Match packets with CS6(preceden'
                                + 'ce 6) dscp (110000)                   '+"\n"
                                + '  cs7(56)    Match packets with CS7(preceden'
                                + 'ce 7) dscp (111000)'
                                  ;
                      type qos-reserved-words ;
                    }
                  }
                }
                container precedences {
                  description 'Select IP-Precedence as match criteria'
                              ;
                  list precedence {
                    description 'Set IP Precedence value as match criteria'
                                ;
                    key ip-type ;
                    leaf ip-type {
                      description 'Configure DSCP value Based on IP, see below:'
                                + ''+"\n"
                                + '  any  Packets based on any IP;'+"\n"
                                + '  ipv4 Packets based on IPv4;'+"\n"
                                + '  ipv6 Packets based on IPv6;'
                                  ;
                      type qos-ip-type ;
                    }
                    leaf not {
                      description 'Configure the opposite range flag,'+"\n"
                                + '  true  Match opposite range'+"\n"
                                + '  false Match current range'
                                  ;
                      type boolean ;
                      default false ;
                    }
                    leaf prec-value {
                      description 'Configure QoS IP Precedence in range mode, s'
                                + 'upport single precedence value or range(max '
                                + 'num:4;spacing mark:,) in <0-7>. For example,'
                                + '"0,2-4,7",etc.'
                                  ;
                      type qos-prec-bitmap ;
                      mandatory true ;
                    }
                  }
                }
                container mpls-exp {
                  description 'Select MPLS-EXP as match criteria'
                              ;
                  presence 'Select MPLS-EXP as match criteria'
                           ;
                  leaf mpls-exp-value {
                    description 'Configure QoS MPLS-EXP value in range mode, su'
                              + 'pport single MPLS-EXP value or range(max num:4'
                              + ';spacing mark:,) in <0-7>. For example,"0,2-4,'
                              + '7",etc.'
                                ;
                    type qos-mpls-bitmap ;
                    mandatory true ;
                  }
                }
                container in-vlan {
                  description 'Select inner-VLAN as match criteria'
                              ;
                  presence 'Select inner-VLAN as match criteria'
                           ;
                  leaf vlan-value {
                    description 'Configure inner-VLAN value in range mode, supp'
                              + 'ort single inner-VLAN value or range(max num:4'
                              + ';spacing mark:,) in <1-4094>. For example,"1,3'
                              + '00-400,1000,2000-4000",etc.'
                                ;
                    type qos-vlan-bitmap ;
                    mandatory true ;
                  }
                }
                container out-vlan {
                  description 'Select outer-VLAN as match criteria'
                              ;
                  presence 'Select outer-VLAN as match criteria'
                           ;
                  leaf vlan-value {
                    description 'Configure outer-VLAN value in range mode, supp'
                              + 'ort single outer-VLAN value or range(max num:4'
                              + ';spacing mark:,) in <1-4094>. For example,"1,3'
                              + '00-400,1000,2000-4000",etc.'
                                ;
                    type qos-vlan-bitmap ;
                    mandatory true ;
                  }
                }
                container in-8021p {
                  description 'Select inner 802.1p as match criteria'
                              ;
                  presence 'Select inner 802.1p as match criteria'
                           ;
                  leaf in-8021p-value {
                    description 'Configure inner 802.1p value in range mode, su'
                              + 'pport single 802.1p value or range(max num:4;s'
                              + 'pacing mark:,) in <0-7>. For example,"0,2-4,7"'
                              + ',etc.'
                                ;
                    type qos-8021p-bitmap ;
                    mandatory true ;
                  }
                }
                container out-8021p {
                  description 'Select outer 802.1p as match criteria'
                              ;
                  presence 'Select outer 802.1p as match criteria'
                           ;
                  leaf out-8021p-value {
                    description 'Configure outer 802.1p value in range mode, su'
                              + 'pport single 802.1p value or range(max num:4;s'
                              + 'pacing mark:,) in <0-7>. For example,"0,2-4,7"'
                              + ',etc.'
                                ;
                    type qos-8021p-bitmap ;
                    mandatory true ;
                  }
                }
                container qos-group {
                  description 'Select qos-group as match criteria'
                              ;
                  presence 'Select qos-group as match criteria'
                           ;
                  leaf qos-id {
                    description 'Set qos-group number,support <1-65535>'
                                ;
                    type uint16 {
                      range 1..65535 ;
                    }
                    mandatory true ;
                  }
                }
                container vrf-name {
                  description 'Select vrf-name as match criteria'
                              ;
                  presence 'Select vrf-name as match criteria'
                           ;
                  leaf vrf-name {
                    description 'Set vrf name, support 1-32 characters'
                                ;
                    type string {
                      length 1..32 {
                        description 'Vrf name, support 1-32 characters'
                                    ;
                      }
                    }
                    mandatory true ;
                  }
                }
                container uni-cast {
                  description 'Select unicast as match criteria'
                              ;
                  presence 'Select unicast as match criteria'
                           ;
                  leaf uni-cast {
                    description 'Set unicast as match criteria'
                                ;
                    type empty ;
                    mandatory true ;
                  }
                }
                container multi-cast {
                  description 'Select multicast as match criteria'
                              ;
                  presence 'Select multicast as match criteria'
                           ;
                  leaf multi-cast {
                    description 'Set multicast as match criteria'
                                ;
                    type empty ;
                    mandatory true ;
                  }
                }
                container mac-addr {
                  description 'Select mac-address as match criteria'
                              ;
                  presence 'Select mac-address as match criteria'
                           ;
                  leaf mac-address {
                    description 'Configure mac-address'
                                ;
                    type ncd:mac-address ;
                    mandatory true ;
                  }
                }
                container ipv4-acls {
                  description 'Select IPv4 ACL name as match criteria'
                              ;
                  list ipv4-acl {
                    description 'Set IPv4 ACL name as match criteria'
                                ;
                    key acl-name ;
                    leaf acl-name {
                      description 'Set ipv4-access-list name, support 1-31 char'
                                + 'acters'
                                  ;
                      type string {
                        length 1..31 {
                          description 'Name of ACL, support 1-31 characters'
                                      ;
                        }
                      }
                    }
                  }
                }
                container ipv6-acls {
                  description 'Select IPv6 ACL name as match criteria'
                              ;
                  list ipv6-acl {
                    description 'Set IPv6 ACL name as match criteria'
                                ;
                    key acl-name ;
                    leaf acl-name {
                      description 'Set ipv6-access-list name, support 1-31 char'
                                + 'acters'
                                  ;
                      type string {
                        length 1..31 {
                          description 'Name of ACL, support 1-31 characters'
                                      ;
                        }
                      }
                    }
                  }
                }
                container link-acls {
                  if-feature class-match-link-acl ;
                  description 'Select link ACL name as match criteria'
                              ;
                  list link-acl {
                    description 'Set link ACL name as match criteria'
                                ;
                    key acl-name ;
                    leaf acl-name {
                      description 'Set link-access-list name, support 1-31 char'
                                + 'acters'
                                  ;
                      type string {
                        length 1..31 {
                          description 'Name of ACL, support 1-31 characters'
                                      ;
                        }
                      }
                    }
                  }
                }
                container vpws {
                  description 'Select VPWS instance name as match criteria'
                              ;
                  presence 'Select VPWS instance name as match criteria'
                           ;
                  leaf vpws-name {
                    description 'Set VPWS instance name, support 1-32 characters'
                                ;
                    type string {
                      length 1..32 {
                        description 'VPWS instance name, support 1-32 characters'
                                    ;
                      }
                    }
                    mandatory true ;
                  }
                }
                container vpls {
                  description 'Select VPLS instance name as match criteria'
                              ;
                  presence 'Select VPLS instance name as match criteria'
                           ;
                  leaf vpls-name {
                    description 'Set VPLS instance name, support 1-32 characters'
                                ;
                    type string {
                      length 1..32 {
                        description 'VPLS instance name, support 1-32 characters'
                                    ;
                      }
                    }
                    mandatory true ;
                  }
                }
                container service-class {
                  if-feature phb-mode ;
                  description 'Select PHB as match criteria'
                              ;
                  presence 'Select PHB as match criteria'
                           ;
                  leaf service-class {
                    description 'Select service class of PHB info, see below:'+"\n"
                              + '  be  Best effort'+"\n"
                              + '  af1 Assured forwarding class 1'+"\n"
                              + '  af2 Assured forwarding class 2'+"\n"
                              + '  af3 Assured forwarding class 3'+"\n"
                              + '  af4 Assured forwarding class 4'+"\n"
                              + '  ef  Expedited forward'+"\n"
                              + '  cs6 Internetwork control service class'+"\n"
                              + '  cs7 Network control service class'
                                ;
                    type qos-service-class ;
                    mandatory true ;
                  }
                }
                container vni {
                  description 'To select VNI (VXLAN Network Identifier) as matc'
                            + 'h criteria'
                              ;
                  presence 'To select VNI as match criteria'
                           ;
                  leaf vni-range1-start {
                    description 'The starting-value of the first VNI range'
                                ;
                    type uint32 {
                      range 1..16777215 ;
                    }
                    mandatory true ;
                  }
                  leaf vni-range1-end {
                    description 'The ending-value of the first VNI range'
                                ;
                    type uint32 {
                      range 1..16777215 ;
                    }
                    mandatory true ;
                  }
                  container vni-range2 {
                    description 'To select the second VNI range'
                                ;
                    presence 'The configuration of the second VNI range'
                             ;
                    leaf vni-range2-start {
                      description 'The starting-value of the second VNI range'
                                  ;
                      type uint32 {
                        range 1..16777215 ;
                      }
                      mandatory true ;
                    }
                    leaf vni-range2-end {
                      description 'The ending-value of the second VNI range'
                                  ;
                      type uint32 {
                        range 1..16777215 ;
                      }
                      mandatory true ;
                    }
                    container vni-range3 {
                      description 'To select the third VNI range'
                                  ;
                      presence 'The configuration of the third VNI range'
                               ;
                      leaf vni-range3-start {
                        description 'The starting-value of the third VNI range'
                                    ;
                        type uint32 {
                          range 1..16777215 ;
                        }
                        mandatory true ;
                      }
                      leaf vni-range3-end {
                        description 'The ending-value of the third VNI range'
                                    ;
                        type uint32 {
                          range 1..16777215 ;
                        }
                        mandatory true ;
                      }
                      container vni-range4 {
                        description 'To select the fourth VNI range'
                                    ;
                        presence 'The configuration of the fourth VNI range'
                                 ;
                        leaf vni-range4-start {
                          description 'The starting-value of the fourth VNI ran'
                                    + 'ge'
                                      ;
                          type uint32 {
                            range 1..16777215 ;
                          }
                          mandatory true ;
                        }
                        leaf vni-range4-end {
                          description 'The ending-value of the fourth VNI range'
                                      ;
                          type uint32 {
                            range 1..16777215 ;
                          }
                          mandatory true ;
                        }
                      }
                    }
                  }
                }
                container ipv4-mixed-acls {
                  description 'Select IPv4 mixed ACL name as match criteria'
                              ;
                  list ipv4-mixed-acl {
                    description 'Set IPv4 mixed ACL name as match criteria'
                                ;
                    key acl-name ;
                    leaf acl-name {
                      description 'Set ipv4-mixed-access-list name, support 1-3'
                                + '1 characters'
                                  ;
                      type string {
                        length 1..31 {
                          description 'Name of ACL, support 1-31 characters'
                                      ;
                        }
                      }
                    }
                  }
                }
                container ipv6-mixed-acls {
                  description 'Select IPv6 mixed ACL name as match criteria'
                              ;
                  list ipv6-mixed-acl {
                    description 'Set IPv6 mixed ACL name as match criteria'
                                ;
                    key acl-name ;
                    leaf acl-name {
                      description 'Set ipv6-mixed-access-list name, support 1-3'
                                + '1 characters'
                                  ;
                      type string {
                        length 1..31 {
                          description 'Name of ACL, support 1-31 characters'
                                      ;
                        }
                      }
                    }
                  }
                }
                container ipv4-vxlan-acls {
                  description 'Select IPv4 vxlan ACL name as match criteria.'
                              ;
                  list ipv4-vxlan-acl {
                    description 'Set IPv4 vxlan ACL name as match criteria.'
                                ;
                    key acl-name ;
                    leaf acl-name {
                      description 'Set ipv4-vxlan-access-list name, support 1-3'
                                + '1 characters.'
                                  ;
                      type string {
                        length 1..31 {
                          description 'Name of ACL, support 1-31 characters.'
                                      ;
                        }
                      }
                    }
                  }
                }
                container ipv6-vxlan-acls {
                  description 'Select IPv6 vxlan ACL name as match criteria.'
                              ;
                  list ipv6-vxlan-acl {
                    description 'Set IPv6 vxlan ACL name as match criteria.'
                                ;
                    key acl-name ;
                    leaf acl-name {
                      description 'Set ipv6-vxlan-access-list name, support 1-3'
                                + '1 characters.'
                                  ;
                      type string {
                        length 1..31 {
                          description 'Name of ACL, support 1-31 characters.'
                                      ;
                        }
                      }
                    }
                  }
                }
              }
              container cmap-description {
                description 'Description of a class map, support 1-79 character'
                          + 's.'
                            ;
                presence 'Specify description of class map'
                         ;
                leaf cmap-description {
                  description 'Description of a class map, support 1-79 charact'
                            + 'ers.'
                              ;
                  type ncd:string-with-blank {
                    length 1..79 {
                      description 'Description of a class map, support 1-79 cha'
                                + 'racters.'
                                  ;
                    }
                  }
                  mandatory true ;
                }
              }
            }
          }
          ncd:revise-date 2021-01-25 ;
        }
        container cps-based {
          description 'Class map based on control-plane-security'
                      ;
          container class-maps {
            description 'Configure H-QoS class map lists'
                        ;
            list class-map {
              description 'Configure H-QoS class map list'
                          ;
              key cmap-name ;
              leaf cmap-name {
                description 'Name of the class map, support 1-31 characters'
                            ;
                type string {
                  length 1..31 {
                    description 'Name of the class map, support 1-31 characters'
                                ;
                  }
                }
              }
              leaf match-relation {
                description 'The type of packets matching, see bellow:         '
                          + '       '+"\n"
                          + '  match-all Packets meet all of the match criteria'
                          + ''+"\n"
                          + '  match-any Packets meet any of the match criteria'
                            ;
                type enumeration {
                  enum match-all {
                    value 1 ;
                    description 'Packets meet all of the match criteria'
                                ;
                  }
                  enum match-any {
                    value 2 ;
                    description 'Packets meet any of the match criteria'
                                ;
                  }
                }
                mandatory true ;
              }
              container match {
                description 'Configure match criteria for a class map'
                            ;
                container in-vlan {
                  description 'Select inner-VLAN as match criteria'
                              ;
                  presence 'Select inner-VLAN as match criteria'
                           ;
                  leaf vlan-value {
                    description 'Configure inner-VLAN value in range mode, supp'
                              + 'ort single inner-VLAN value or range(max num:4'
                              + ';spacing mark:,) in <1-4094>. For example,"1,3'
                              + '00-400,1000,2000-4000",etc.'
                                ;
                    type qos-vlan-bitmap ;
                    mandatory true ;
                  }
                }
                container out-vlan {
                  description 'Select outer-VLAN as match criteria'
                              ;
                  presence 'Select outer-VLAN as match criteria'
                           ;
                  leaf vlan-value {
                    description 'Configure outer-VLAN value in range mode, supp'
                              + 'ort single outer-VLAN value or range(max num:4'
                              + ';spacing mark:,) in <1-4094>. For example,"1,3'
                              + '00-400,1000,2000-4000",etc.'
                                ;
                    type qos-vlan-bitmap ;
                    mandatory true ;
                  }
                }
                container ipv4-acls {
                  description 'Select IPv4 ACL name as match criteria'
                              ;
                  list ipv4-acl {
                    description 'Set IPv4 ACL name as match criteria'
                                ;
                    key acl-name ;
                    leaf acl-name {
                      description 'Set ipv4-access-list name, support 1-31 char'
                                + 'acters'
                                  ;
                      type string {
                        length 1..31 {
                          description 'Name of ACL, support 1-31 characters'
                                      ;
                        }
                      }
                    }
                  }
                }
                container ipv6-acls {
                  description 'Select IPv6 ACL name as match criteria'
                              ;
                  list ipv6-acl {
                    description 'Set IPv6 ACL name as match criteria'
                                ;
                    key acl-name ;
                    leaf acl-name {
                      description 'Set ipv6-access-list name, support 1-31 char'
                                + 'acters'
                                  ;
                      type string {
                        length 1..31 {
                          description 'Name of ACL, support 1-31 characters'
                                      ;
                        }
                      }
                    }
                  }
                }
                container link-acls {
                  description 'Select link ACL name as match criteria'
                              ;
                  list link-acl {
                    description 'Set link ACL name as match criteria'
                                ;
                    key acl-name ;
                    leaf acl-name {
                      description 'Set link-access-list name, support 1-31 char'
                                + 'acters'
                                  ;
                      type string {
                        length 1..31 {
                          description 'Name of ACL, support 1-31 characters'
                                      ;
                        }
                      }
                    }
                  }
                }
                container flowtypes {
                  description 'Select flowtype name as match criteria'
                              ;
                  list flowtype {
                    description 'Set flowtype name as match criteria'
                                ;
                    key flowtype-name ;
                    leaf flowtype-name {
                      description 'Set flowtype-name'
                                  ;
                      type cps:flowtype-name-ex ;
                    }
                  }
                }
              }
              container cmap-description {
                description 'Description of a class map, support 1-79 character'
                          + 's.'
                            ;
                presence 'Specify description of class map'
                         ;
                leaf cmap-description {
                  description 'Description of a class map, support 1-79 charact'
                            + 'ers.'
                              ;
                  type ncd:string-with-blank {
                    length 1..79 {
                      description 'Description of a class map, support 1-79 cha'
                                + 'racters.'
                                  ;
                    }
                  }
                  mandatory true ;
                }
              }
            }
          }
          ncd:revise-date 2021-04-18 ;
        }
      }
      container policy-map {
        description 'Configure H-QoS policy map'
                    ;
        container normal {
          if-feature normal-mode ;
          description 'Policy map based on normal'
                      ;
          container policy-maps {
            description 'Configure H-QoS policy map lists'
                        ;
            list policy-map {
              description 'Configure H-QoS policy maps'
                          ;
              key pmap-name ;
              leaf pmap-name {
                description 'Name of the policy map, support 1-31 characters'
                            ;
                type string {
                  length 1..31 {
                    description 'Name of the policy map, support 1-31 characters'
                                ;
                  }
                }
              }
              container class-maps {
                description 'Configure H-QoS policy class'
                            ;
                list class-map {
                  description 'Configure H-QoS policy class'
                              ;
                  key cmap-name ;
                  leaf cmap-name {
                    description 'Name of the class map, support 1-31 characters'
                                ;
                    type string {
                      length 1..31 {
                        description 'Name of the class map, support 1-31 charac'
                                  + 'ters'
                                    ;
                      }
                    }
                  }
                  container bandwidth {
                    description 'Configure minimum guaranteed bandwidth'
                                ;
                    presence 'Configure minimum guaranteed bandwidth'
                             ;
                    leaf percentage {
                      description 'Set the exact bandwidth percentage, support '
                                + '<1-100>'
                                  ;
                      type uint16 {
                        range 1..100 {
                          description 'The exact bandwidth percentage, support '
                                    + '<1-100>'
                                      ;
                        }
                      }
                      mandatory true ;
                    }
                  }
                  container bandwidth-remaining {
                    description 'Configure leftover bandwidth'
                                ;
                    presence 'Configure leftover bandwidth'
                             ;
                    leaf percentage {
                      description 'Set the guaranteed percentage, support <1-10'
                                + '0>'
                                  ;
                      type uint16 {
                        range 1..100 {
                          description 'The guaranteed percentage, support <1-10'
                                    + '0>'
                                      ;
                        }
                      }
                      mandatory true ;
                    }
                  }
                  container priority-level {
                    description 'Configure PQ(Priority Queuing) priority level'
                                ;
                    presence 'Configure PQ priority level'
                             ;
                    leaf priority-value {
                      description 'Set the priority level of PQ, support <1-4>'
                                  ;
                      type uint16 {
                        range 1..4 {
                          description 'The priority level of PQ, support <1-4>'
                                      ;
                        }
                      }
                      mandatory true ;
                    }
                  }
                  container priority-llq {
                    description 'Configure LLQ(Low Latency Queuing) priority'
                                ;
                    presence 'Configure LLQ priority'
                             ;
                    leaf priority-llq {
                      description 'Specify LLQ'
                                  ;
                      type empty ;
                      mandatory true ;
                    }
                  }
                  container queue-limit {
                    description 'Configure queue depth'
                                ;
                    presence 'Configure queue depth'
                             ;
                    choice queue-limit {
                      description 'Configure queue depth'
                                  ;
                      case queue-depth {
                        description 'Set queue depth'
                                    ;
                        leaf queue-depth {
                          description 'Set queue depth, such as 7KB, 16KB, 24KB'
                                    + ', 64KB, 512KB, 2000KB, 8000KB,1000KB,800'
                                    + '0000KB,1000000KB,128000KB,16000KB,24000K'
                                    + 'B,512000KB,64000KB'
                                      ;
                          type enumeration {
                            enum 16 {
                              value 1 ;
                              description 'Set queue depth to 16KB'
                                          ;
                            }
                            enum 24 {
                              value 2 ;
                              description 'Set queue depth to 24KB'
                                          ;
                            }
                            enum 64 {
                              value 3 ;
                              description 'Set queue depth to 64KB'
                                          ;
                            }
                            enum 512 {
                              value 4 ;
                              description 'Set queue depth to 512KB'
                                          ;
                            }
                            enum 2000 {
                              value 5 ;
                              description 'Set queue depth to 2000KB'
                                          ;
                            }
                            enum 8000 {
                              value 6 ;
                              description 'Set queue depth to 8000KB'
                                          ;
                            }
                            enum 7 {
                              value 7 ;
                              description 'Set queue depth to 7KB'
                                          ;
                            }
                            enum 1000 {
                              value 20 ;
                              description 'Set queue depth to 1000KB'
                                          ;
                            }
                            enum 8000000 {
                              value 21 ;
                              description 'Set queue depth to 8000000KB'
                                          ;
                            }
                            enum 1000000 {
                              value 13 ;
                              description 'Set queue depth to 1000000KB'
                                          ;
                            }
                            enum 128000 {
                              value 11 ;
                              description 'Set queue depth to 128000KB'
                                          ;
                            }
                            enum 16000 {
                              value 8 ;
                              description 'Set queue depth to 16000KB'
                                          ;
                            }
                            enum 24000 {
                              value 9 ;
                              description 'Set queue depth to 24000KB'
                                          ;
                            }
                            enum 512000 {
                              value 12 ;
                              description 'Set queue depth to 512000KB'
                                          ;
                            }
                            enum 64000 {
                              value 10 ;
                              description 'Set queue depth to 64000KB'
                                          ;
                            }
                          }
                          units KB ;
                          mandatory true ;
                        }
                      }
                      case queue-value {
                        description 'Set queue depth value(default:KB)'
                                    ;
                        container queue-value {
                          description 'Set queue depth value(default:KB)'
                                      ;
                          leaf queue-value {
                            description 'Set queue depth value(default:KB)'
                                        ;
                            type uint32 {
                              range 7..8000000 {
                                description 'Set queue depth value(default:KB)'
                                            ;
                              }
                            }
                            mandatory true ;
                          }
                        }
                        ncd:revise-date 2019-08-19 ;
                      }
                      case queue-cache-time {
                        description 'Configure cache time of the queue'
                                    ;
                        container queue-cache-time {
                          description 'Configure cache time of the queue'
                                      ;
                          leaf queue-cache-time {
                            description 'Set cache time(default:us)'
                                        ;
                            type uint32 {
                              range 1..100000 {
                                description 'Set cache time(default:us)'
                                            ;
                              }
                            }
                            mandatory true ;
                          }
                        }
                        ncd:revise-date 2019-08-19 ;
                      }
                    }
                  }
                  container random-detect {
                    description 'Configure WRED(Weighted Random Early Detection'
                              + ') information'
                                ;
                    container enable {
                      description 'Configure WRED enable'
                                  ;
                      presence 'Configure WRED enable'
                               ;
                      leaf enable {
                        description 'Specify WRED enable'
                                    ;
                        type empty ;
                        mandatory true ;
                      }
                    }
                    container colors {
                      if-feature policy-action-wred-color ;
                      description 'Configure WRED thresholds based on color'
                                  ;
                      list color {
                        description 'Configure WRED thresholds based on color'
                                    ;
                        key color-type ;
                        leaf color-type {
                          description 'set WRED color, such as green, yellow, r'
                                    + 'ed'
                                      ;
                          type qos-color-type ;
                        }
                        choice threshold {
                          description 'Set the threshold'
                                      ;
                          case threshold-value {
                            description 'Set the threshold value'
                                        ;
                            leaf min-threshold {
                              description 'Set the minimum threshold in kilobytes, support <1-1024000>'
                                          ;
                              type uint32 {
                                range 1..1024000 {
                                  description 'The minimum threshold in kilobytes, support <1-1024000>'
                                              ;
                                }
                              }
                              units KB ;
                              mandatory true ;
                            }
                            leaf max-threshold {
                              description 'Set the maximum threshold in kilobytes, support <1-1024000>'
                                          ;
                              type uint32 {
                                range 1..1024000 {
                                  description 'The maximum threshold in kilobytes, support <1-1024000>'
                                              ;
                                }
                              }
                              units KB ;
                              mandatory true ;
                            }
                          }
                          case threshold-percentage {
                            description 'Set the threshold percentage'
                                        ;
                            container threshold-percentage {
                              description 'Set the threshold percentage'
                                          ;
                              leaf min-threshold-percentage {
                                description 'Set the minimum threshold percentage, support <1-100>'
                                            ;
                                type uint32 {
                                  range 1..100 {
                                    description 'The minimum threshold percentage, support <1-100>'
                                                ;
                                  }
                                }
                                mandatory true ;
                              }
                              leaf max-threshold-percentage {
                                description 'Set the maximum threshold percentage, support <1-100>'
                                            ;
                                type uint32 {
                                  range 1..100 {
                                    description 'The maximum threshold percentage, support <1-100>'
                                                ;
                                  }
                                }
                                mandatory true ;
                              }
                            }
                          }
                          ncd:revise-date 2019-08-05 ;
                        }
                        leaf probability {
                          description 'Set mark probability denominator, suppor'
                                    + 't <1-100>'
                                      ;
                          type uint8 {
                            range 1..100 {
                              description 'Set mark probability denominator, support <1-100>'
                                          ;
                            }
                          }
                          mandatory true ;
                        }
                      }
                    }
                    container precedences {
                      description 'Configure WRED thresholds based on precedence'
                                  ;
                      list precedence {
                        description 'Configure WRED thresholds based on precede'
                                  + 'nce'
                                    ;
                        key prec-value ;
                        leaf prec-value {
                          description 'Set the precedence value, such as MPLS E'
                                    + 'XP, VLAN 802.1p, IP DSCP, IP Precedence,'
                                    + ' support <0-7>'
                                      ;
                          type uint16 {
                            range 0..7 {
                              description 'The IP-Precedence value, support <0-7>'
                                          ;
                            }
                          }
                        }
                        choice threshold {
                          description 'Set the threshold'
                                      ;
                          case threshold-value {
                            description 'Set the threshold value'
                                        ;
                            leaf min-threshold {
                              description 'Set the minimum threshold (default: kilobytes)'
                                          ;
                              type uint32 {
                                range 1..4294967295 {
                                  description 'The minimum threshold (default: kilobytes), support <1-4294967295>'
                                              ;
                                }
                              }
                              mandatory true ;
                            }
                            leaf min-threshold-unit {
                              description 'set min-threshold unit, such as kbytes, mbytes, gbytes'
                                          ;
                              type qos-threshold-unit-type ;
                            }
                            leaf max-threshold {
                              description 'Set the maximum threshold (default: kilobytes)'
                                          ;
                              type uint32 {
                                range 1..4294967295 {
                                  description 'The maximum threshold (default: kilobytes), support <1-4294967295>.'
                                              ;
                                }
                              }
                              mandatory true ;
                            }
                            leaf max-threshold-unit {
                              description 'set max-threshold unit, such as kbytes, mbytes, gbytes'
                                          ;
                              type qos-threshold-unit-type ;
                            }
                          }
                          case threshold-percentage {
                            description 'Set the threshold percentage'
                                        ;
                            container threshold-percentage {
                              description 'Set the threshold percentage'
                                          ;
                              leaf min-threshold-percentage {
                                description 'Set the minimum threshold percentage, support <1-100>'
                                            ;
                                type uint32 {
                                  range 1..100 {
                                    description 'The minimum threshold percentage, support <1-100>'
                                                ;
                                  }
                                }
                                mandatory true ;
                              }
                              leaf max-threshold-percentage {
                                description 'Set the maximum threshold percentage, support <1-100>'
                                            ;
                                type uint32 {
                                  range 1..100 {
                                    description 'The maximum threshold percentage, support <1-100>'
                                                ;
                                  }
                                }
                                mandatory true ;
                              }
                            }
                          }
                          ncd:revise-date 2019-08-05 ;
                        }
                        leaf probability {
                          description 'Set mark probability denominator, suppor'
                                    + 't <1-100>'
                                      ;
                          type uint32 {
                            range 1..100 {
                              description 'Set mark probability denominator, support <1-100>'
                                          ;
                            }
                          }
                          mandatory true ;
                        }
                      }
                    }
                    container weight {
                      description 'Configure WRED exponential weight factor'
                                  ;
                      presence 'Configure WRED exponential weight factor'
                               ;
                      leaf weight-value {
                        description 'Specify exponent used in weighted average '
                                  + 'calculation, support <1-16>'
                                    ;
                        type uint16 {
                          range 1..16 {
                            description 'Exponent used in weighted average calculation'
                                        ;
                          }
                        }
                        mandatory true ;
                      }
                    }
                  }
                  container service-policy {
                    description 'Configure hierarchical service policy'
                                ;
                    presence 'Configure hierarchical service policy'
                             ;
                    leaf hpolicy-name {
                      description 'Name of the hierarchical policy, support 1-3'
                                + '1 characters'
                                  ;
                      type string {
                        length 1..31 {
                          description 'Name of the hierarchical policy, support'
                                    + ' 1-31 characters'
                                      ;
                        }
                      }
                      mandatory true ;
                    }
                  }
                  container shape {
                    if-feature policy-action-shape ;
                    description 'Configure flow shape'
                                ;
                    presence 'Configure flow shape'
                             ;
                    leaf shape-type {
                      description 'Set shape type, such as peak, average'
                                  ;
                      type enumeration {
                        enum average {
                          value 1 ;
                          description 'Set average as shape type'
                                      ;
                        }
                        enum peak {
                          value 2 ;
                          description 'Set peak as shape type'
                                      ;
                        }
                      }
                      mandatory true ;
                    }
                    choice shape-method {
                      description 'Select rate or rate percentage as shape unit'
                                  ;
                      mandatory true ;
                      case rate {
                        description 'Select the average or peak rate'
                                    ;
                        leaf rate-value {
                          description 'Set the average or peak rate in kilobits'
                                    + ' per second, support <1-4294967295>'
                                      ;
                          type uint32 {
                            range 1..4294967295 {
                              description 'The average or peak rate in kbps, support <1-4294967295>'
                                          ;
                            }
                          }
                          units kbps ;
                          mandatory true ;
                        }
                      }
                      case percent {
                        description 'Select rate percent as shape unit'
                                    ;
                        leaf percentage {
                          description 'Set the exact rate percentage, support <'
                                    + '1-100>'
                                      ;
                          type uint16 {
                            range 1..100 {
                              description 'The exact rate percentage, support <1-100>'
                                          ;
                            }
                          }
                          mandatory true ;
                        }
                      }
                    }
                    container burst-rate {
                      description 'Configure burst and peak rate'
                                  ;
                      presence 'Configure committed burst and peak rate'
                               ;
                      leaf bc-value {
                        description 'Set the bc value in kilobits per second, s'
                                  + 'upport <1-4294967295>'
                                    ;
                        type uint32 {
                          range 1..4294967295 {
                            description 'The committed burst information rate in kilobits per second, support <1-429496'
                                      + '7295>'
                                        ;
                          }
                        }
                        units kbps ;
                        mandatory true ;
                      }
                      leaf be-value {
                        description 'Set the be value in kilobits per second, s'
                                  + 'upport <1-4294967295>'
                                    ;
                        type uint32 {
                          range 1..4294967295 {
                            description 'The peak information rate in kilobits per second, support <1-4294967295>'
                                        ;
                          }
                        }
                        units kbps ;
                        mandatory true ;
                      }
                    }
                  }
                  container police {
                    description 'Configure traffic policing'
                                ;
                    presence 'Configure traffic policing'
                             ;
                    choice cir-pir-value-percentage {
                      description 'Configure CIR CBS PIR and PBS'
                                  ;
                      mandatory true ;
                      case cir-pir-value {
                        description 'Configure CIR and PIR with value form'
                                    ;
                        leaf cir {
                          description 'Configure the CIR(Committed Information '
                                    + 'Rate) value (default: kilobits per secon'
                                    + 'd)'
                                      ;
                          type uint32 {
                            range 8..4294967295 {
                              description 'The CIR value (default: kilobits per second),support <8-4294967295>.'
                                          ;
                            }
                          }
                          mandatory true ;
                        }
                        leaf cir-unit {
                          description 'set cir unit, such as kbps, mbps, gbps'
                                      ;
                          type qos-rate-unit-type ;
                        }
                        leaf cbs {
                          description 'Configure the CBS(Committed Burst Size) '
                                    + 'size (default: KB)'
                                      ;
                          type uint32 {
                            range 1..4294967295 {
                              description 'The CBS(Committed Burst Size) size (default: KB), support <1-4294967295>'
                                          ;
                            }
                          }
                        }
                        leaf cbs-unit {
                          description 'set cbs unit, such as kb, mb, gb'
                                      ;
                          type qos-bucket-unit-type ;
                        }
                        container pir-pbs {
                          description 'Configure PIR and PBS'
                                      ;
                          presence 'Configure pir and pbs'
                                   ;
                          leaf pir {
                            description 'Configure the PIR(Peak Information Rate) value (default: kilobits per second)'
                                        ;
                            type uint32 {
                              range 8..4294967295 {
                                description 'The PIR(Peak Information Rate) value (default: kilobits per second), suppo'
                                          + 'rt <8-4294967295>'
                                            ;
                              }
                            }
                            mandatory true ;
                          }
                          leaf pir-unit {
                            description 'set pir unit, such as kbps, mbps, gbps'
                                        ;
                            type qos-rate-unit-type ;
                          }
                          leaf pbs {
                            description 'Configure the PBS(Peak Burst Size) size (default: KB)'
                                        ;
                            type uint32 {
                              range 1..4294967295 {
                                description 'The PBS(Peak Burst Size) size (default: KB), support <1-4294967295>'
                                            ;
                              }
                            }
                          }
                          leaf pbs-unit {
                            description 'set pbs unit, such as kb, mb, gb'
                                        ;
                            type qos-bucket-unit-type ;
                          }
                        }
                      }
                      case cir-pir-percentage {
                        description 'Configure CIR and PIR with percentage form'
                                    ;
                        container cir-pir-percentage {
                          description 'Configure CIR and PIR with percentage fo'
                                    + 'rm'
                                      ;
                          leaf cir-percentage {
                            description 'Configure CIR with percentage form'
                                        ;
                            type uint8 {
                              range 1..100 {
                                description 'Configure CIR with percentage form'
                                            ;
                              }
                            }
                            mandatory true ;
                          }
                          container pir-percentage {
                            description 'Configure PIR with percentage form'
                                        ;
                            presence 'Configure PIR with percentage form'
                                     ;
                            leaf pir-percentage {
                              description 'Configure PIR with percentage form'
                                          ;
                              type uint8 {
                                range 1..100 {
                                  description 'Configure PIR with percentage form'
                                              ;
                                }
                              }
                              mandatory true ;
                            }
                          }
                        }
                        ncd:revise-date 2020-06-09 ;
                      }
                    }
                    container action {
                      description 'Configure action to packets'
                                  ;
                      presence 'Configure action to packets'
                               ;
                      container conform-action {
                        description 'Action to packets that conform to the rate'
                                  + ' limit'
                                    ;
                        choice conform-action {
                          description 'Specify action to packets that conform t'
                                    + 'o the rate limit'
                                      ;
                          mandatory true ;
                          case ca-drop {
                            description 'Drop packet in conform-action'
                                        ;
                            leaf drop {
                              description 'Specify action to drop packet'
                                          ;
                              type empty ;
                              mandatory true ;
                            }
                          }
                          case ca-transmit {
                            description 'Transmit packet in conform-action'
                                        ;
                            leaf transmit {
                              description 'Specify action to transmit packet'
                                          ;
                              type empty ;
                              mandatory true ;
                            }
                          }
                          case ca-mpls-exp {
                            description 'Rewrite packet MPLS-EXP and transmit the packet'
                                        ;
                            leaf set-exp-transmit {
                              description 'Specify action to rewrite packet MPLS-EXP and transmit it'
                                          ;
                              type empty ;
                              mandatory true ;
                            }
                            leaf mpls-exp-value {
                              description 'Reset MPLS-EXP value in conform-action, support <0-7>'
                                          ;
                              type uint8 {
                                range 0..7 {
                                  description 'The MPLS-EXP value, support <0-7>'
                                              ;
                                }
                              }
                              mandatory true ;
                            }
                          }
                          case ca-precedence {
                            description 'Rewrite packet precedence and transmit the packet'
                                        ;
                            leaf set-prec-transmit {
                              description 'Specify action to rewrite packet precedence and transmit it'
                                          ;
                              type empty ;
                              mandatory true ;
                            }
                            leaf prec-value {
                              description 'Reset the IP-Precedence value in conform-action, support <0-7>'
                                          ;
                              type uint8 {
                                range 0..7 {
                                  description 'The IP-Precedence value, support <0-7>'
                                              ;
                                }
                              }
                              mandatory true ;
                            }
                          }
                          case ca-dscp {
                            description 'Rewrite packet DSCP and transmit the packet'
                                        ;
                            leaf set-dscp-transmit {
                              description 'Specify action to rewrite packet DSCP and transmit it'
                                          ;
                              type empty ;
                              mandatory true ;
                            }
                            leaf dscp-value {
                              description 'Reset DSCP in conform-action, support <0-63>'
                                          ;
                              type uint8 {
                                range 0..63 {
                                  description 'The DSCP value, support <0-63>'
                                              ;
                                }
                              }
                              mandatory true ;
                            }
                          }
                          case ca-8021p {
                            description 'Rewrite packet 802.1p and transmit the packet'
                                        ;
                            leaf set-8021p-transmit {
                              description 'Specify action to rewrite packet 802.1p and transmit it'
                                          ;
                              type empty ;
                              mandatory true ;
                            }
                            leaf value-8021p {
                              description 'Reset 802.1p in conform-action, support <0-7>'
                                          ;
                              type uint8 {
                                range 0..7 {
                                  description 'The 802.1p value, support <0-7>'
                                              ;
                                }
                              }
                              mandatory true ;
                            }
                          }
                          case ca-priority {
                            description 'Rewrite packet priority and transmit the packet'
                                        ;
                            leaf set-priority-transmit {
                              description 'Specify action to rewrite packet priority and transmit it'
                                          ;
                              type empty ;
                              mandatory true ;
                            }
                            leaf priority-value {
                              description 'Reset priority in conform-action, support <1-4>'
                                          ;
                              type uint8 {
                                range 1..4 {
                                  description 'The priority value, support <1-4>'
                                              ;
                                }
                              }
                              mandatory true ;
                            }
                          }
                        }
                      }
                      container exceed-action {
                        description 'Action to packets that exceed the rate lim'
                                  + 'it'
                                    ;
                        choice exceed-action {
                          description 'Specify action to packets that exceed th'
                                    + 'e rate limit'
                                      ;
                          mandatory true ;
                          case ea-drop {
                            description 'Drop packet in exceed-action'
                                        ;
                            leaf drop {
                              description 'Specify action to drop packet'
                                          ;
                              type empty ;
                              mandatory true ;
                            }
                          }
                          case ea-transmit {
                            description 'Transmit packet in exceed-action'
                                        ;
                            leaf transmit {
                              description 'Specify action to transmit packet'
                                          ;
                              type empty ;
                              mandatory true ;
                            }
                          }
                          case ea-mpls-exp {
                            description 'Rewrite packet MPLS-EXP and transmit the packet'
                                        ;
                            leaf set-exp-transmit {
                              description 'Specify action to rewrite packet MPLS-EXP and transmit it'
                                          ;
                              type empty ;
                              mandatory true ;
                            }
                            leaf mpls-exp-value {
                              description 'Reset MPLS-EXP value in exceed-action, support <0-7>'
                                          ;
                              type uint8 {
                                range 0..7 {
                                  description 'The MPLS-EXP value, support <0-7>'
                                              ;
                                }
                              }
                              mandatory true ;
                            }
                          }
                          case ea-precedence {
                            description 'Rewrite packet precedence and transmit the packet'
                                        ;
                            leaf set-prec-transmit {
                              description 'Specify action to rewrite packet precedence and transmit it'
                                          ;
                              type empty ;
                              mandatory true ;
                            }
                            leaf prec-value {
                              description 'Reset the IP-Precedence value in exceed-action, support <0-7>'
                                          ;
                              type uint8 {
                                range 0..7 {
                                  description 'The IP-Precedence value, support <0-7>'
                                              ;
                                }
                              }
                              mandatory true ;
                            }
                          }
                          case ea-dscp {
                            description 'Rewrite packet DSCP and transmit the packet'
                                        ;
                            leaf set-dscp-transmit {
                              description 'Specify action to rewrite packet DSCP and transmit it'
                                          ;
                              type empty ;
                              mandatory true ;
                            }
                            leaf dscp-value {
                              description 'Reset DSCP in exceed-action, support <0-63>'
                                          ;
                              type uint8 {
                                range 0..63 {
                                  description 'The DSCP value, support <0-63>'
                                              ;
                                }
                              }
                              mandatory true ;
                            }
                          }
                          case ea-8021p {
                            description 'Rewrite packet 802.1p and transmit the packet'
                                        ;
                            leaf set-8021p-transmit {
                              description 'Specify action to rewrite packet 802.1p and transmit it'
                                          ;
                              type empty ;
                              mandatory true ;
                            }
                            leaf value-8021p {
                              description 'Reset 802.1p in exceed-action, support <0-7>'
                                          ;
                              type uint8 {
                                range 0..7 {
                                  description 'The 802.1p value, support <0-7>'
                                              ;
                                }
                              }
                              mandatory true ;
                            }
                          }
                          case ea-priority {
                            description 'Rewrite packet priority and transmit the packet'
                                        ;
                            leaf set-priority-transmit {
                              description 'Specify action to rewrite packet priority and transmit it'
                                          ;
                              type empty ;
                              mandatory true ;
                            }
                            leaf priority-value {
                              description 'Reset priority in exceed-action, support <1-4>'
                                          ;
                              type uint8 {
                                range 1..4 {
                                  description 'The priority value, support <1-4>'
                                              ;
                                }
                              }
                              mandatory true ;
                            }
                          }
                        }
                      }
                      container violate-action {
                        description 'Action to packets that violate the rate li'
                                  + 'mit'
                                    ;
                        choice violate-action {
                          description 'Specify action to packets that violate t'
                                    + 'he rate limit'
                                      ;
                          mandatory true ;
                          case va-drop {
                            description 'Drop packet in violate-action'
                                        ;
                            leaf drop {
                              description 'Specify action to drop packet'
                                          ;
                              type empty ;
                              mandatory true ;
                            }
                          }
                          case va-transmit {
                            description 'Transmit packet in violate-action'
                                        ;
                            leaf transmit {
                              description 'Specify action to transmit packet'
                                          ;
                              type empty ;
                              mandatory true ;
                            }
                          }
                          case va-mpls-exp {
                            description 'Rewrite packet MPLS-EXP and transmit the packet'
                                        ;
                            leaf set-exp-transmit {
                              description 'Specify action to rewrite packet MPLS-EXP and transmit it'
                                          ;
                              type empty ;
                              mandatory true ;
                            }
                            leaf mpls-exp-value {
                              description 'Reset MPLS-EXP value in violate-action, support <0-7>'
                                          ;
                              type uint8 {
                                range 0..7 {
                                  description 'The MPLS-EXP value, support <0-7>'
                                              ;
                                }
                              }
                              mandatory true ;
                            }
                          }
                          case va-precedence {
                            description 'Rewrite packet precedence and transmit the packet'
                                        ;
                            leaf set-prec-transmit {
                              description 'Specify action to rewrite packet precedence and transmit it'
                                          ;
                              type empty ;
                              mandatory true ;
                            }
                            leaf prec-value {
                              description 'Reset the IP-Precedence value in violate-action, support <0-7>'
                                          ;
                              type uint8 {
                                range 0..7 {
                                  description 'The IP-Precedence value, support <0-7>'
                                              ;
                                }
                              }
                              mandatory true ;
                            }
                          }
                          case va-dscp {
                            description 'Rewrite packet DSCP and transmit the packet'
                                        ;
                            leaf set-dscp-transmit {
                              description 'Specify action to rewrite packet DSCP and transmit it'
                                          ;
                              type empty ;
                              mandatory true ;
                            }
                            leaf dscp-value {
                              description 'Reset DSCP in violate-action, support <0-63>'
                                          ;
                              type uint8 {
                                range 0..63 {
                                  description 'The DSCP value, support <0-63>'
                                              ;
                                }
                              }
                              mandatory true ;
                            }
                          }
                          case va-8021p {
                            description 'Rewrite packet 802.1p and transmit the packet'
                                        ;
                            leaf set-8021p-transmit {
                              description 'Specify action to rewrite packet 802.1p and transmit it'
                                          ;
                              type empty ;
                              mandatory true ;
                            }
                            leaf value-8021p {
                              description 'Reset 802.1p in violate-action, support <0-7>'
                                          ;
                              type uint8 {
                                range 0..7 {
                                  description 'The 802.1p value, support <0-7>'
                                              ;
                                }
                              }
                              mandatory true ;
                            }
                          }
                          case va-priority {
                            description 'Rewrite packet priority and transmit the packet'
                                        ;
                            leaf set-priority-transmit {
                              description 'Specify action to rewrite packet priority and transmit it'
                                          ;
                              type empty ;
                              mandatory true ;
                            }
                            leaf priority-value {
                              description 'Reset priority in violate-action, support <1-4>'
                                          ;
                              type uint8 {
                                range 1..4 {
                                  description 'The priority value, support <1-4>'
                                              ;
                                }
                              }
                              mandatory true ;
                            }
                          }
                        }
                      }
                    }
                  }
                  container set {
                    description 'Mark a packet'
                                ;
                    container dscp {
                      description 'Select DSCP as mark type'
                                  ;
                      presence 'Select DSCP as mark typ'
                               ;
                      choice method {
                        description 'Specify the method to set DSCP'
                                    ;
                        mandatory true ;
                        case set-value {
                          description 'Set the DSCP value directly'
                                      ;
                          container set-value {
                            description 'Set the DSCP value directly'
                                        ;
                            leaf dscp-value {
                              description 'DSCP value, support <0-63>'
                                          ;
                              type uint16 {
                                range 0..63 {
                                  description 'DSCP value, support <0-63>'
                                              ;
                                }
                              }
                              mandatory true ;
                            }
                          }
                        }
                        case inherit {
                          description 'Set the DSCP value by inheriting'
                                      ;
                          container inherit {
                            description 'Set the DSCP value by inheriting'
                                        ;
                            leaf inherit-type {
                              description 'Specify the source inherit type, such as precedence, mpls-exp, 8021p, dscp, '
                                        + 'pay-load 8021p'
                                          ;
                              type enumeration {
                                enum precedence {
                                  value 1 ;
                                  description 'Select precedence as source inherit'
                                              ;
                                }
                                enum mpls-exp {
                                  value 2 ;
                                  description 'Select MPLS-EXP as source inherit'
                                              ;
                                }
                                enum 8021p {
                                  value 3 ;
                                  description 'Select 802.1p as source inherit'
                                              ;
                                }
                                enum dscp {
                                  value 4 ;
                                  description 'Select dscp as source inherit'
                                              ;
                                }
                                enum pay-load-8021p {
                                  value 6 ;
                                  description 'Select inner 802.1p as source inherit'
                                              ;
                                }
                              }
                              mandatory true ;
                            }
                          }
                        }
                      }
                    }
                    container precedence {
                      description 'Select precedence as mark type'
                                  ;
                      presence 'Select precedence as mark type'
                               ;
                      choice method {
                        description 'Specify the method to set IP Precedence'
                                    ;
                        mandatory true ;
                        case set-value {
                          description 'Set the IP Precedence value directly'
                                      ;
                          container set-value {
                            description 'Set the IP Precedence value directly'
                                        ;
                            leaf prec-value {
                              description 'IP Precedence value, support <0-7>'
                                          ;
                              type uint16 {
                                range 0..7 {
                                  description 'IP Precedence value, support <0-7>'
                                              ;
                                }
                              }
                              mandatory true ;
                            }
                          }
                        }
                        case inherit {
                          description 'Set the IP Precedence value by inheriting'
                                      ;
                          container inherit {
                            description 'Set the IP Precedence value by inheriting'
                                        ;
                            leaf inherit-type {
                              description 'Specify the source inherit type, such as precedence, mpls-exp, 8021p, dscp'
                                          ;
                              type enumeration {
                                enum precedence {
                                  value 1 ;
                                  description 'Select precedence as source inherit'
                                              ;
                                }
                                enum mpls-exp {
                                  value 2 ;
                                  description 'Select MPLS-EXP as source inherit'
                                              ;
                                }
                                enum 8021p {
                                  value 3 ;
                                  description 'Select 802.1p as source inherit'
                                              ;
                                }
                                enum dscp {
                                  value 4 ;
                                  description 'Select dscp as source inherit'
                                              ;
                                }
                              }
                              mandatory true ;
                            }
                          }
                        }
                      }
                    }
                    container pri-8021p {
                      description 'Select 802.1p as mark type'
                                  ;
                      presence 'Select 802.1p as mark type'
                               ;
                      choice method {
                        description 'Specify the method to set 802.1p'
                                    ;
                        mandatory true ;
                        case set-value {
                          description 'Set the 802.1p value directly'
                                      ;
                          container set-value {
                            description 'Set the 802.1p value directly'
                                        ;
                            leaf value-8021p {
                              description '802.1p value, support <0-7>'
                                          ;
                              type uint16 {
                                range 0..7 {
                                  description '802.1p value, support <0-7>'
                                              ;
                                }
                              }
                              mandatory true ;
                            }
                            leaf inner-outer {
                              description 'Set 8021p inner or outer flag.If vlaue is 0, it means outer flag. If value i'
                                        + 's 1,it means inner and outer flag.'
                                          ;
                              type uint8 {
                                range 0..1 {
                                  description 'Inner or outer flag. 0 is outer. 1 is inner and outer'
                                              ;
                                }
                              }
                              default 0 ;
                              ncd:revise-date 2017-01-10 ;
                            }
                          }
                        }
                        case inherit {
                          description 'Set the 802.1p value by inheriting'
                                      ;
                          container inherit {
                            description 'Set the 802.1p value by inheriting'
                                        ;
                            leaf inherit-type {
                              description 'Specify the source inherit type, such as precedence, mpls-exp, 8021p, dscp'
                                          ;
                              type enumeration {
                                enum precedence {
                                  value 1 ;
                                  description 'Select precedence as source inherit'
                                              ;
                                }
                                enum mpls-exp {
                                  value 2 ;
                                  description 'Select MPLS-EXP as source inherit'
                                              ;
                                }
                                enum 8021p {
                                  value 3 ;
                                  description 'Select 802.1p as source inherit'
                                              ;
                                }
                                enum dscp {
                                  value 4 ;
                                  description 'Select dscp as source inherit'
                                              ;
                                }
                              }
                              mandatory true ;
                            }
                            leaf inner-outer {
                              description 'Set 8021p inner or outer flag.If vlaue is 0, it means outer flag. If value i'
                                        + 's 1,it means inner and outer flag.'
                                          ;
                              type uint8 {
                                range 0..1 {
                                  description 'Inner or outer flag. 0 is outer. 1 is inner and outer'
                                              ;
                                }
                              }
                              default 0 ;
                              ncd:revise-date 2017-01-10 ;
                            }
                          }
                        }
                      }
                    }
                    container mpls-exp {
                      description 'Select MPLS-EXP as mark type'
                                  ;
                      presence 'Select MPLS-EXP as mark type'
                               ;
                      leaf label-type {
                        if-feature policy-action-set-label ;
                        description 'Select MPLS-EXP label position, such as '+"\n"
                                  + '    default    The default for topmost lab'
                                  + 'el'+"\n"
                                  + '    topmost    Set the MPLS-EXP value on t'
                                  + 'opmost label'+"\n"
                                  + '    imposition Set the MPLS-EXP value on a'
                                  + 'll imposed labels'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on all imposed labels'
                                        ;
                          }
                          enum default {
                            value 0 ;
                            description 'The default for topmost label'
                                        ;
                          }
                          enum inner {
                            value 3 ;
                            description 'Set the MPLS-EXP value on inner label'
                                        ;
                          }
                        }
                      }
                      choice method {
                        description 'Specify the method to set MPLS-EXP'
                                    ;
                        mandatory true ;
                        case set-value {
                          description 'Set the MPLS-EXP value directly'
                                      ;
                          container set-value {
                            description 'Set the MPLS-EXP value directly'
                                        ;
                            leaf mpls-exp-value {
                              description 'MPLS-EXP value, support <0-7>'
                                          ;
                              type uint16 {
                                range 0..7 {
                                  description 'MPLS-EXP value, support <0-7>'
                                              ;
                                }
                              }
                              mandatory true ;
                            }
                          }
                        }
                        case inherit {
                          description 'Set the MPLS-EXP value by inheriting'
                                      ;
                          container inherit {
                            description 'Set the MPLS-EXP value by inheriting'
                                        ;
                            leaf inherit-type {
                              description 'Specify the source inherit type, such as precedence, mpls-exp, 8021p, dscp'
                                          ;
                              type enumeration {
                                enum precedence {
                                  value 1 ;
                                  description 'Select precedence as source inherit'
                                              ;
                                }
                                enum mpls-exp {
                                  value 2 ;
                                  description 'Select MPLS-EXP as source inherit'
                                              ;
                                }
                                enum 8021p {
                                  value 3 ;
                                  description 'Select 802.1p as source inherit'
                                              ;
                                }
                                enum dscp {
                                  value 4 ;
                                  description 'Select dscp as source inherit'
                                              ;
                                }
                              }
                              mandatory true ;
                            }
                          }
                        }
                      }
                    }
                    container multi-mpls-exp {
                      if-feature policy-action-set-multi-exp ;
                      description 'Select multi-MPLS-EXP as mark type'
                                  ;
                      presence 'Select multi-MPLS-EXP as mark type'
                               ;
                      leaf inner-value {
                        description 'Inner multi-MPLS-EXP value, support <0-7>'
                                    ;
                        type uint8 {
                          range 0..7 {
                            description 'Inner multi-MPLS-EXP value, support <0-7>'
                                        ;
                          }
                        }
                        mandatory true ;
                      }
                      leaf outer-value {
                        description 'Outer multi-MPLS-EXP value, support <0-7>'
                                    ;
                        type uint8 {
                          range 0..7 {
                            description 'Outer multi-MPLS-EXP value, support <0-7>'
                                        ;
                          }
                        }
                        mandatory true ;
                      }
                    }
                    container interface {
                      description 'Specify interface name'
                                  ;
                      presence 'Specify interface name'
                               ;
                      leaf if-name {
                        description 'Specify interface name'
                                    ;
                        type ncd:ifname {
                          length 1..31 {
                            description 'Name of the interface, support 1-31 characters'
                                        ;
                          }
                        }
                        mandatory true ;
                      }
                      ncd:revise-date 2017-02-20 ;
                    }
                    container vlan-id {
                      description 'Configure VLAN ID'
                                  ;
                      presence 'Configure VLAN ID'
                               ;
                      leaf vlan-value {
                        description 'Set VLAN ID, support <1-4094>'
                                    ;
                        type uint16 {
                          range 1..4094 ;
                        }
                        mandatory true ;
                      }
                      ncd:revise-date 2017-02-20 ;
                    }
                    container service-query {
                      description 'Configure service function path'
                                  ;
                      presence 'Configure service function path'
                               ;
                      leaf query-number {
                        description 'Service function path, support <0-255>'
                                    ;
                        type uint8 {
                          range 0..255 ;
                        }
                        mandatory true ;
                      }
                      ncd:revise-date 2017-02-20 ;
                    }
                    container service-class {
                      description 'Configure service class'
                                  ;
                      presence 'Configure service function path'
                               ;
                      leaf service-class {
                        description 'Select service class of PHB info, see belo'
                                  + 'w:'+"\n"
                                  + '  be (1) Best effort'+"\n"
                                  + '  af1(2) Assured forwarding class 1'+"\n"
                                  + '  af2(3) Assured forwarding class 2'+"\n"
                                  + '  af3(4) Assured forwarding class 3'+"\n"
                                  + '  af4(5) Assured forwarding class 4'+"\n"
                                  + '  ef (6) Expedited forward'+"\n"
                                  + '  cs6(7) Internetwork control service clas'
                                  + 's'+"\n"
                                  + '  cs7(8) Network control service class'
                                    ;
                        type qos-service-class ;
                        mandatory true ;
                      }
                      leaf color-type {
                        description 'Specify packets color, support <green,yell'
                                  + 'ow,red>'
                                    ;
                        type qos-color-type ;
                      }
                      ncd:revise-date 2021-01-18 ;
                    }
                  }
                  container drop {
                    if-feature policy-action-drop ;
                    description 'Configure drop'
                                ;
                    presence 'Configure drop'
                             ;
                    leaf drop {
                      description 'Specify drop'
                                  ;
                      type empty ;
                      mandatory true ;
                    }
                  }
                  container latency-time-threshold {
                    description 'Configure latency time threshold'
                                ;
                    presence 'Configure latency time threshold'
                             ;
                    leaf value {
                      description 'Set the threshold of latency time'
                                  ;
                      type uint32 {
                        range 1..1000 ;
                      }
                      mandatory true ;
                    }
                    ncd:revise-date 2020-04-06 ;
                  }
                  container bandwidth-threshold {
                    description 'Configure bandwidth threshold'
                                ;
                    presence 'Configure bandwidth threshold'
                             ;
                    leaf value {
                      description 'Set the threshold of bandwidth'
                                  ;
                      type uint32 {
                        range 1..10000000 ;
                      }
                      mandatory true ;
                    }
                    container percentage {
                      description 'Configure percentage of acceleration or dece'
                                + 'leration'
                                  ;
                      leaf up {
                        description 'Configure percentage of acceleration (perc'
                                  + 'entage <0.0-100.0>)'
                                    ;
                        type decimal64 {
                          fraction-digits 2 ;
                          range 0..100 ;
                        }
                      }
                      leaf down {
                        description 'Configure percentage of deceleration (perc'
                                  + 'entage <0.0-100.0>)'
                                    ;
                        type decimal64 {
                          fraction-digits 2 ;
                          range 0..100 ;
                        }
                      }
                    }
                    ncd:revise-date 2020-04-06 ;
                  }
                  container drop-rate-threshold {
                    description 'Configure drop rate threshold'
                                ;
                    presence 'Configure drop rate threshold'
                             ;
                    leaf percentage {
                      description 'Set the threshold of drop rate (percentage <'
                                + '0.0-100.0>)'
                                  ;
                      type decimal64 {
                        fraction-digits 2 ;
                        range 0.0..100.0 ;
                      }
                      mandatory true ;
                    }
                    ncd:revise-date 2020-04-06 ;
                  }
                }
                container class-default {
                  description 'Select the default class'
                              ;
                  presence 'Specify the default class'
                           ;
                  leaf class-default {
                    description 'Specify the default class'
                                ;
                    type empty ;
                    mandatory true ;
                  }
                  container bandwidth {
                    description 'Configure minimum guaranteed bandwidth'
                                ;
                    presence 'Configure minimum guaranteed bandwidth'
                             ;
                    leaf percentage {
                      description 'Set the exact bandwidth percentage, support '
                                + '<1-100>'
                                  ;
                      type uint16 {
                        range 1..100 {
                          description 'The exact bandwidth percentage, support '
                                    + '<1-100>'
                                      ;
                        }
                      }
                      mandatory true ;
                    }
                  }
                  container bandwidth-remaining {
                    description 'Configure leftover bandwidth'
                                ;
                    presence 'Configure leftover bandwidth'
                             ;
                    leaf percentage {
                      description 'Set the guaranteed percentage, support <1-10'
                                + '0>'
                                  ;
                      type uint16 {
                        range 1..100 {
                          description 'The guaranteed percentage, support <1-10'
                                    + '0>'
                                      ;
                        }
                      }
                      mandatory true ;
                    }
                  }
                  container priority-level {
                    description 'Configure PQ(Priority Queuing) priority level'
                                ;
                    presence 'Configure PQ priority level'
                             ;
                    leaf priority-value {
                      description 'Set the priority level of PQ, support <1-4>'
                                  ;
                      type uint16 {
                        range 1..4 {
                          description 'The priority level of PQ, support <1-4>'
                                      ;
                        }
                      }
                      mandatory true ;
                    }
                  }
                  container priority-llq {
                    description 'Configure LLQ(Low Latency Queuing) priority'
                                ;
                    presence 'Configure LLQ priority'
                             ;
                    leaf priority-llq {
                      description 'Specify LLQ'
                                  ;
                      type empty ;
                      mandatory true ;
                    }
                  }
                  container queue-limit {
                    description 'Configure queue depth'
                                ;
                    presence 'Configure queue depth'
                             ;
                    choice queue-limit {
                      description 'Configure queue depth'
                                  ;
                      case queue-depth {
                        description 'Set queue depth'
                                    ;
                        leaf queue-depth {
                          description 'Set queue depth, such as 7KB, 16KB, 24KB'
                                    + ', 64KB, 512KB, 2000KB, 8000KB,1000KB,800'
                                    + '0000KB,1000000KB,128000KB,16000KB,24000K'
                                    + 'B,512000KB,64000KB'
                                      ;
                          type enumeration {
                            enum 16 {
                              value 1 ;
                              description 'Set queue depth to 16KB'
                                          ;
                            }
                            enum 24 {
                              value 2 ;
                              description 'Set queue depth to 24KB'
                                          ;
                            }
                            enum 64 {
                              value 3 ;
                              description 'Set queue depth to 64KB'
                                          ;
                            }
                            enum 512 {
                              value 4 ;
                              description 'Set queue depth to 512KB'
                                          ;
                            }
                            enum 2000 {
                              value 5 ;
                              description 'Set queue depth to 2000KB'
                                          ;
                            }
                            enum 8000 {
                              value 6 ;
                              description 'Set queue depth to 8000KB'
                                          ;
                            }
                            enum 7 {
                              value 7 ;
                              description 'Set queue depth to 7KB'
                                          ;
                            }
                            enum 1000 {
                              value 20 ;
                              description 'Set queue depth to 1000KB'
                                          ;
                            }
                            enum 8000000 {
                              value 21 ;
                              description 'Set queue depth to 8000000KB'
                                          ;
                            }
                            enum 1000000 {
                              value 13 ;
                              description 'Set queue depth to 1000000KB'
                                          ;
                            }
                            enum 128000 {
                              value 11 ;
                              description 'Set queue depth to 128000KB'
                                          ;
                            }
                            enum 16000 {
                              value 8 ;
                              description 'Set queue depth to 16000KB'
                                          ;
                            }
                            enum 24000 {
                              value 9 ;
                              description 'Set queue depth to 24000KB'
                                          ;
                            }
                            enum 512000 {
                              value 12 ;
                              description 'Set queue depth to 512000KB'
                                          ;
                            }
                            enum 64000 {
                              value 10 ;
                              description 'Set queue depth to 64000KB'
                                          ;
                            }
                          }
                          units KB ;
                          mandatory true ;
                        }
                      }
                      case queue-value {
                        description 'Set queue depth value(default:KB)'
                                    ;
                        container queue-value {
                          description 'Set queue depth value(default:KB)'
                                      ;
                          leaf queue-value {
                            description 'Set queue depth value(default:KB)'
                                        ;
                            type uint32 {
                              range 7..8000000 {
                                description 'Set queue depth value(default:KB)'
                                            ;
                              }
                            }
                            mandatory true ;
                          }
                        }
                        ncd:revise-date 2019-08-19 ;
                      }
                      case queue-cache-time {
                        description 'Configure cache time of the queue'
                                    ;
                        container queue-cache-time {
                          description 'Configure cache time of the queue'
                                      ;
                          leaf queue-cache-time {
                            description 'Set cache time(default:us)'
                                        ;
                            type uint32 {
                              range 1..100000 {
                                description 'Set cache time(default:us)'
                                            ;
                              }
                            }
                            mandatory true ;
                          }
                        }
                        ncd:revise-date 2019-08-19 ;
                      }
                    }
                  }
                  container random-detect {
                    description 'Configure WRED(Weighted Random Early Detection'
                              + ') information'
                                ;
                    container enable {
                      description 'Configure WRED enable'
                                  ;
                      presence 'Configure WRED enable'
                               ;
                      leaf enable {
                        description 'Specify WRED enable'
                                    ;
                        type empty ;
                        mandatory true ;
                      }
                    }
                    container colors {
                      if-feature policy-action-wred-color ;
                      description 'Configure WRED thresholds based on color'
                                  ;
                      list color {
                        description 'Configure WRED thresholds based on color'
                                    ;
                        key color-type ;
                        leaf color-type {
                          description 'set WRED color, such as green, yellow, r'
                                    + 'ed'
                                      ;
                          type qos-color-type ;
                        }
                        choice threshold {
                          description 'Set the threshold'
                                      ;
                          case threshold-value {
                            description 'Set the threshold value'
                                        ;
                            leaf min-threshold {
                              description 'Set the minimum threshold in kilobytes, support <1-1024000>'
                                          ;
                              type uint32 {
                                range 1..1024000 {
                                  description 'The minimum threshold in kilobytes, support <1-1024000>'
                                              ;
                                }
                              }
                              units KB ;
                              mandatory true ;
                            }
                            leaf max-threshold {
                              description 'Set the maximum threshold in kilobytes, support <1-1024000>'
                                          ;
                              type uint32 {
                                range 1..1024000 {
                                  description 'The maximum threshold in kilobytes, support <1-1024000>'
                                              ;
                                }
                              }
                              units KB ;
                              mandatory true ;
                            }
                          }
                          case threshold-percentage {
                            description 'Set the threshold percentage'
                                        ;
                            container threshold-percentage {
                              description 'Set the threshold percentage'
                                          ;
                              leaf min-threshold-percentage {
                                description 'Set the minimum threshold percentage, support <1-100>'
                                            ;
                                type uint32 {
                                  range 1..100 {
                                    description 'The minimum threshold percentage, support <1-100>'
                                                ;
                                  }
                                }
                                mandatory true ;
                              }
                              leaf max-threshold-percentage {
                                description 'Set the maximum threshold percentage, support <1-100>'
                                            ;
                                type uint32 {
                                  range 1..100 {
                                    description 'The maximum threshold percentage, support <1-100>'
                                                ;
                                  }
                                }
                                mandatory true ;
                              }
                            }
                          }
                          ncd:revise-date 2019-08-05 ;
                        }
                        leaf probability {
                          description 'Set mark probability denominator, suppor'
                                    + 't <1-100>'
                                      ;
                          type uint8 {
                            range 1..100 {
                              description 'Set mark probability denominator, support <1-100>'
                                          ;
                            }
                          }
                          mandatory true ;
                        }
                      }
                    }
                    container precedences {
                      description 'Configure WRED thresholds based on precedence'
                                  ;
                      list precedence {
                        description 'Configure WRED thresholds based on precede'
                                  + 'nce'
                                    ;
                        key prec-value ;
                        leaf prec-value {
                          description 'Set the precedence value, such as MPLS E'
                                    + 'XP, VLAN 802.1p, IP DSCP, IP Precedence,'
                                    + ' support <0-7>'
                                      ;
                          type uint16 {
                            range 0..7 {
                              description 'The precedence value, support <0-7>'
                                          ;
                            }
                          }
                        }
                        choice threshold {
                          case threshold-value {
                            description 'Set the threshold value'
                                        ;
                            leaf min-threshold {
                              description 'Set the minimum threshold (default: kilobytes)'
                                          ;
                              type uint32 {
                                range 1..4294967295 {
                                  description 'The minimum threshold (default: kilobytes), support <1-4294967295>'
                                              ;
                                }
                              }
                              mandatory true ;
                            }
                            leaf min-threshold-unit {
                              description 'set min-threshold unit, such as kbytes, mbytes, gbytes'
                                          ;
                              type qos-threshold-unit-type ;
                            }
                            leaf max-threshold {
                              description 'Set the maximum threshold (default: kilobytes)'
                                          ;
                              type uint32 {
                                range 1..4294967295 {
                                  description 'The maximum threshold (default: kilobytes), support <1-4294967295>'
                                              ;
                                }
                              }
                              mandatory true ;
                            }
                            leaf max-threshold-unit {
                              description 'set max-threshold unit, such as kbytes, mbytes, gbytes'
                                          ;
                              type qos-threshold-unit-type ;
                            }
                          }
                          case threshold-percentage {
                            description 'Set the threshold percentage'
                                        ;
                            container threshold-percentage {
                              description 'Set the threshold percentage'
                                          ;
                              leaf min-threshold-percentage {
                                description 'Set the minimum threshold percentage, support <1-100>'
                                            ;
                                type uint32 {
                                  range 1..100 {
                                    description 'The minimum threshold percentage, support <1-100>'
                                                ;
                                  }
                                }
                                mandatory true ;
                              }
                              leaf max-threshold-percentage {
                                description 'Set the maximum threshold percentage, support <1-100>'
                                            ;
                                type uint32 {
                                  range 1..100 {
                                    description 'The maximum threshold percentage, support <1-100>'
                                                ;
                                  }
                                }
                                mandatory true ;
                              }
                            }
                          }
                          ncd:revise-date 2019-08-05 ;
                        }
                        leaf probability {
                          description 'Set mark probability denominator, suppor'
                                    + 't <1-100>'
                                      ;
                          type uint32 {
                            range 1..100 {
                              description 'Set mark probability denominator, support <1-100>'
                                          ;
                            }
                          }
                          mandatory true ;
                        }
                      }
                    }
                    container weight {
                      description 'Configure WRED exponential weight factor'
                                  ;
                      presence 'Configure WRED exponential weight factor'
                               ;
                      leaf weight-value {
                        description 'Specify exponent used in weighted average '
                                  + 'calculation, support <1-16>'
                                    ;
                        type uint16 {
                          range 1..16 {
                            description 'Exponent used in weighted average calculation'
                                        ;
                          }
                        }
                        mandatory true ;
                      }
                    }
                  }
                  container service-policy {
                    description 'Configure hierarchical service policy'
                                ;
                    presence 'Configure hierarchical service policy'
                             ;
                    leaf hpolicy-name {
                      description 'Name of the hierarchical policy, support 1-3'
                                + '1 characters'
                                  ;
                      type string {
                        length 1..31 {
                          description 'Name of the hierarchical policy, support'
                                    + ' 1-31 characters'
                                      ;
                        }
                      }
                      mandatory true ;
                    }
                  }
                  container shape {
                    if-feature policy-action-shape ;
                    description 'Configure flow shape'
                                ;
                    presence 'Configure flow shape'
                             ;
                    leaf shape-type {
                      description 'Set shape type, such as peak, average'
                                  ;
                      type enumeration {
                        enum average {
                          value 1 ;
                          description 'Set average as shape type'
                                      ;
                        }
                        enum peak {
                          value 2 ;
                          description 'Set peak as shape type'
                                      ;
                        }
                      }
                      mandatory true ;
                    }
                    choice shape-method {
                      description 'Select rate or rate percentage as shape unit'
                                  ;
                      mandatory true ;
                      case rate {
                        description 'Select the average or peak rate'
                                    ;
                        leaf rate-value {
                          description 'Set the average or peak rate in kilobits'
                                    + ' per second, support <1-4294967295>'
                                      ;
                          type uint32 {
                            range 1..4294967295 {
                              description 'The average or peak rate in kbps, support <1-4294967295>'
                                          ;
                            }
                          }
                          units kbps ;
                          mandatory true ;
                        }
                      }
                      case percent {
                        description 'Select rate percent as shape unit'
                                    ;
                        leaf percentage {
                          description 'Set the exact rate percentage, support <'
                                    + '1-100>'
                                      ;
                          type uint16 {
                            range 1..100 {
                              description 'The exact rate percentage, support <1-100>'
                                          ;
                            }
                          }
                          mandatory true ;
                        }
                      }
                    }
                    container burst-rate {
                      description 'Configure burst and peak rate'
                                  ;
                      presence 'Configure committed burst and peak rate'
                               ;
                      leaf bc-value {
                        description 'Set the bc value in kilobits per second, s'
                                  + 'upport <1-4294967295>'
                                    ;
                        type uint32 {
                          range 1..4294967295 {
                            description 'The committed burst information rate in kilobits per second, support <1-429496'
                                      + '7295>'
                                        ;
                          }
                        }
                        units kbps ;
                        mandatory true ;
                      }
                      leaf be-value {
                        description 'Set the be value in kilobits per second, s'
                                  + 'upport <1-4294967295>'
                                    ;
                        type uint32 {
                          range 1..4294967295 {
                            description 'The peak information rate in kilobits per second, support <1-4294967295>'
                                        ;
                          }
                        }
                        units kbps ;
                        mandatory true ;
                      }
                    }
                  }
                  container police {
                    description 'Configure traffic policing'
                                ;
                    presence 'Configure traffic policing'
                             ;
                    choice cir-pir-value-percentage {
                      description 'Configure CIR CBS PIR and PBS'
                                  ;
                      mandatory true ;
                      case cir-pir-value {
                        description 'Configure CIR and PIR with value form'
                                    ;
                        leaf cir {
                          description 'Configure the CIR(Committed Information '
                                    + 'Rate) value (default: kilobits per secon'
                                    + 'd)'
                                      ;
                          type uint32 {
                            range 8..4294967295 {
                              description 'The CIR value (default: kilobits per second),support <8-4294967295>.'
                                          ;
                            }
                          }
                          mandatory true ;
                        }
                        leaf cir-unit {
                          description 'set cir unit, such as kbps, mbps, gbps'
                                      ;
                          type qos-rate-unit-type ;
                        }
                        leaf cbs {
                          description 'Configure the CBS(Committed Burst Size) '
                                    + 'size (default: KB)'
                                      ;
                          type uint32 {
                            range 1..4294967295 {
                              description 'The CBS(Committed Burst Size) size (default: KB), support <1-4294967295>'
                                          ;
                            }
                          }
                        }
                        leaf cbs-unit {
                          description 'set cbs unit, such as kb, mb, gb'
                                      ;
                          type qos-bucket-unit-type ;
                        }
                        container pir-pbs {
                          description 'Configure PIR and PBS'
                                      ;
                          presence 'Configure pir and pbs'
                                   ;
                          leaf pir {
                            description 'Configure the PIR(Peak Information Rate) value (default: kilobits per second)'
                                        ;
                            type uint32 {
                              range 8..4294967295 {
                                description 'The PIR(Peak Information Rate) value (default: kilobits per second), suppo'
                                          + 'rt <8-4294967295>'
                                            ;
                              }
                            }
                            mandatory true ;
                          }
                          leaf pir-unit {
                            description 'set pir unit, such as kbps, mbps, gbps'
                                        ;
                            type qos-rate-unit-type ;
                          }
                          leaf pbs {
                            description 'Configure the PBS(Peak Burst Size) size (default: KB)'
                                        ;
                            type uint32 {
                              range 1..4294967295 {
                                description 'The PBS(Peak Burst Size) size (default: KB), support <1-4294967295>'
                                            ;
                              }
                            }
                          }
                          leaf pbs-unit {
                            description 'set pbs unit, such as kb, mb, gb'
                                        ;
                            type qos-bucket-unit-type ;
                          }
                        }
                      }
                      case cir-pir-percentage {
                        description 'Configure CIR and PIR with percentage form'
                                    ;
                        container cir-pir-percentage {
                          description 'Configure CIR and PIR with percentage fo'
                                    + 'rm'
                                      ;
                          leaf cir-percentage {
                            description 'Configure CIR with percentage form'
                                        ;
                            type uint8 {
                              range 1..100 {
                                description 'Configure CIR with percentage form'
                                            ;
                              }
                            }
                            mandatory true ;
                          }
                          container pir-percentage {
                            description 'Configure PIR with percentage form'
                                        ;
                            presence 'Configure PIR with percentage form'
                                     ;
                            leaf pir-percentage {
                              description 'Configure PIR with percentage form'
                                          ;
                              type uint8 {
                                range 1..100 {
                                  description 'Configure PIR with percentage form'
                                              ;
                                }
                              }
                              mandatory true ;
                            }
                          }
                        }
                        ncd:revise-date 2020-06-09 ;
                      }
                    }
                    container action {
                      description 'Configure action to packets'
                                  ;
                      presence 'Configure action to packets'
                               ;
                      container conform-action {
                        description 'Action to packets that conform to the rate'
                                  + ' limit'
                                    ;
                        choice conform-action {
                          description 'Specify action to packets that conform t'
                                    + 'o the rate limit'
                                      ;
                          mandatory true ;
                          case ca-drop {
                            description 'Drop packet in conform-action'
                                        ;
                            leaf drop {
                              description 'Specify action to drop packet'
                                          ;
                              type empty ;
                              mandatory true ;
                            }
                          }
                          case ca-transmit {
                            description 'Transmit packet in conform-action'
                                        ;
                            leaf transmit {
                              description 'Specify action to transmit packet'
                                          ;
                              type empty ;
                              mandatory true ;
                            }
                          }
                          case ca-mpls-exp {
                            description 'Rewrite packet MPLS-EXP and transmit the packet'
                                        ;
                            leaf set-exp-transmit {
                              description 'Specify action to rewrite packet MPLS-EXP and transmit it'
                                          ;
                              type empty ;
                              mandatory true ;
                            }
                            leaf mpls-exp-value {
                              description 'Reset MPLS-EXP value in conform-action, support <0-7>'
                                          ;
                              type uint8 {
                                range 0..7 {
                                  description 'The MPLS-EXP value, support <0-7>'
                                              ;
                                }
                              }
                              mandatory true ;
                            }
                          }
                          case ca-precedence {
                            description 'Rewrite packet precedence and transmit the packet'
                                        ;
                            leaf set-prec-transmit {
                              description 'Specify action to rewrite packet precedence and transmit it'
                                          ;
                              type empty ;
                              mandatory true ;
                            }
                            leaf prec-value {
                              description 'Reset the IP-Precedence value in conform-action, support <0-7>'
                                          ;
                              type uint8 {
                                range 0..7 {
                                  description 'The IP-Precedence value, support <0-7>'
                                              ;
                                }
                              }
                              mandatory true ;
                            }
                          }
                          case ca-dscp {
                            description 'Rewrite packet DSCP and transmit the packet'
                                        ;
                            leaf set-dscp-transmit {
                              description 'Specify action to rewrite packet DSCP and transmit it'
                                          ;
                              type empty ;
                              mandatory true ;
                            }
                            leaf dscp-value {
                              description 'Reset DSCP in conform-action, support <0-63>'
                                          ;
                              type uint8 {
                                range 0..63 {
                                  description 'The DSCP value, support <0-63>'
                                              ;
                                }
                              }
                              mandatory true ;
                            }
                          }
                          case ca-8021p {
                            description 'Rewrite packet 802.1p and transmit the packet'
                                        ;
                            leaf set-8021p-transmit {
                              description 'Specify action to rewrite packet 802.1p and transmit it'
                                          ;
                              type empty ;
                              mandatory true ;
                            }
                            leaf value-8021p {
                              description 'Reset 802.1p in conform-action, support <0-7>'
                                          ;
                              type uint8 {
                                range 0..7 {
                                  description 'The 802.1p value, support <0-7>'
                                              ;
                                }
                              }
                              mandatory true ;
                            }
                          }
                          case ca-priority {
                            description 'Rewrite packet priority and transmit the packet'
                                        ;
                            leaf set-priority-transmit {
                              description 'Specify action to rewrite packet priority and transmit it'
                                          ;
                              type empty ;
                              mandatory true ;
                            }
                            leaf priority-value {
                              description 'Reset priority in conform-action, support <1-4>'
                                          ;
                              type uint8 {
                                range 1..4 {
                                  description 'The priority value, support <1-4>'
                                              ;
                                }
                              }
                              mandatory true ;
                            }
                          }
                        }
                      }
                      container exceed-action {
                        description 'Action to packets that exceed the rate lim'
                                  + 'it'
                                    ;
                        choice exceed-action {
                          description 'Specify action to packets that exceed th'
                                    + 'e rate limit'
                                      ;
                          mandatory true ;
                          case ea-drop {
                            description 'Drop packet in exceed-action'
                                        ;
                            leaf drop {
                              description 'Specify action to drop packet'
                                          ;
                              type empty ;
                              mandatory true ;
                            }
                          }
                          case ea-transmit {
                            description 'Transmit packet in exceed-action'
                                        ;
                            leaf transmit {
                              description 'Specify action to transmit packet'
                                          ;
                              type empty ;
                              mandatory true ;
                            }
                          }
                          case ea-mpls-exp {
                            description 'Rewrite packet MPLS-EXP and transmit the packet'
                                        ;
                            leaf set-exp-transmit {
                              description 'Specify action to rewrite packet MPLS-EXP and transmit it'
                                          ;
                              type empty ;
                              mandatory true ;
                            }
                            leaf mpls-exp-value {
                              description 'Reset MPLS-EXP value in exceed-action, support <0-7>'
                                          ;
                              type uint8 {
                                range 0..7 {
                                  description 'The MPLS-EXP value, support <0-7>'
                                              ;
                                }
                              }
                              mandatory true ;
                            }
                          }
                          case ea-precedence {
                            description 'Rewrite packet precedence and transmit the packet'
                                        ;
                            leaf set-prec-transmit {
                              description 'Specify action to rewrite packet precedence and transmit it'
                                          ;
                              type empty ;
                              mandatory true ;
                            }
                            leaf prec-value {
                              description 'Reset the IP-Precedence value in exceed-action, support <0-7>'
                                          ;
                              type uint8 {
                                range 0..7 {
                                  description 'The IP-Precedence value, support <0-7>'
                                              ;
                                }
                              }
                              mandatory true ;
                            }
                          }
                          case ea-dscp {
                            description 'Rewrite packet DSCP and transmit the packet'
                                        ;
                            leaf set-dscp-transmit {
                              description 'Specify action to rewrite packet DSCP and transmit it'
                                          ;
                              type empty ;
                              mandatory true ;
                            }
                            leaf dscp-value {
                              description 'Reset DSCP in exceed-action, support <0-63>'
                                          ;
                              type uint8 {
                                range 0..63 {
                                  description 'The DSCP value, support <0-63>'
                                              ;
                                }
                              }
                              mandatory true ;
                            }
                          }
                          case ea-8021p {
                            description 'Rewrite packet 802.1p and transmit the packet'
                                        ;
                            leaf set-8021p-transmit {
                              description 'Specify action to rewrite packet 802.1p and transmit the packet'
                                          ;
                              type empty ;
                              mandatory true ;
                            }
                            leaf value-8021p {
                              description 'Reset 802.1p in exceed-action, support <0-7>'
                                          ;
                              type uint8 {
                                range 0..7 {
                                  description 'The 802.1p value, support <0-7>'
                                              ;
                                }
                              }
                              mandatory true ;
                            }
                          }
                          case ea-priority {
                            description 'Rewrite packet priority and transmit the packet'
                                        ;
                            leaf set-priority-transmit {
                              description 'Specify action to rewrite packet priority and transmit it'
                                          ;
                              type empty ;
                              mandatory true ;
                            }
                            leaf priority-value {
                              description 'Reset priority in exceed-action, support <1-4>'
                                          ;
                              type uint8 {
                                range 1..4 {
                                  description 'The priority value, support <1-4>'
                                              ;
                                }
                              }
                              mandatory true ;
                            }
                          }
                        }
                      }
                      container violate-action {
                        description 'Action to packets that violate the rate li'
                                  + 'mit'
                                    ;
                        choice violate-action {
                          description 'Specify action to packets that violate t'
                                    + 'he rate limit'
                                      ;
                          mandatory true ;
                          case va-drop {
                            description 'Drop packet in violate-action'
                                        ;
                            leaf drop {
                              description 'Specify action to drop packet'
                                          ;
                              type empty ;
                              mandatory true ;
                            }
                          }
                          case va-transmit {
                            description 'Transmit packet in violate-action'
                                        ;
                            leaf transmit {
                              description 'Specify action to transmit packet'
                                          ;
                              type empty ;
                              mandatory true ;
                            }
                          }
                          case va-mpls-exp {
                            description 'Rewrite packet MPLS-EXP and transmit the packet'
                                        ;
                            leaf set-exp-transmit {
                              description 'Specify action to rewrite packet MPLS-EXP and transmit it'
                                          ;
                              type empty ;
                              mandatory true ;
                            }
                            leaf mpls-exp-value {
                              description 'Reset MPLS-EXP value in violate-action, support <0-7>'
                                          ;
                              type uint8 {
                                range 0..7 {
                                  description 'The MPLS-EXP value, support <0-7>'
                                              ;
                                }
                              }
                              mandatory true ;
                            }
                          }
                          case va-precedence {
                            description 'Rewrite packet precedence and transmit the packet'
                                        ;
                            leaf set-prec-transmit {
                              description 'Specify action to rewrite packet precedence and transmit it'
                                          ;
                              type empty ;
                              mandatory true ;
                            }
                            leaf prec-value {
                              description 'Reset the IP-Precedence value in violate-action, support <0-7>'
                                          ;
                              type uint8 {
                                range 0..7 {
                                  description 'The IP-Precedence value, support <0-7>'
                                              ;
                                }
                              }
                              mandatory true ;
                            }
                          }
                          case va-dscp {
                            description 'Rewrite packet DSCP and transmit the packet'
                                        ;
                            leaf set-dscp-transmit {
                              description 'Specify action to rewrite packet DSCP and transmit it'
                                          ;
                              type empty ;
                              mandatory true ;
                            }
                            leaf dscp-value {
                              description 'Reset DSCP in violate-action, support <0-63>'
                                          ;
                              type uint8 {
                                range 0..63 {
                                  description 'The DSCP value, support <0-63>'
                                              ;
                                }
                              }
                              mandatory true ;
                            }
                          }
                          case va-8021p {
                            description 'Rewrite packet 802.1p and transmit the packet'
                                        ;
                            leaf set-8021p-transmit {
                              description 'Specify action to rewrite packet 802.1p and transmit it'
                                          ;
                              type empty ;
                              mandatory true ;
                            }
                            leaf value-8021p {
                              description 'Reset 802.1p in violate-action, support <0-7>'
                                          ;
                              type uint8 {
                                range 0..7 {
                                  description 'The 802.1p value, support <0-7>'
                                              ;
                                }
                              }
                              mandatory true ;
                            }
                          }
                          case va-priority {
                            description 'Rewrite packet priority and transmit the packet'
                                        ;
                            leaf set-priority-transmit {
                              description 'Specify action to rewrite packet priority and transmit it'
                                          ;
                              type empty ;
                              mandatory true ;
                            }
                            leaf priority-value {
                              description 'Reset priority in violate-action, support <1-4>'
                                          ;
                              type uint8 {
                                range 1..4 {
                                  description 'The priority value, support <1-4>'
                                              ;
                                }
                              }
                              mandatory true ;
                            }
                          }
                        }
                      }
                    }
                  }
                  container set {
                    description 'Mark a packet'
                                ;
                    container dscp {
                      description 'Select DSCP as mark type'
                                  ;
                      presence 'Select DSCP as mark typ'
                               ;
                      choice method {
                        description 'Specify the method to set DSCP'
                                    ;
                        mandatory true ;
                        case set-value {
                          description 'Set the DSCP value directly'
                                      ;
                          container set-value {
                            description 'Set the DSCP value directly'
                                        ;
                            leaf dscp-value {
                              description 'DSCP value, support <0-63>'
                                          ;
                              type uint16 {
                                range 0..63 {
                                  description 'DSCP value, support <0-63>'
                                              ;
                                }
                              }
                              mandatory true ;
                            }
                          }
                        }
                        case inherit {
                          description 'Set the DSCP value by inheriting'
                                      ;
                          container inherit {
                            description 'Set the DSCP value by inheriting'
                                        ;
                            leaf inherit-type {
                              description 'Specify the source inherit type, such as precedence, mpls-exp, 8021p, dscp, '
                                        + 'pay-load 8021p'
                                          ;
                              type enumeration {
                                enum precedence {
                                  value 1 ;
                                  description 'Select precedence as source inherit'
                                              ;
                                }
                                enum mpls-exp {
                                  value 2 ;
                                  description 'Select MPLS-EXP as source inherit'
                                              ;
                                }
                                enum 8021p {
                                  value 3 ;
                                  description 'Select 802.1p as source inherit'
                                              ;
                                }
                                enum dscp {
                                  value 4 ;
                                  description 'Select dscp as source inherit'
                                              ;
                                }
                                enum pay-load-8021p {
                                  value 6 ;
                                  description 'Select inner 802.1p as source inherit'
                                              ;
                                }
                              }
                              mandatory true ;
                            }
                          }
                        }
                      }
                    }
                    container precedence {
                      description 'Select precedence as mark type'
                                  ;
                      presence 'Select precedence as mark type'
                               ;
                      choice method {
                        description 'Specify the method to set IP Precedence'
                                    ;
                        mandatory true ;
                        case set-value {
                          description 'Set the IP Precedence value directly'
                                      ;
                          container set-value {
                            description 'Set the IP Precedence value directly'
                                        ;
                            leaf prec-value {
                              description 'IP Precedence value, support <0-7>'
                                          ;
                              type uint16 {
                                range 0..7 {
                                  description 'IP Precedence value, support <0-7>'
                                              ;
                                }
                              }
                              mandatory true ;
                            }
                          }
                        }
                        case inherit {
                          description 'Set the IP Precedence value by inheriting'
                                      ;
                          container inherit {
                            description 'Set the IP Precedence value by inheriting'
                                        ;
                            leaf inherit-type {
                              description 'Specify the source inherit type, such as precedence, mpls-exp, 8021p, dscp'
                                          ;
                              type enumeration {
                                enum precedence {
                                  value 1 ;
                                  description 'Select precedence as source inherit'
                                              ;
                                }
                                enum mpls-exp {
                                  value 2 ;
                                  description 'Select MPLS-EXP as source inherit'
                                              ;
                                }
                                enum 8021p {
                                  value 3 ;
                                  description 'Select 802.1p as source inherit'
                                              ;
                                }
                                enum dscp {
                                  value 4 ;
                                  description 'Select dscp as source inherit'
                                              ;
                                }
                              }
                              mandatory true ;
                            }
                          }
                        }
                      }
                    }
                    container pri-8021p {
                      description 'Select 802.1p as mark type'
                                  ;
                      presence 'Select 802.1p as mark type'
                               ;
                      choice method {
                        description 'Specify the method to set 802.1p'
                                    ;
                        mandatory true ;
                        case set-value {
                          description 'Set the 802.1p value directly'
                                      ;
                          container set-value {
                            description 'Set the 802.1p value directly'
                                        ;
                            leaf value-8021p {
                              description '802.1p value, support <0-7>'
                                          ;
                              type uint16 {
                                range 0..7 {
                                  description '802.1p value, support <0-7>'
                                              ;
                                }
                              }
                              mandatory true ;
                            }
                            leaf inner-outer {
                              description 'Set 8021p inner or outer flag.If vlaue is 0, it means outer flag. If value i'
                                        + 's 1,it means inner and outer flag.'
                                          ;
                              type uint8 {
                                range 0..1 {
                                  description 'Inner or outer flag. 0 is outer. 1 is inner and outer'
                                              ;
                                }
                              }
                              default 0 ;
                              ncd:revise-date 2017-01-10 ;
                            }
                          }
                        }
                        case inherit {
                          description 'Set the 802.1p value by inheriting'
                                      ;
                          container inherit {
                            description 'Set the 802.1p value by inheriting'
                                        ;
                            leaf inherit-type {
                              description 'Specify the source inherit type, such as precedence, mpls-exp, 8021p, dscp'
                                          ;
                              type enumeration {
                                enum precedence {
                                  value 1 ;
                                  description 'Select precedence as source inherit'
                                              ;
                                }
                                enum mpls-exp {
                                  value 2 ;
                                  description 'Select MPLS-EXP as source inherit'
                                              ;
                                }
                                enum 8021p {
                                  value 3 ;
                                  description 'Select 802.1p as source inherit'
                                              ;
                                }
                                enum dscp {
                                  value 4 ;
                                  description 'Select dscp as source inherit'
                                              ;
                                }
                              }
                              mandatory true ;
                            }
                            leaf inner-outer {
                              description 'Set 8021p inner or outer flag.If vlaue is 0, it means outer flag. If value i'
                                        + 's 1,it means inner and outer flag.'
                                          ;
                              type uint8 {
                                range 0..1 {
                                  description 'Inner or outer flag. 0 is outer. 1 is inner and outer'
                                              ;
                                }
                              }
                              default 0 ;
                              ncd:revise-date 2017-01-10 ;
                            }
                          }
                        }
                      }
                    }
                    container mpls-exp {
                      description 'Select MPLS-EXP as mark type'
                                  ;
                      presence 'Select MPLS-EXP as mark type'
                               ;
                      leaf label-type {
                        if-feature policy-action-set-label ;
                        description 'Select MPLS-EXP label position, such as '+"\n"
                                  + '    default    The default for topmost lab'
                                  + 'el'+"\n"
                                  + '    topmost    Set the MPLS-EXP value on t'
                                  + 'opmost label'+"\n"
                                  + '    imposition Set the MPLS-EXP value on a'
                                  + 'll imposed labels'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on all imposed labels'
                                        ;
                          }
                          enum default {
                            value 0 ;
                            description 'The default for topmost label'
                                        ;
                          }
                          enum inner {
                            value 3 ;
                            description 'Set the MPLS-EXP value on inner label'
                                        ;
                          }
                        }
                      }
                      choice method {
                        description 'Specify the method to set MPLS-EXP'
                                    ;
                        mandatory true ;
                        case set-value {
                          description 'Set the MPLS-EXP value directly'
                                      ;
                          container set-value {
                            description 'Set the MPLS-EXP value directly'
                                        ;
                            leaf mpls-exp-value {
                              description 'MPLS-EXP value, support <0-7>'
                                          ;
                              type uint16 {
                                range 0..7 {
                                  description 'MPLS-EXP value, support <0-7>'
                                              ;
                                }
                              }
                              mandatory true ;
                            }
                          }
                        }
                        case inherit {
                          description 'Set the MPLS-EXP value by inheriting'
                                      ;
                          container inherit {
                            description 'Set the MPLS-EXP value by inheriting'
                                        ;
                            leaf inherit-type {
                              description 'Specify the source inherit type, such as precedence, mpls-exp, 8021p, dscp'
                                          ;
                              type enumeration {
                                enum precedence {
                                  value 1 ;
                                  description 'Select precedence as source inherit'
                                              ;
                                }
                                enum mpls-exp {
                                  value 2 ;
                                  description 'Select MPLS-EXP as source inherit'
                                              ;
                                }
                                enum 8021p {
                                  value 3 ;
                                  description 'Select 802.1p as source inherit'
                                              ;
                                }
                                enum dscp {
                                  value 4 ;
                                  description 'Select dscp as source inherit'
                                              ;
                                }
                              }
                              mandatory true ;
                            }
                          }
                        }
                      }
                    }
                    container multi-mpls-exp {
                      if-feature policy-action-set-multi-exp ;
                      description 'Select multi-MPLS-EXP as mark type'
                                  ;
                      presence 'Select multi-MPLS-EXP as mark type'
                               ;
                      leaf inner-value {
                        description 'Inner multi-MPLS-EXP value, support <0-7>'
                                    ;
                        type uint8 {
                          range 0..7 {
                            description 'Inner multi-MPLS-EXP value, support <0-7>'
                                        ;
                          }
                        }
                        mandatory true ;
                      }
                      leaf outer-value {
                        description 'Outer multi-MPLS-EXP value, support <0-7>'
                                    ;
                        type uint8 {
                          range 0..7 {
                            description 'Outer multi-MPLS-EXP value, support <0-7>'
                                        ;
                          }
                        }
                        mandatory true ;
                      }
                    }
                    container interface {
                      description 'Specify interface name'
                                  ;
                      presence 'Specify interface name'
                               ;
                      leaf if-name {
                        description 'Specify interface name'
                                    ;
                        type ncd:ifname {
                          length 1..31 {
                            description 'Name of the interface, support 1-31 characters'
                                        ;
                          }
                        }
                        mandatory true ;
                      }
                      ncd:revise-date 2017-02-20 ;
                    }
                    container vlan-id {
                      description 'Configure VLAN ID'
                                  ;
                      presence 'Configure VLAN ID'
                               ;
                      leaf vlan-value {
                        description 'Set VLAN ID, support <1-4094>'
                                    ;
                        type uint16 {
                          range 1..4094 ;
                        }
                        mandatory true ;
                      }
                      ncd:revise-date 2017-02-20 ;
                    }
                    container service-query {
                      description 'Configure service function path'
                                  ;
                      presence 'Configure service function path'
                               ;
                      leaf query-number {
                        description 'Service function path, support <0-255>'
                                    ;
                        type uint8 {
                          range 0..255 ;
                        }
                        mandatory true ;
                      }
                      ncd:revise-date 2017-02-20 ;
                    }
                    container service-class {
                      description 'Configure service class'
                                  ;
                      presence 'Configure service function path'
                               ;
                      leaf service-class {
                        description 'Select service class of PHB info, see belo'
                                  + 'w:'+"\n"
                                  + '  be (1) Best effort'+"\n"
                                  + '  af1(2) Assured forwarding class 1'+"\n"
                                  + '  af2(3) Assured forwarding class 2'+"\n"
                                  + '  af3(4) Assured forwarding class 3'+"\n"
                                  + '  af4(5) Assured forwarding class 4'+"\n"
                                  + '  ef (6) Expedited forward'+"\n"
                                  + '  cs6(7) Internetwork control service clas'
                                  + 's'+"\n"
                                  + '  cs7(8) Network control service class'
                                    ;
                        type qos-service-class ;
                        mandatory true ;
                      }
                      leaf color-type {
                        description 'Specify packets color, support <green,yell'
                                  + 'ow,red>'
                                    ;
                        type qos-color-type ;
                      }
                      ncd:revise-date 2021-01-18 ;
                    }
                  }
                  container drop {
                    if-feature policy-action-drop ;
                    description 'Configure drop'
                                ;
                    presence 'Configure drop'
                             ;
                    leaf drop {
                      description 'Specify drop'
                                  ;
                      type empty ;
                      mandatory true ;
                    }
                  }
                  container latency-time-threshold {
                    description 'Configure latency time threshold'
                                ;
                    presence 'Configure latency time threshold'
                             ;
                    leaf value {
                      description 'Set the threshold of latency time'
                                  ;
                      type uint32 {
                        range 1..1000 ;
                      }
                      mandatory true ;
                    }
                    ncd:revise-date 2020-04-06 ;
                  }
                  container bandwidth-threshold {
                    description 'Configure bandwidth threshold'
                                ;
                    presence 'Configure bandwidth threshold'
                             ;
                    leaf value {
                      description 'Set the threshold of bandwidth'
                                  ;
                      type uint32 {
                        range 1..10000000 ;
                      }
                      mandatory true ;
                    }
                    container percentage {
                      description 'Configure percentage of acceleration or dece'
                                + 'leration'
                                  ;
                      leaf up {
                        description 'Configure percentage of acceleration (perc'
                                  + 'entage <0.0-100.0>)'
                                    ;
                        type decimal64 {
                          fraction-digits 2 ;
                          range 0..100 ;
                        }
                      }
                      leaf down {
                        description 'Configure percentage of deceleration (perc'
                                  + 'entage <0.0-100.0>)'
                                    ;
                        type decimal64 {
                          fraction-digits 2 ;
                          range 0..100 ;
                        }
                      }
                    }
                    ncd:revise-date 2020-04-06 ;
                  }
                  container drop-rate-threshold {
                    description 'Configure drop rate threshold'
                                ;
                    presence 'Configure drop rate threshold'
                             ;
                    leaf percentage {
                      description 'Set the threshold of drop rate (percentage <'
                                + '0.0-100.0>)'
                                  ;
                      type decimal64 {
                        fraction-digits 2 ;
                        range 0.0..100.0 ;
                      }
                      mandatory true ;
                    }
                    ncd:revise-date 2020-04-06 ;
                  }
                }
              }
              container pmap-description {
                description 'Description of a policy map, support 1-79 characte'
                          + 'rs.'
                            ;
                presence 'Specify description of policy map'
                         ;
                leaf pmap-description {
                  description 'Description of a policy map, support 1-79 charac'
                            + 'ters.'
                              ;
                  type ncd:string-with-blank {
                    length 1..79 {
                      description 'Description of a policy map, support 1-79 ch'
                                + 'aracters.'
                                  ;
                    }
                  }
                  mandatory true ;
                }
                ncd:revise-date 2020-06-18 ;
              }
            }
          }
        }
        container car-action {
          if-feature car-action-mode ;
          description 'Policy map based on car-action'
                      ;
          container policy-maps {
            description 'Configure H-QoS policy map lists'
                        ;
            list policy-map {
              description 'Configure H-QoS policy maps'
                          ;
              key pmap-name ;
              leaf pmap-name {
                description 'Name of the policy map, support 1-31 characters'
                            ;
                type string {
                  length 1..31 {
                    description 'Name of the policy map, support 1-31 characters'
                                ;
                  }
                }
              }
              container class-maps {
                description 'Configure H-QoS policy class'
                            ;
                list class-map {
                  description 'Configure H-QoS policy class'
                              ;
                  key cmap-name ;
                  leaf cmap-name {
                    description 'Name of the class map, support 1-31 characters'
                                ;
                    type string {
                      length 1..31 {
                        description 'Name of the class map, support 1-31 charac'
                                  + 'ters'
                                    ;
                      }
                    }
                  }
                  container police {
                    description 'Configure traffic policing'
                                ;
                    presence 'Configure traffic policing'
                             ;
                    leaf cir {
                      description 'Configure the CIR(Committed Information Rate'
                                + ') value (default: kilobits per second)'
                                  ;
                      type uint32 {
                        range 8..4294967295 {
                          description 'The CIR value (default: kilobits per sec'
                                    + 'ond),support <8-4294967295>'
                                      ;
                        }
                      }
                      mandatory true ;
                    }
                    leaf cir-unit {
                      description 'set cir unit, such as kbps, mbps, gbps'
                                  ;
                      type qos-rate-unit-type ;
                    }
                    leaf cbs {
                      description 'Configure the CBS(Committed Burst Size) size'
                                + ' in bytes.'
                                  ;
                      type uint32 {
                        range 1..4294967295 {
                          description 'The CBS(Committed Burst Size) size in by'
                                    + 'tes, support <1-4294967295>'
                                      ;
                        }
                      }
                      units Byte ;
                    }
                    leaf pir {
                      description 'Configure the PIR(Peak Information Rate) val'
                                + 'ue (default: kilobits per second)'
                                  ;
                      type uint32 {
                        range 8..4294967295 {
                          description 'The PIR(Peak Information Rate) value (de'
                                    + 'fault: kilobits per second), support <8-'
                                    + '4294967295>'
                                      ;
                        }
                      }
                      mandatory true ;
                    }
                    leaf pir-unit {
                      description 'set pir unit, such as kbps, mbps, gbps'
                                  ;
                      type qos-rate-unit-type ;
                    }
                    leaf pbs {
                      description 'Configure the PBS(Peak Burst Size) size in b'
                                + 'ytes.'
                                  ;
                      type uint32 {
                        range 1..4294967295 {
                          description 'The PBS(Peak Burst Size) size in bytes, '
                                    + 'support <1-4294967295>'
                                      ;
                        }
                      }
                      units Byte ;
                    }
                    container conform-action {
                      description 'Action to packets that conform to the rate l'
                                + 'imit'
                                  ;
                      choice conform-action {
                        description 'Specify action to packets that conform to '
                                  + 'the rate limit'
                                    ;
                        mandatory true ;
                        case ca-drop {
                          description 'Drop packet in conform-action'
                                      ;
                          leaf drop {
                            description 'Specify action to drop packet'
                                        ;
                            type empty ;
                            mandatory true ;
                          }
                        }
                        case ca-transmit {
                          description 'Transmit packet in conform-action'
                                      ;
                          leaf transmit {
                            description 'Specify action to transmit packet'
                                        ;
                            type empty ;
                            mandatory true ;
                          }
                        }
                        case ca-mpls-exp {
                          description 'Rewrite packet MPLS-EXP and transmit the'
                                    + ' packet'
                                      ;
                          leaf set-exp-transmit {
                            description 'Specify action to rewrite packet MPLS-EXP and transmit it'
                                        ;
                            type empty ;
                            mandatory true ;
                          }
                          container mpls-label-type {
                            description 'Set MPLS-EXP label type'
                                        ;
                            presence 'Set MPLS-EXP label type'
                                     ;
                            leaf label-type {
                              description 'Set MPLS-EXP label position, such as '+"\n"
                                        + '    topmost    Set the MPLS-EXP value on topmost label'+"\n"
                                        + '    imposition Set the MPLS-EXP value on imposition label'+"\n"
                                        + '    inner      Set the MPLS-EXP value on inner label'
                                          ;
                              type enumeration {
                                enum topmost {
                                  value 1 ;
                                  description 'Set the MPLS-EXP value on topmost label'
                                              ;
                                }
                                enum imposition {
                                  value 2 ;
                                  description 'Set the MPLS-EXP value on imposition label'
                                              ;
                                }
                                enum inner {
                                  value 3 ;
                                  description 'Set the MPLS-EXP value on inner label'
                                              ;
                                }
                              }
                              mandatory true ;
                            }
                          }
                          leaf mpls-exp-value {
                            description 'Reset MPLS-EXP value in conform-action, support <0-7>'
                                        ;
                            type uint8 {
                              range 0..7 {
                                description 'The MPLS-EXP value, support <0-7>'
                                            ;
                              }
                            }
                            mandatory true ;
                          }
                        }
                        case ca-precedence {
                          description 'Rewrite packet precedence and transmit t'
                                    + 'he packet'
                                      ;
                          leaf set-prec-transmit {
                            description 'Specify action to rewrite packet precedence and transmit it'
                                        ;
                            type empty ;
                            mandatory true ;
                          }
                          leaf prec-value {
                            description 'Reset the IP-Precedence value in conform-action, support <0-7>'
                                        ;
                            type uint8 {
                              range 0..7 {
                                description 'The IP-Precedence value, support <0-7>'
                                            ;
                              }
                            }
                            mandatory true ;
                          }
                        }
                        case ca-dscp {
                          description 'Rewrite packet DSCP and transmit the pac'
                                    + 'ket'
                                      ;
                          leaf set-dscp-transmit {
                            description 'Specify action to rewrite packet DSCP and transmit it'
                                        ;
                            type empty ;
                            mandatory true ;
                          }
                          leaf dscp-value {
                            description 'Reset DSCP in conform-action, support <0-63>'
                                        ;
                            type uint8 {
                              range 0..63 {
                                description 'The DSCP value, support <0-63>'
                                            ;
                              }
                            }
                            mandatory true ;
                          }
                        }
                        case ca-8021p {
                          description 'Rewrite packet 802.1p and transmit the p'
                                    + 'acket'
                                      ;
                          leaf set-8021p-transmit {
                            description 'Specify action to rewrite packet 802.1p and transmit it'
                                        ;
                            type empty ;
                            mandatory true ;
                          }
                          leaf value-8021p {
                            description 'Reset 802.1p in conform-action, support <0-7>'
                                        ;
                            type uint8 {
                              range 0..7 {
                                description 'The 802.1p value, support <0-7>'
                                            ;
                              }
                            }
                            mandatory true ;
                          }
                        }
                        case ca-multi-exp-transmit {
                          description 'Rewrite packet multi-MPLS-EXP and transm'
                                    + 'it it'
                                      ;
                          leaf set-multi-exp-transmit {
                            description 'Specify action to rewrite packet multi-MPLS-EXP and transmit it'
                                        ;
                            type empty ;
                            mandatory true ;
                          }
                          leaf inner-value {
                            description 'Inner multi-MPLS-EXP value, support <0-7>'
                                        ;
                            type uint8 {
                              range 0..7 {
                                description 'Inner multi-MPLS-EXP value, support <0-7>'
                                            ;
                              }
                            }
                            mandatory true ;
                          }
                          leaf outer-value {
                            description 'Outer multi-MPLS-EXP value, support <0-7>'
                                        ;
                            type uint8 {
                              range 0..7 {
                                description 'Outer multi-MPLS-EXP value, support <0-7>'
                                            ;
                              }
                            }
                            mandatory true ;
                          }
                        }
                        case ca-service-class {
                          description 'Specify action to rewrite packet service'
                                    + '-class and transmit it'
                                      ;
                          leaf service-class-value {
                            description 'Reset service class in conform-action'
                                        ;
                            type qos-service-class ;
                            mandatory true ;
                          }
                          ncd:revise-date 2020-06-23 ;
                        }
                      }
                    }
                    container exceed-action {
                      description 'Action to packets that exceed the rate limit'
                                  ;
                      choice exceed-action {
                        description 'Specify action to packets that exceed the '
                                  + 'rate limit'
                                    ;
                        mandatory true ;
                        case ea-drop {
                          description 'Drop packet in exceed-action'
                                      ;
                          leaf drop {
                            description 'Specify action to drop packet'
                                        ;
                            type empty ;
                            mandatory true ;
                          }
                        }
                        case ea-transmit {
                          description 'Transmit packet in exceed-action'
                                      ;
                          leaf transmit {
                            description 'Specify action to transmit packet'
                                        ;
                            type empty ;
                            mandatory true ;
                          }
                        }
                        case ea-mpls-exp {
                          description 'Rewrite packet MPLS-EXP and transmit the'
                                    + ' packet'
                                      ;
                          leaf set-exp-transmit {
                            description 'Specify action to rewrite packet MPLS-EXP and transmit it'
                                        ;
                            type empty ;
                            mandatory true ;
                          }
                          container mpls-label-type {
                            description 'Set MPLS-EXP label type'
                                        ;
                            presence 'Set MPLS-EXP label type'
                                     ;
                            leaf label-type {
                              description 'Set MPLS-EXP label position, such as '+"\n"
                                        + '    topmost    Set the MPLS-EXP value on topmost label'+"\n"
                                        + '    imposition Set the MPLS-EXP value on imposition label'+"\n"
                                        + '    inner      Set the MPLS-EXP value on inner label'
                                          ;
                              type enumeration {
                                enum topmost {
                                  value 1 ;
                                  description 'Set the MPLS-EXP value on topmost label'
                                              ;
                                }
                                enum imposition {
                                  value 2 ;
                                  description 'Set the MPLS-EXP value on imposition label'
                                              ;
                                }
                                enum inner {
                                  value 3 ;
                                  description 'Set the MPLS-EXP value on inner label'
                                              ;
                                }
                              }
                              mandatory true ;
                            }
                          }
                          leaf mpls-exp-value {
                            description 'Reset MPLS-EXP value in exceed-action, support <0-7>'
                                        ;
                            type uint8 {
                              range 0..7 {
                                description 'The MPLS-EXP value, support <0-7>'
                                            ;
                              }
                            }
                            mandatory true ;
                          }
                        }
                        case ea-precedence {
                          description 'Rewrite packet precedence and transmit t'
                                    + 'he packet'
                                      ;
                          leaf set-prec-transmit {
                            description 'Specify action to rewrite packet precedence and transmit it'
                                        ;
                            type empty ;
                            mandatory true ;
                          }
                          leaf prec-value {
                            description 'Reset the IP-Precedence value in exceed-action, support <0-7>'
                                        ;
                            type uint8 {
                              range 0..7 {
                                description 'The IP-Precedence value, support <0-7>'
                                            ;
                              }
                            }
                            mandatory true ;
                          }
                        }
                        case ea-dscp {
                          description 'Rewrite packet DSCP and transmit the pac'
                                    + 'ket'
                                      ;
                          leaf set-dscp-transmit {
                            description 'Specify action to rewrite packet DSCP and transmit it'
                                        ;
                            type empty ;
                            mandatory true ;
                          }
                          leaf dscp-value {
                            description 'Reset DSCP in exceed-action, support <0-63>'
                                        ;
                            type uint8 {
                              range 0..63 {
                                description 'The DSCP value, support <0-63>'
                                            ;
                              }
                            }
                            mandatory true ;
                          }
                        }
                        case ea-8021p {
                          description 'Rewrite packet 802.1p and transmit the p'
                                    + 'acket'
                                      ;
                          leaf set-8021p-transmit {
                            description 'Specify action to rewrite packet 802.1p and transmit it'
                                        ;
                            type empty ;
                            mandatory true ;
                          }
                          leaf value-8021p {
                            description 'Reset 802.1p in exceed-action, support <0-7>'
                                        ;
                            type uint8 {
                              range 0..7 {
                                description 'The 802.1p value, support <0-7>'
                                            ;
                              }
                            }
                            mandatory true ;
                          }
                        }
                        case ea-multi-exp-transmit {
                          description 'Rewrite packet multi-MPLS-EXP and transm'
                                    + 'it it'
                                      ;
                          leaf set-multi-exp-transmit {
                            description 'Specify action to rewrite packet multi-MPLS-EXP and transmit it'
                                        ;
                            type empty ;
                            mandatory true ;
                          }
                          leaf inner-value {
                            description 'Inner multi-MPLS-EXP value, support <0-7>'
                                        ;
                            type uint8 {
                              range 0..7 {
                                description 'Inner multi-MPLS-EXP value, support <0-7>'
                                            ;
                              }
                            }
                            mandatory true ;
                          }
                          leaf outer-value {
                            description 'Outer multi-MPLS-EXP value, support <0-7>'
                                        ;
                            type uint8 {
                              range 0..7 {
                                description 'Outer multi-MPLS-EXP value, support <0-7>'
                                            ;
                              }
                            }
                            mandatory true ;
                          }
                        }
                        case ea-service-class {
                          description 'Specify action to rewrite packet service'
                                    + ' class and transmit it'
                                      ;
                          leaf service-class-value {
                            description 'Reset service class in exceed-action'
                                        ;
                            type qos-service-class ;
                            mandatory true ;
                          }
                          ncd:revise-date 2020-06-23 ;
                        }
                      }
                    }
                    container violate-action {
                      description 'Action to packets that violate the rate limit'
                                  ;
                      choice violate-action {
                        description 'Specify action to packets that violate the'
                                  + ' rate limit'
                                    ;
                        mandatory true ;
                        case va-drop {
                          description 'Drop packet in violate-action'
                                      ;
                          leaf drop {
                            description 'Specify action to drop packet'
                                        ;
                            type empty ;
                            mandatory true ;
                          }
                        }
                        case va-transmit {
                          description 'Transmit packet in violate-action'
                                      ;
                          leaf transmit {
                            description 'Specify action to transmit packet'
                                        ;
                            type empty ;
                            mandatory true ;
                          }
                        }
                        case va-mpls-exp {
                          description 'Rewrite packet MPLS-EXP and transmit the'
                                    + ' packet'
                                      ;
                          leaf set-exp-transmit {
                            description 'Specify action to rewrite packet MPLS-EXP and transmit it'
                                        ;
                            type empty ;
                            mandatory true ;
                          }
                          container mpls-label-type {
                            description 'Set MPLS-EXP label type'
                                        ;
                            presence 'Set MPLS-EXP label type'
                                     ;
                            leaf label-type {
                              description 'Set MPLS-EXP label position, such as '+"\n"
                                        + '    topmost    Set the MPLS-EXP value on topmost label'+"\n"
                                        + '    imposition Set the MPLS-EXP value on imposition label'+"\n"
                                        + '    inner      Set the MPLS-EXP value on inner label'
                                          ;
                              type enumeration {
                                enum topmost {
                                  value 1 ;
                                  description 'Set the MPLS-EXP value on topmost label'
                                              ;
                                }
                                enum imposition {
                                  value 2 ;
                                  description 'Set the MPLS-EXP value on imposition label'
                                              ;
                                }
                                enum inner {
                                  value 3 ;
                                  description 'Set the MPLS-EXP value on inner label'
                                              ;
                                }
                              }
                              mandatory true ;
                            }
                          }
                          leaf mpls-exp-value {
                            description 'Reset MPLS-EXP value in violate-action, support <0-7>'
                                        ;
                            type uint8 {
                              range 0..7 {
                                description 'The MPLS-EXP value, support <0-7>'
                                            ;
                              }
                            }
                            mandatory true ;
                          }
                        }
                        case va-precedence {
                          description 'Rewrite packet precedence and transmit t'
                                    + 'he packet'
                                      ;
                          leaf set-prec-transmit {
                            description 'Specify action to rewrite packet precedence and transmit it'
                                        ;
                            type empty ;
                            mandatory true ;
                          }
                          leaf prec-value {
                            description 'Reset the IP-Precedence value in violate-action, support <0-7>'
                                        ;
                            type uint8 {
                              range 0..7 {
                                description 'The IP-Precedence value, support <0-7>'
                                            ;
                              }
                            }
                            mandatory true ;
                          }
                        }
                        case va-dscp {
                          description 'Rewrite packet DSCP and transmit the pac'
                                    + 'ket'
                                      ;
                          leaf set-dscp-transmit {
                            description 'Specify action to rewrite packet DSCP and transmit it'
                                        ;
                            type empty ;
                            mandatory true ;
                          }
                          leaf dscp-value {
                            description 'Reset DSCP in violate-action, support <0-63>'
                                        ;
                            type uint8 {
                              range 0..63 {
                                description 'The DSCP value, support <0-63>'
                                            ;
                              }
                            }
                            mandatory true ;
                          }
                        }
                        case va-8021p {
                          description 'Rewrite packet 802.1p and transmit the p'
                                    + 'acket'
                                      ;
                          leaf set-8021p-transmit {
                            description 'Specify action to rewrite packet 802.1p and transmit it'
                                        ;
                            type empty ;
                            mandatory true ;
                          }
                          leaf value-8021p {
                            description 'Reset 802.1p in violate-action, support <0-7>'
                                        ;
                            type uint8 {
                              range 0..7 {
                                description 'The 802.1p value, support <0-7>'
                                            ;
                              }
                            }
                            mandatory true ;
                          }
                        }
                        case va-multi-exp-transmit {
                          description 'Rewrite packet multi-MPLS-EXP and transm'
                                    + 'it it'
                                      ;
                          leaf set-multi-exp-transmit {
                            description 'Specify action to rewrite packet multi-MPLS-EXP and transmit it'
                                        ;
                            type empty ;
                            mandatory true ;
                          }
                          leaf inner-value {
                            description 'Inner multi-MPLS-EXP value, support <0-7>'
                                        ;
                            type uint8 {
                              range 0..7 {
                                description 'Inner multi-MPLS-EXP value, support <0-7>'
                                            ;
                              }
                            }
                            mandatory true ;
                          }
                          leaf outer-value {
                            description 'Outer multi-MPLS-EXP value, support <0-7>'
                                        ;
                            type uint8 {
                              range 0..7 {
                                description 'Outer multi-MPLS-EXP value, support <0-7>'
                                            ;
                              }
                            }
                            mandatory true ;
                          }
                        }
                        case va-service-class {
                          description 'Specify action to rewrite packet service'
                                    + ' class and transmit it'
                                      ;
                          leaf service-class-value {
                            description 'Reset service class in violate-action'
                                        ;
                            type qos-service-class ;
                            mandatory true ;
                          }
                          ncd:revise-date 2020-06-23 ;
                        }
                      }
                    }
                  }
                  container priority-level {
                    description 'Configure PQ(Priority Queuing) priority level.'
                                ;
                    presence 'Configure PQ priority level'
                             ;
                    leaf priority-value {
                      description 'Set the priority level of PQ, support <1-4>.'
                                  ;
                      type uint16 {
                        range 1..4 {
                          description 'The priority level of PQ, support <1-4>.'
                                      ;
                        }
                      }
                      mandatory true ;
                    }
                    ncd:revise-date 2017-06-12 ;
                  }
                  container priority-llq {
                    description 'Configure LLQ(Low Latency Queuing) priority.'
                                ;
                    presence 'Configure LLQ priority'
                             ;
                    leaf priority-llq {
                      description 'Specify LLQ.'
                                  ;
                      type empty ;
                      mandatory true ;
                    }
                    ncd:revise-date 2017-06-12 ;
                  }
                  container set {
                    description 'Mark a packet'
                                ;
                    container dscp {
                      description 'Select DSCP as mark type'
                                  ;
                      presence 'Select DSCP as mark type'
                               ;
                      container inherit {
                        description 'Set the DSCP value by inheriting'
                                    ;
                        leaf inherit-type {
                          description 'Specify the source inherit type, such as'
                                    + ' precedence, mpls-exp, 8021p, dscp, pay-'
                                    + 'load 8021p'
                                      ;
                          type enumeration {
                            enum precedence {
                              value 1 ;
                              description 'Select precedence as source inherit'
                                          ;
                            }
                            enum mpls-exp {
                              value 2 ;
                              description 'Select MPLS-EXP as source inherit'
                                          ;
                            }
                            enum 8021p {
                              value 3 ;
                              description 'Select 802.1p as source inherit'
                                          ;
                            }
                            enum dscp {
                              value 4 ;
                              description 'Select dscp as source inherit'
                                          ;
                            }
                            enum pay-load-8021p {
                              value 6 ;
                              description 'Select inner 802.1p as source inherit'
                                          ;
                            }
                          }
                          mandatory true ;
                        }
                      }
                    }
                    container precedence {
                      description 'Select precedence as mark type'
                                  ;
                      presence 'Select precedence as mark type'
                               ;
                      container inherit {
                        description 'Set the IP Precedence value by inheriting'
                                    ;
                        leaf inherit-type {
                          description 'Specify the source inherit type, such as'
                                    + ' precedence, mpls-exp, 8021p, dscp'
                                      ;
                          type enumeration {
                            enum precedence {
                              value 1 ;
                              description 'Select precedence as source inherit'
                                          ;
                            }
                            enum mpls-exp {
                              value 2 ;
                              description 'Select MPLS-EXP as source inherit'
                                          ;
                            }
                            enum 8021p {
                              value 3 ;
                              description 'Select 802.1p as source inherit'
                                          ;
                            }
                            enum dscp {
                              value 4 ;
                              description 'Select dscp as source inherit'
                                          ;
                            }
                          }
                          mandatory true ;
                        }
                      }
                    }
                    container pri-8021p {
                      description 'Select 802.1p as mark type'
                                  ;
                      presence 'Select 802.1p as mark type'
                               ;
                      container inherit {
                        description 'Set the 802.1p value by inheriting'
                                    ;
                        leaf inherit-type {
                          description 'Specify the source inherit type, such as'
                                    + ' precedence, mpls-exp, 8021p, dscp'
                                      ;
                          type enumeration {
                            enum precedence {
                              value 1 ;
                              description 'Select precedence as source inherit'
                                          ;
                            }
                            enum mpls-exp {
                              value 2 ;
                              description 'Select MPLS-EXP as source inherit'
                                          ;
                            }
                            enum 8021p {
                              value 3 ;
                              description 'Select 802.1p as source inherit'
                                          ;
                            }
                            enum dscp {
                              value 4 ;
                              description 'Select dscp as source inherit'
                                          ;
                            }
                          }
                          mandatory true ;
                        }
                        leaf inner-outer {
                          description 'Set 8021p inner or outer flag.If vlaue i'
                                    + 's 0, it means outer flag. If value is 1,'
                                    + 'it means inner and outer flag.'
                                      ;
                          type uint8 {
                            range 0..1 {
                              description 'Inner or outer flag. 0 is outer. 1 is inner and outer'
                                          ;
                            }
                          }
                          default 0 ;
                        }
                      }
                    }
                    container mpls-exp {
                      description 'Select MPLS-EXP as mark type'
                                  ;
                      presence 'Select MPLS-EXP as mark type'
                               ;
                      leaf label-type {
                        if-feature policy-action-set-label ;
                        description 'Select MPLS-EXP label position, such as '+"\n"
                                  + '    default    The default for topmost lab'
                                  + 'el'+"\n"
                                  + '    topmost    Set the MPLS-EXP value on t'
                                  + 'opmost label'+"\n"
                                  + '    imposition Set the MPLS-EXP value on a'
                                  + 'll imposed labels'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on all imposed labels'
                                        ;
                          }
                          enum default {
                            value 0 ;
                            description 'The default for topmost label'
                                        ;
                          }
                          enum inner {
                            value 3 ;
                            description 'Set the MPLS-EXP value on inner label'
                                        ;
                          }
                        }
                        mandatory true ;
                      }
                      container inherit {
                        description 'Set the MPLS-EXP value by inheriting'
                                    ;
                        leaf inherit-type {
                          description 'Specify the source inherit type, such as'
                                    + ' precedence, mpls-exp, 8021p, dscp'
                                      ;
                          type enumeration {
                            enum precedence {
                              value 1 ;
                              description 'Select precedence as source inherit'
                                          ;
                            }
                            enum mpls-exp {
                              value 2 ;
                              description 'Select MPLS-EXP as source inherit'
                                          ;
                            }
                            enum 8021p {
                              value 3 ;
                              description 'Select 802.1p as source inherit'
                                          ;
                            }
                            enum dscp {
                              value 4 ;
                              description 'Select dscp as source inherit'
                                          ;
                            }
                          }
                          mandatory true ;
                        }
                      }
                    }
                    container service-class {
                      description 'Configure service class'
                                  ;
                      presence 'Configure service function path'
                               ;
                      leaf service-class {
                        description 'Select service class of PHB info, see belo'
                                  + 'w:'+"\n"
                                  + '  be (1) Best effort'+"\n"
                                  + '  af1(2) Assured forwarding class 1'+"\n"
                                  + '  af2(3) Assured forwarding class 2'+"\n"
                                  + '  af3(4) Assured forwarding class 3'+"\n"
                                  + '  af4(5) Assured forwarding class 4'+"\n"
                                  + '  ef (6) Expedited forward'+"\n"
                                  + '  cs6(7) Internetwork control service clas'
                                  + 's'+"\n"
                                  + '  cs7(8) Network control service class'
                                    ;
                        type qos-service-class ;
                        mandatory true ;
                      }
                      leaf color-type {
                        description 'Specify packets color, support <green,yell'
                                  + 'ow,red>'
                                    ;
                        type qos-color-type ;
                        ncd:revise-date 2021-01-18 ;
                      }
                    }
                    ncd:revise-date 2018-09-19 ;
                  }
                }
                container class-default {
                  description 'Configure the default class'
                              ;
                  presence 'Configure the default class'
                           ;
                  leaf class-default {
                    description 'Specify the default class'
                                ;
                    type empty ;
                    mandatory true ;
                  }
                  container police {
                    description 'Configure traffic policing'
                                ;
                    presence 'Configure traffic policing'
                             ;
                    leaf cir {
                      description 'Configure the CIR(Committed Information Rate'
                                + ') value (default: kilobits per second)'
                                  ;
                      type uint32 {
                        range 8..400000000 {
                          description 'The CIR value (default: kilobits per sec'
                                    + 'ond),support <8-400000000>'
                                      ;
                        }
                      }
                      mandatory true ;
                    }
                    leaf cir-unit {
                      description 'set cir unit, such as kbps, mbps, gbps'
                                  ;
                      type qos-rate-unit-type ;
                    }
                    leaf cbs {
                      description 'Configure the CBS(Committed Burst Size) size'
                                + ' in bytes, support <15000-2000000000>'
                                  ;
                      type uint32 {
                        range 15000..2000000000 {
                          description 'The CBS(Committed Burst Size) size in by'
                                    + 'tes, support <15000-2000000000>'
                                      ;
                        }
                      }
                      units Byte ;
                    }
                    leaf pir {
                      description 'Configure the PIR(Peak Information Rate) val'
                                + 'ue (default: kilobits per second)'
                                  ;
                      type uint32 {
                        range 8..400000000 {
                          description 'The PIR(Peak Information Rate) value (de'
                                    + 'fault: kilobits per second), support <8-'
                                    + '400000000>'
                                      ;
                        }
                      }
                      mandatory true ;
                    }
                    leaf pir-unit {
                      description 'set pir unit, such as kbps, mbps, gbps'
                                  ;
                      type qos-rate-unit-type ;
                    }
                    leaf pbs {
                      description 'Configure the PBS(Peak Burst Size) size in b'
                                + 'ytes, support <15000-2000000000>'
                                  ;
                      type uint32 {
                        range 15000..2000000000 {
                          description 'The PBS(Peak Burst Size) size in bytes, '
                                    + 'support <15000-2000000000>'
                                      ;
                        }
                      }
                      units Byte ;
                    }
                    container conform-action {
                      description 'Action to packets that conform to the rate l'
                                + 'imit'
                                  ;
                      choice conform-action {
                        description 'Specify action to packets that conform to '
                                  + 'the rate limit'
                                    ;
                        mandatory true ;
                        case ca-drop {
                          description 'Drop packet in conform-action'
                                      ;
                          leaf drop {
                            description 'Specify action to drop packet'
                                        ;
                            type empty ;
                            mandatory true ;
                          }
                        }
                        case ca-transmit {
                          description 'Transmit packet in conform-action'
                                      ;
                          leaf transmit {
                            description 'Specify action to transmit packet'
                                        ;
                            type empty ;
                            mandatory true ;
                          }
                        }
                        case ca-mpls-exp {
                          description 'Rewrite packet MPLS-EXP and transmit the'
                                    + ' packet'
                                      ;
                          leaf set-exp-transmit {
                            description 'Specify action to rewrite packet MPLS-EXP and transmit it'
                                        ;
                            type empty ;
                            mandatory true ;
                          }
                          container mpls-label-type {
                            description 'Set MPLS-EXP label type'
                                        ;
                            presence 'Set MPLS-EXP label type'
                                     ;
                            leaf label-type {
                              description 'Set MPLS-EXP label position, such as '+"\n"
                                        + '    topmost    Set the MPLS-EXP value on topmost label'+"\n"
                                        + '    imposition Set the MPLS-EXP value on imposition label'+"\n"
                                        + '    inner      Set the MPLS-EXP value on inner label'
                                          ;
                              type enumeration {
                                enum topmost {
                                  value 1 ;
                                  description 'Set the MPLS-EXP value on topmost label'
                                              ;
                                }
                                enum imposition {
                                  value 2 ;
                                  description 'Set the MPLS-EXP value on imposition label'
                                              ;
                                }
                                enum inner {
                                  value 3 ;
                                  description 'Set the MPLS-EXP value on inner label'
                                              ;
                                }
                              }
                              mandatory true ;
                            }
                          }
                          leaf mpls-exp-value {
                            description 'Reset MPLS-EXP value in conform-action, support <0-7>'
                                        ;
                            type uint8 {
                              range 0..7 {
                                description 'The MPLS-EXP value, support <0-7>'
                                            ;
                              }
                            }
                            mandatory true ;
                          }
                        }
                        case ca-precedence {
                          description 'Rewrite packet precedence and transmit t'
                                    + 'he packet'
                                      ;
                          leaf set-prec-transmit {
                            description 'Specify action to rewrite packet precedence and transmit it'
                                        ;
                            type empty ;
                            mandatory true ;
                          }
                          leaf prec-value {
                            description 'Reset the IP-Precedence value in conform-action, support <0-7>'
                                        ;
                            type uint8 {
                              range 0..7 {
                                description 'The IP-Precedence value, support <0-7>'
                                            ;
                              }
                            }
                            mandatory true ;
                          }
                        }
                        case ca-dscp {
                          description 'Rewrite packet DSCP and transmit the pac'
                                    + 'ket'
                                      ;
                          leaf set-dscp-transmit {
                            description 'Specify action to rewrite packet DSCP and transmit it'
                                        ;
                            type empty ;
                            mandatory true ;
                          }
                          leaf dscp-value {
                            description 'Reset DSCP in conform-action, support <0-63>'
                                        ;
                            type uint8 {
                              range 0..63 {
                                description 'The DSCP value, support <0-63>'
                                            ;
                              }
                            }
                            mandatory true ;
                          }
                        }
                        case ca-8021p {
                          description 'Rewrite packet 802.1p and transmit the p'
                                    + 'acket'
                                      ;
                          leaf set-8021p-transmit {
                            description 'Specify action to rewrite packet 802.1p and transmit it'
                                        ;
                            type empty ;
                            mandatory true ;
                          }
                          leaf value-8021p {
                            description 'Reset 802.1p in conform-action, support <0-7>'
                                        ;
                            type uint8 {
                              range 0..7 {
                                description 'The 802.1p value, support <0-7>'
                                            ;
                              }
                            }
                            mandatory true ;
                          }
                        }
                        case ca-multi-exp-transmit {
                          description 'Rewrite packet multi-MPLS-EXP and transm'
                                    + 'it it'
                                      ;
                          leaf set-multi-exp-transmit {
                            description 'Specify action to rewrite packet multi-MPLS-EXP and transmit it'
                                        ;
                            type empty ;
                            mandatory true ;
                          }
                          leaf inner-value {
                            description 'Inner multi-MPLS-EXP value, support <0-7>'
                                        ;
                            type uint8 {
                              range 0..7 {
                                description 'Inner multi-MPLS-EXP value, support <0-7>'
                                            ;
                              }
                            }
                            mandatory true ;
                          }
                          leaf outer-value {
                            description 'Outer multi-MPLS-EXP value, support <0-7>'
                                        ;
                            type uint8 {
                              range 0..7 {
                                description 'Outer multi-MPLS-EXP value, support <0-7>'
                                            ;
                              }
                            }
                            mandatory true ;
                          }
                        }
                        case ca-service-class {
                          description 'Specify action to rewrite packet service'
                                    + '-class and transmit it'
                                      ;
                          leaf service-class-value {
                            description 'Reset service class in conform-action'
                                        ;
                            type qos-service-class ;
                            mandatory true ;
                          }
                          ncd:revise-date 2020-06-23 ;
                        }
                      }
                    }
                    container exceed-action {
                      description 'Action to packets that exceed the rate limit'
                                  ;
                      choice exceed-action {
                        description 'Specify action to packets that exceed the '
                                  + 'rate limit'
                                    ;
                        mandatory true ;
                        case ea-drop {
                          description 'Drop packet in exceed-action'
                                      ;
                          leaf drop {
                            description 'Specify action to drop packet'
                                        ;
                            type empty ;
                            mandatory true ;
                          }
                        }
                        case ea-transmit {
                          description 'Transmit packet in exceed-action'
                                      ;
                          leaf transmit {
                            description 'Specify action to transmit packet'
                                        ;
                            type empty ;
                            mandatory true ;
                          }
                        }
                        case ea-mpls-exp {
                          description 'Rewrite packet MPLS-EXP and transmit the'
                                    + ' packet'
                                      ;
                          leaf set-exp-transmit {
                            description 'Specify action to rewrite packet MPLS-EXP and transmit it'
                                        ;
                            type empty ;
                            mandatory true ;
                          }
                          container mpls-label-type {
                            description 'Set MPLS-EXP label type'
                                        ;
                            presence 'Set MPLS-EXP label type'
                                     ;
                            leaf label-type {
                              description 'Set MPLS-EXP label position, such as '+"\n"
                                        + '    topmost    Set the MPLS-EXP value on topmost label'+"\n"
                                        + '    imposition Set the MPLS-EXP value on imposition label'+"\n"
                                        + '    inner      Set the MPLS-EXP value on inner label'
                                          ;
                              type enumeration {
                                enum topmost {
                                  value 1 ;
                                  description 'Set the MPLS-EXP value on topmost label'
                                              ;
                                }
                                enum imposition {
                                  value 2 ;
                                  description 'Set the MPLS-EXP value on imposition label'
                                              ;
                                }
                                enum inner {
                                  value 3 ;
                                  description 'Set the MPLS-EXP value on inner label'
                                              ;
                                }
                              }
                              mandatory true ;
                            }
                          }
                          leaf mpls-exp-value {
                            description 'Reset MPLS-EXP value in exceed-action, support <0-7>'
                                        ;
                            type uint8 {
                              range 0..7 {
                                description 'The MPLS-EXP value, support <0-7>'
                                            ;
                              }
                            }
                            mandatory true ;
                          }
                        }
                        case ea-precedence {
                          description 'Rewrite packet precedence and transmit t'
                                    + 'he packet'
                                      ;
                          leaf set-prec-transmit {
                            description 'Specify action to rewrite packet precedence and transmit it'
                                        ;
                            type empty ;
                            mandatory true ;
                          }
                          leaf prec-value {
                            description 'Reset the IP-Precedence value in exceed-action, support <0-7>'
                                        ;
                            type uint8 {
                              range 0..7 {
                                description 'The IP-Precedence value, support <0-7>'
                                            ;
                              }
                            }
                            mandatory true ;
                          }
                        }
                        case ea-dscp {
                          description 'Rewrite packet DSCP and transmit the pac'
                                    + 'ket'
                                      ;
                          leaf set-dscp-transmit {
                            description 'Specify action to rewrite packet DSCP and transmit it'
                                        ;
                            type empty ;
                            mandatory true ;
                          }
                          leaf dscp-value {
                            description 'Reset DSCP in exceed-action, support <0-63>'
                                        ;
                            type uint8 {
                              range 0..63 {
                                description 'The DSCP value, support <0-63>'
                                            ;
                              }
                            }
                            mandatory true ;
                          }
                        }
                        case ea-8021p {
                          description 'Rewrite packet 802.1p and transmit the p'
                                    + 'acket'
                                      ;
                          leaf set-8021p-transmit {
                            description 'Specify action to rewrite packet 802.1p and transmit it'
                                        ;
                            type empty ;
                            mandatory true ;
                          }
                          leaf value-8021p {
                            description 'Reset 802.1p in exceed-action, support <0-7>'
                                        ;
                            type uint8 {
                              range 0..7 {
                                description 'The 802.1p value, support <0-7>'
                                            ;
                              }
                            }
                            mandatory true ;
                          }
                        }
                        case ea-multi-exp-transmit {
                          description 'Rewrite packet multi-MPLS-EXP and transm'
                                    + 'it it'
                                      ;
                          leaf set-multi-exp-transmit {
                            description 'Specify action to rewrite packet multi-MPLS-EXP and transmit it'
                                        ;
                            type empty ;
                            mandatory true ;
                          }
                          leaf inner-value {
                            description 'Inner multi-MPLS-EXP value, support <0-7>'
                                        ;
                            type uint8 {
                              range 0..7 {
                                description 'Inner multi-MPLS-EXP value, support <0-7>'
                                            ;
                              }
                            }
                            mandatory true ;
                          }
                          leaf outer-value {
                            description 'Outer multi-MPLS-EXP value, support <0-7>'
                                        ;
                            type uint8 {
                              range 0..7 {
                                description 'Outer multi-MPLS-EXP value, support <0-7>'
                                            ;
                              }
                            }
                            mandatory true ;
                          }
                        }
                        case ea-service-class {
                          description 'Specify action to rewrite packet service'
                                    + ' class and transmit it'
                                      ;
                          leaf service-class-value {
                            description 'Reset service class in exceed-action'
                                        ;
                            type qos-service-class ;
                            mandatory true ;
                          }
                          ncd:revise-date 2020-06-23 ;
                        }
                      }
                    }
                    container violate-action {
                      description 'Action to packets that violate the rate limit'
                                  ;
                      choice violate-action {
                        description 'Specify action to packets that violate the'
                                  + ' rate limit'
                                    ;
                        mandatory true ;
                        case va-drop {
                          description 'Drop packet in violate-action'
                                      ;
                          leaf drop {
                            description 'Specify action to drop packet'
                                        ;
                            type empty ;
                            mandatory true ;
                          }
                        }
                        case va-transmit {
                          description 'Transmit packet in violate-action'
                                      ;
                          leaf transmit {
                            description 'Specify action to transmit packet'
                                        ;
                            type empty ;
                            mandatory true ;
                          }
                        }
                        case va-mpls-exp {
                          description 'Rewrite packet MPLS-EXP and transmit the'
                                    + ' packet'
                                      ;
                          leaf set-exp-transmit {
                            description 'Specify action to rewrite packet MPLS-EXP and transmit it'
                                        ;
                            type empty ;
                            mandatory true ;
                          }
                          container mpls-label-type {
                            description 'Set MPLS-EXP label type'
                                        ;
                            presence 'Set MPLS-EXP label type'
                                     ;
                            leaf label-type {
                              description 'Set MPLS-EXP label position, such as '+"\n"
                                        + '    topmost    Set the MPLS-EXP value on topmost label'+"\n"
                                        + '    imposition Set the MPLS-EXP value on imposition label'+"\n"
                                        + '    inner      Set the MPLS-EXP value on inner label'
                                          ;
                              type enumeration {
                                enum topmost {
                                  value 1 ;
                                  description 'Set the MPLS-EXP value on topmost label'
                                              ;
                                }
                                enum imposition {
                                  value 2 ;
                                  description 'Set the MPLS-EXP value on imposition label'
                                              ;
                                }
                                enum inner {
                                  value 3 ;
                                  description 'Set the MPLS-EXP value on inner label'
                                              ;
                                }
                              }
                              mandatory true ;
                            }
                          }
                          leaf mpls-exp-value {
                            description 'Reset MPLS-EXP value in violate-action, support <0-7>'
                                        ;
                            type uint8 {
                              range 0..7 {
                                description 'The MPLS-EXP value, support <0-7>'
                                            ;
                              }
                            }
                            mandatory true ;
                          }
                        }
                        case va-precedence {
                          description 'Rewrite packet precedence and transmit t'
                                    + 'he packet'
                                      ;
                          leaf set-prec-transmit {
                            description 'Specify action to rewrite packet precedence and transmit it'
                                        ;
                            type empty ;
                            mandatory true ;
                          }
                          leaf prec-value {
                            description 'Reset the IP-Precedence value in violate-action, support <0-7>'
                                        ;
                            type uint8 {
                              range 0..7 {
                                description 'The IP-Precedence value, support <0-7>'
                                            ;
                              }
                            }
                            mandatory true ;
                          }
                        }
                        case va-dscp {
                          description 'Rewrite packet DSCP and transmit the pac'
                                    + 'ket'
                                      ;
                          leaf set-dscp-transmit {
                            description 'Specify action to rewrite packet DSCP and transmit it'
                                        ;
                            type empty ;
                            mandatory true ;
                          }
                          leaf dscp-value {
                            description 'Reset DSCP in violate-action, support <0-63>'
                                        ;
                            type uint8 {
                              range 0..63 {
                                description 'The DSCP value, support <0-63>'
                                            ;
                              }
                            }
                            mandatory true ;
                          }
                        }
                        case va-8021p {
                          description 'Rewrite packet 802.1p and transmit the p'
                                    + 'acket'
                                      ;
                          leaf set-8021p-transmit {
                            description 'Specify action to rewrite packet 802.1p and transmit it'
                                        ;
                            type empty ;
                            mandatory true ;
                          }
                          leaf value-8021p {
                            description 'Reset 802.1p in violate-action, support <0-7>'
                                        ;
                            type uint8 {
                              range 0..7 {
                                description 'The 802.1p value, support <0-7>'
                                            ;
                              }
                            }
                            mandatory true ;
                          }
                        }
                        case va-multi-exp-transmit {
                          description 'Rewrite packet multi-MPLS-EXP and transm'
                                    + 'it it'
                                      ;
                          leaf set-multi-exp-transmit {
                            description 'Specify action to rewrite packet multi-MPLS-EXP and transmit it'
                                        ;
                            type empty ;
                            mandatory true ;
                          }
                          leaf inner-value {
                            description 'Inner multi-MPLS-EXP value, support <0-7>'
                                        ;
                            type uint8 {
                              range 0..7 {
                                description 'Inner multi-MPLS-EXP value, support <0-7>'
                                            ;
                              }
                            }
                            mandatory true ;
                          }
                          leaf outer-value {
                            description 'Outer multi-MPLS-EXP value, support <0-7>'
                                        ;
                            type uint8 {
                              range 0..7 {
                                description 'Outer multi-MPLS-EXP value, support <0-7>'
                                            ;
                              }
                            }
                            mandatory true ;
                          }
                        }
                        case va-service-class {
                          description 'Specify action to rewrite packet service'
                                    + ' class and transmit it'
                                      ;
                          leaf service-class-value {
                            description 'Reset service class in violate-action'
                                        ;
                            type qos-service-class ;
                            mandatory true ;
                          }
                          ncd:revise-date 2020-06-23 ;
                        }
                      }
                    }
                  }
                  container priority-level {
                    description 'Configure PQ(Priority Queuing) priority level.'
                                ;
                    presence 'Configure PQ priority level'
                             ;
                    leaf priority-value {
                      description 'Set the priority level of PQ, support <1-4>.'
                                  ;
                      type uint16 {
                        range 1..4 {
                          description 'The priority level of PQ, support <1-4>.'
                                      ;
                        }
                      }
                      mandatory true ;
                    }
                    ncd:revise-date 2017-06-12 ;
                  }
                  container priority-llq {
                    description 'Configure LLQ(Low Latency Queuing) priority.'
                                ;
                    presence 'Configure LLQ priority'
                             ;
                    leaf priority-llq {
                      description 'Specify LLQ.'
                                  ;
                      type empty ;
                      mandatory true ;
                    }
                    ncd:revise-date 2017-06-12 ;
                  }
                  container set {
                    description 'Mark a packet'
                                ;
                    container dscp {
                      description 'Select DSCP as mark type'
                                  ;
                      presence 'Select DSCP as mark type'
                               ;
                      container inherit {
                        description 'Set the DSCP value by inheriting'
                                    ;
                        leaf inherit-type {
                          description 'Specify the source inherit type, such as'
                                    + ' precedence, mpls-exp, 8021p, dscp, pay-'
                                    + 'load 8021p'
                                      ;
                          type enumeration {
                            enum precedence {
                              value 1 ;
                              description 'Select precedence as source inherit'
                                          ;
                            }
                            enum mpls-exp {
                              value 2 ;
                              description 'Select MPLS-EXP as source inherit'
                                          ;
                            }
                            enum 8021p {
                              value 3 ;
                              description 'Select 802.1p as source inherit'
                                          ;
                            }
                            enum dscp {
                              value 4 ;
                              description 'Select dscp as source inherit'
                                          ;
                            }
                            enum pay-load-8021p {
                              value 6 ;
                              description 'Select inner 802.1p as source inherit'
                                          ;
                            }
                          }
                          mandatory true ;
                        }
                      }
                    }
                    container precedence {
                      description 'Select precedence as mark type'
                                  ;
                      presence 'Select precedence as mark type'
                               ;
                      container inherit {
                        description 'Set the IP Precedence value by inheriting'
                                    ;
                        leaf inherit-type {
                          description 'Specify the source inherit type, such as'
                                    + ' precedence, mpls-exp, 8021p, dscp'
                                      ;
                          type enumeration {
                            enum precedence {
                              value 1 ;
                              description 'Select precedence as source inherit'
                                          ;
                            }
                            enum mpls-exp {
                              value 2 ;
                              description 'Select MPLS-EXP as source inherit'
                                          ;
                            }
                            enum 8021p {
                              value 3 ;
                              description 'Select 802.1p as source inherit'
                                          ;
                            }
                            enum dscp {
                              value 4 ;
                              description 'Select dscp as source inherit'
                                          ;
                            }
                          }
                          mandatory true ;
                        }
                      }
                    }
                    container pri-8021p {
                      description 'Select 802.1p as mark type'
                                  ;
                      presence 'Select 802.1p as mark type'
                               ;
                      container inherit {
                        description 'Set the 802.1p value by inheriting'
                                    ;
                        leaf inherit-type {
                          description 'Specify the source inherit type, such as'
                                    + ' precedence, mpls-exp, 8021p, dscp'
                                      ;
                          type enumeration {
                            enum precedence {
                              value 1 ;
                              description 'Select precedence as source inherit'
                                          ;
                            }
                            enum mpls-exp {
                              value 2 ;
                              description 'Select MPLS-EXP as source inherit'
                                          ;
                            }
                            enum 8021p {
                              value 3 ;
                              description 'Select 802.1p as source inherit'
                                          ;
                            }
                            enum dscp {
                              value 4 ;
                              description 'Select dscp as source inherit'
                                          ;
                            }
                          }
                          mandatory true ;
                        }
                        leaf inner-outer {
                          description 'Set 8021p inner or outer flag.If vlaue i'
                                    + 's 0, it means outer flag. If value is 1,'
                                    + 'it means inner and outer flag.'
                                      ;
                          type uint8 {
                            range 0..1 {
                              description 'Inner or outer flag. 0 is outer. 1 is inner and outer'
                                          ;
                            }
                          }
                          default 0 ;
                        }
                      }
                    }
                    container mpls-exp {
                      description 'Select MPLS-EXP as mark type'
                                  ;
                      presence 'Select MPLS-EXP as mark type'
                               ;
                      leaf label-type {
                        if-feature policy-action-set-label ;
                        description 'Select MPLS-EXP label position, such as '+"\n"
                                  + '    default    The default for topmost lab'
                                  + 'el'+"\n"
                                  + '    topmost    Set the MPLS-EXP value on t'
                                  + 'opmost label'+"\n"
                                  + '    imposition Set the MPLS-EXP value on a'
                                  + 'll imposed labels'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on all imposed labels'
                                        ;
                          }
                          enum default {
                            value 0 ;
                            description 'The default for topmost label'
                                        ;
                          }
                          enum inner {
                            value 3 ;
                            description 'Set the MPLS-EXP value on inner label'
                                        ;
                          }
                        }
                        mandatory true ;
                      }
                      container inherit {
                        description 'Set the MPLS-EXP value by inheriting'
                                    ;
                        leaf inherit-type {
                          description 'Specify the source inherit type, such as'
                                    + ' precedence, mpls-exp, 8021p, dscp'
                                      ;
                          type enumeration {
                            enum precedence {
                              value 1 ;
                              description 'Select precedence as source inherit'
                                          ;
                            }
                            enum mpls-exp {
                              value 2 ;
                              description 'Select MPLS-EXP as source inherit'
                                          ;
                            }
                            enum 8021p {
                              value 3 ;
                              description 'Select 802.1p as source inherit'
                                          ;
                            }
                            enum dscp {
                              value 4 ;
                              description 'Select dscp as source inherit'
                                          ;
                            }
                          }
                          mandatory true ;
                        }
                      }
                    }
                    container service-class {
                      description 'Configure service class'
                                  ;
                      presence 'Configure service function path'
                               ;
                      leaf service-class {
                        description 'Select service class of PHB info, see belo'
                                  + 'w:'+"\n"
                                  + '  be (1) Best effort'+"\n"
                                  + '  af1(2) Assured forwarding class 1'+"\n"
                                  + '  af2(3) Assured forwarding class 2'+"\n"
                                  + '  af3(4) Assured forwarding class 3'+"\n"
                                  + '  af4(5) Assured forwarding class 4'+"\n"
                                  + '  ef (6) Expedited forward'+"\n"
                                  + '  cs6(7) Internetwork control service clas'
                                  + 's'+"\n"
                                  + '  cs7(8) Network control service class'
                                    ;
                        type qos-service-class ;
                        mandatory true ;
                      }
                      leaf color-type {
                        description 'Specify packets color, support <green,yell'
                                  + 'ow,red>'
                                    ;
                        type qos-color-type ;
                        ncd:revise-date 2021-01-18 ;
                      }
                    }
                    ncd:revise-date 2018-09-19 ;
                  }
                }
              }
            }
          }
        }
        container phb-based {
          if-feature phb-mode ;
          description 'Policy map based on phb'
                      ;
          container policy-maps {
            description 'Configure H-QoS policy map lists'
                        ;
            list policy-map {
              description 'Configure H-QoS policy maps'
                          ;
              key pmap-name ;
              leaf pmap-name {
                description 'Name of the policy map, support 1-31 characters'
                            ;
                type string {
                  length 1..31 {
                    description 'Name of the policy map, support 1-31 characters'
                                ;
                  }
                }
              }
              container class-maps {
                description 'Configure H-QoS policy class'
                            ;
                list class-map {
                  description 'Configure H-QoS policy class'
                              ;
                  key cmap-name ;
                  leaf cmap-name {
                    description 'Name of the class map, support 1-31 characters'
                                ;
                    type string {
                      length 1..31 ;
                    }
                  }
                  container bandwidth {
                    description 'Configure minimum guaranteed bandwidth'
                                ;
                    presence 'Configure minimum guaranteed bandwidth'
                             ;
                    leaf percentage {
                      description 'Set the exact bandwidth percentage, support '
                                + '<1-100>'
                                  ;
                      type uint16 {
                        range 1..100 {
                          description 'The exact bandwidth percentage, support '
                                    + '<1-100>'
                                      ;
                        }
                      }
                      mandatory true ;
                    }
                  }
                  container priority-level {
                    description 'Configure PQ(Priority Queuing) priority level'
                                ;
                    presence 'Configure PQ priority level'
                             ;
                    leaf priority-value {
                      description 'Set the priority level of PQ, support <1-4>'
                                  ;
                      type uint16 {
                        range 1..4 {
                          description 'The priority level of PQ, support <1-4>'
                                      ;
                        }
                      }
                      mandatory true ;
                    }
                  }
                  container priority-llq {
                    description 'Configure LLQ(Low Latency Queuing) priority'
                                ;
                    presence 'Configure LLQ priority'
                             ;
                    leaf priority-llq {
                      description 'Specify LLQ'
                                  ;
                      type empty ;
                      mandatory true ;
                    }
                  }
                  container police {
                    description 'Configure traffic policing'
                                ;
                    presence 'Configure traffic policing'
                             ;
                    leaf cir {
                      description 'Configure the CIR(Committed Information Rate'
                                + ') value (default: kilobits per second)'
                                  ;
                      type uint32 {
                        range 8..4294967295 {
                          description 'The CIR value (default: kilobits per sec'
                                    + 'ond), support <8-4294967295>'
                                      ;
                        }
                      }
                      mandatory true ;
                    }
                    leaf cir-unit {
                      description 'set cir unit, such as kbps, mbps, gbps'
                                  ;
                      type qos-rate-unit-type ;
                    }
                    leaf cbs {
                      description 'Configure the CBS(Committed Burst Size) size'
                                + ' (default: KB)'
                                  ;
                      type uint32 {
                        range 1..4294967295 {
                          description 'The CBS(Committed Burst Size) size (defa'
                                    + 'ult: KB), support <1-4294967295>'
                                      ;
                        }
                      }
                    }
                    leaf cbs-unit {
                      description 'set cbs unit, such as kb, mb, gb'
                                  ;
                      type qos-bucket-unit-type ;
                    }
                    container pir-pbs {
                      description 'Configure PIR and PBS'
                                  ;
                      presence 'Configure pir and pbs'
                               ;
                      leaf pir {
                        description 'Configure the PIR(Peak Information Rate) v'
                                  + 'alue (default: kilobits per second)'
                                    ;
                        type uint32 {
                          range 8..4294967295 {
                            description 'The PIR(Peak Information Rate) value (default: kilobits per second), support <'
                                      + '8-4294967295>'
                                        ;
                          }
                        }
                        mandatory true ;
                      }
                      leaf pir-unit {
                        description 'set pir unit, such as kbps, mbps, gbps'
                                    ;
                        type qos-rate-unit-type ;
                      }
                      leaf pbs {
                        description 'Configure the PBS(Peak Burst Size) size (d'
                                  + 'efault: KB)'
                                    ;
                        type uint32 {
                          range 1..4294967295 {
                            description 'The PBS(Peak Burst Size) size (default: KB), support <1-4294967295>'
                                        ;
                          }
                        }
                      }
                      leaf pbs-unit {
                        description 'set pbs unit, such as kb, mb, gb'
                                    ;
                        type qos-bucket-unit-type ;
                      }
                    }
                  }
                  container random-detect {
                    description 'Configure WRED(Weighted Random Early Detection'
                              + ') information'
                                ;
                    container enable {
                      description 'Configure WRED enable'
                                  ;
                      presence 'Configure WRED enable'
                               ;
                      leaf enable {
                        description 'Specify WRED enable'
                                    ;
                        type empty ;
                        mandatory true ;
                      }
                    }
                    container colors {
                      description 'Configure WRED thresholds based on color'
                                  ;
                      list color {
                        description 'Configure WRED thresholds based on color'
                                    ;
                        key color-type ;
                        leaf color-type {
                          description 'set WRED color, such as green, yellow, r'
                                    + 'ed'
                                      ;
                          type qos-color-type ;
                        }
                        leaf min-threshold {
                          status obsolete {
                            ncd:revise-date 2019-08-05 ;
                          }
                          description 'Set the minimum threshold in percent, su'
                                    + 'pport <1-100>'
                                      ;
                          type uint32 {
                            range 1..100 {
                              description 'The minimum threshold in percent, support <1-100>'
                                          ;
                            }
                          }
                          mandatory true ;
                        }
                        leaf max-threshold {
                          status obsolete {
                            ncd:revise-date 2019-08-05 ;
                          }
                          description 'Set the maximum threshold in percent, su'
                                    + 'pport <1-100>'
                                      ;
                          type uint32 {
                            range 1..100 {
                              description 'The maximum threshold in percent, support <1-100>'
                                          ;
                            }
                          }
                          mandatory true ;
                        }
                        choice threshold {
                          description 'Set the threshold'
                                      ;
                          case threshold-value {
                            description 'Set the threshold value'
                                        ;
                            leaf min-threshold-value {
                              description 'Set the minimum threshold in kilobytes, support <1-1024000>'
                                          ;
                              type uint32 {
                                range 1..1024000 {
                                  description 'The minimum threshold in kilobytes, support <1-1024000>'
                                              ;
                                }
                              }
                              units KB ;
                              mandatory true ;
                            }
                            leaf max-threshold-value {
                              description 'Set the maximum threshold in kilobytes, support <1-1024000>'
                                          ;
                              type uint32 {
                                range 1..1024000 {
                                  description 'The maximum threshold in kilobytes, support <1-1024000>'
                                              ;
                                }
                              }
                              units KB ;
                              mandatory true ;
                            }
                            ncd:revise-date 2021-01-18 ;
                          }
                          case threshold-percentage {
                            description 'Set the threshold percentage'
                                        ;
                            container threshold-percentage {
                              description 'Set the threshold percentage'
                                          ;
                              leaf min-threshold-percentage {
                                description 'Set the minimum threshold percentage, support <1-100>'
                                            ;
                                type uint32 {
                                  range 1..100 {
                                    description 'The minimum threshold percentage, support <1-100>'
                                                ;
                                  }
                                }
                                mandatory true ;
                              }
                              leaf max-threshold-percentage {
                                description 'Set the maximum threshold percentage, support <1-100>'
                                            ;
                                type uint32 {
                                  range 1..100 {
                                    description 'The maximum threshold percentage, support <1-100>'
                                                ;
                                  }
                                }
                                mandatory true ;
                              }
                            }
                            ncd:revise-date 2019-08-05 ;
                          }
                          ncd:revise-date 2019-08-05 ;
                        }
                        leaf probability {
                          description 'Set mark probability denominator, suppor'
                                    + 't <1-100>'
                                      ;
                          type uint8 {
                            range 1..100 {
                              description 'Set mark probability denominator, support <1-100>'
                                          ;
                            }
                          }
                          mandatory true ;
                        }
                      }
                    }
                    container precedences {
                      description 'Configure WRED thresholds based on precedence'
                                  ;
                      list precedence {
                        description 'Configure WRED thresholds based on precede'
                                  + 'nce'
                                    ;
                        key prec-value ;
                        leaf prec-value {
                          description 'Set the precedence value, such as MPLS E'
                                    + 'XP, VLAN 802.1p, IP DSCP, IP Precedence,'
                                    + ' support <0-7>'
                                      ;
                          type uint16 {
                            range 0..7 {
                              description 'The IP-Precedence value, support <0-7>'
                                          ;
                            }
                          }
                        }
                        choice threshold {
                          description 'Set the threshold'
                                      ;
                          case threshold-value {
                            description 'Set the threshold value'
                                        ;
                            leaf min-threshold {
                              description 'Set the minimum threshold (default: kilobytes)'
                                          ;
                              type uint32 {
                                range 1..4294967295 {
                                  description 'The minimum threshold (default: kilobytes), support <1-4294967295>'
                                              ;
                                }
                              }
                              mandatory true ;
                            }
                            leaf min-threshold-unit {
                              description 'set min-threshold unit, such as kbytes, mbytes, gbytes'
                                          ;
                              type qos-threshold-unit-type ;
                            }
                            leaf max-threshold {
                              description 'Set the maximum threshold (default: kilobytes)'
                                          ;
                              type uint32 {
                                range 1..4294967295 {
                                  description 'The maximum threshold (default: kilobytes), support <1-4294967295>.'
                                              ;
                                }
                              }
                              mandatory true ;
                            }
                            leaf max-threshold-unit {
                              description 'set max-threshold unit, such as kbytes, mbytes, gbytes'
                                          ;
                              type qos-threshold-unit-type ;
                            }
                          }
                          case threshold-percentage {
                            description 'Set the threshold percentage'
                                        ;
                            container threshold-percentage {
                              description 'Set the threshold percentage'
                                          ;
                              leaf min-threshold-percentage {
                                description 'Set the minimum threshold percentage, support <1-100>'
                                            ;
                                type uint32 {
                                  range 1..100 {
                                    description 'The minimum threshold percentage, support <1-100>'
                                                ;
                                  }
                                }
                                mandatory true ;
                              }
                              leaf max-threshold-percentage {
                                description 'Set the maximum threshold percentage, support <1-100>'
                                            ;
                                type uint32 {
                                  range 1..100 {
                                    description 'The maximum threshold percentage, support <1-100>'
                                                ;
                                  }
                                }
                                mandatory true ;
                              }
                            }
                          }
                        }
                        leaf probability {
                          description 'Set mark probability denominator, suppor'
                                    + 't <1-100>'
                                      ;
                          type uint32 {
                            range 1..100 {
                              description 'Set mark probability denominator, support <1-100>'
                                          ;
                            }
                          }
                          mandatory true ;
                        }
                      }
                      ncd:revise-date 2021-01-18 ;
                    }
                    container weight {
                      description 'Configure WRED exponential weight factor'
                                  ;
                      presence 'Configure WRED exponential weight factor'
                               ;
                      leaf weight-value {
                        description 'Specify exponent used in weighted average '
                                  + 'calculation, support <1-16>'
                                    ;
                        type uint16 {
                          range 1..16 {
                            description 'Exponent used in weighted average calculation'
                                        ;
                          }
                        }
                        mandatory true ;
                      }
                      ncd:revise-date 2021-01-18 ;
                    }
                    ncd:revise-date 2018-08-18 ;
                  }
                  container service-policy {
                    description 'Configure hierarchical service policy'
                                ;
                    presence 'Configure hierarchical service policy'
                             ;
                    leaf hpolicy-name {
                      description 'Name of the hierarchical policy, support 1-3'
                                + '1 characters'
                                  ;
                      type string {
                        length 1..31 {
                          description 'Name of the hierarchical policy, support'
                                    + ' 1-31 characters'
                                      ;
                        }
                      }
                      mandatory true ;
                    }
                    ncd:revise-date 2021-01-11 ;
                  }
                }
                container class-default {
                  description 'Select the default class'
                              ;
                  presence 'Specify the default class'
                           ;
                  leaf class-default {
                    description 'Specify the default class'
                                ;
                    type empty ;
                    mandatory true ;
                  }
                  container bandwidth {
                    description 'Configure minimum guaranteed bandwidth'
                                ;
                    presence 'Configure minimum guaranteed bandwidth'
                             ;
                    leaf percentage {
                      description 'Set the exact bandwidth percentage, support '
                                + '<1-100>'
                                  ;
                      type uint16 {
                        range 1..100 {
                          description 'The exact bandwidth percentage, support '
                                    + '<1-100>'
                                      ;
                        }
                      }
                      mandatory true ;
                    }
                  }
                  container priority-level {
                    description 'Configure PQ(Priority Queuing) priority level'
                                ;
                    presence 'Configure PQ priority level'
                             ;
                    leaf priority-value {
                      description 'Set the priority level of PQ, support <1-4>'
                                  ;
                      type uint16 {
                        range 1..4 {
                          description 'The priority level of PQ, support <1-4>'
                                      ;
                        }
                      }
                      mandatory true ;
                    }
                  }
                  container priority-llq {
                    description 'Configure LLQ(Low Latency Queuing) priority'
                                ;
                    presence 'Configure LLQ priority'
                             ;
                    leaf priority-llq {
                      description 'Specify LLQ'
                                  ;
                      type empty ;
                      mandatory true ;
                    }
                  }
                  container police {
                    description 'Configure traffic policing'
                                ;
                    presence 'Configure traffic policing'
                             ;
                    leaf cir {
                      description 'Configure the CIR(Committed Information Rate'
                                + ') value (default: kilobits per second)'
                                  ;
                      type uint32 {
                        range 8..4294967295 {
                          description 'The CIR value (default: kilobits per sec'
                                    + 'ond), support <8-4294967295>'
                                      ;
                        }
                      }
                      mandatory true ;
                    }
                    leaf cir-unit {
                      description 'set cir unit, such as kbps, mbps, gbps'
                                  ;
                      type qos-rate-unit-type ;
                    }
                    leaf cbs {
                      description 'Configure the CBS(Committed Burst Size) size'
                                + ' (default: KB)'
                                  ;
                      type uint32 {
                        range 1..4294967295 {
                          description 'The CBS(Committed Burst Size) size (defa'
                                    + 'ult: KB), support <1-4294967295>'
                                      ;
                        }
                      }
                    }
                    leaf cbs-unit {
                      description 'set cbs unit, such as kb, mb, gb'
                                  ;
                      type qos-bucket-unit-type ;
                    }
                    container pir-pbs {
                      description 'Configure PIR and PBS'
                                  ;
                      presence 'Configure pir and pbs'
                               ;
                      leaf pir {
                        description 'Configure the PIR(Peak Information Rate) v'
                                  + 'alue (default: kilobits per second)'
                                    ;
                        type uint32 {
                          range 8..4294967295 {
                            description 'The PIR(Peak Information Rate) value (default: kilobits per second), support <'
                                      + '8-4294967295>'
                                        ;
                          }
                        }
                        mandatory true ;
                      }
                      leaf pir-unit {
                        description 'set pir unit, such as kbps, mbps, gbps'
                                    ;
                        type qos-rate-unit-type ;
                      }
                      leaf pbs {
                        description 'Configure the PBS(Peak Burst Size) size (d'
                                  + 'efault: KB)'
                                    ;
                        type uint32 {
                          range 1..4294967295 {
                            description 'The PBS(Peak Burst Size) size (default: KB), support <1-4294967295>'
                                        ;
                          }
                        }
                      }
                      leaf pbs-unit {
                        description 'set pbs unit, such as kb, mb, gb'
                                    ;
                        type qos-bucket-unit-type ;
                      }
                    }
                  }
                  container random-detect {
                    description 'Configure WRED(Weighted Random Early Detection'
                              + ') information'
                                ;
                    container enable {
                      description 'Configure WRED enable'
                                  ;
                      presence 'Configure WRED enable'
                               ;
                      leaf enable {
                        description 'Specify WRED enable'
                                    ;
                        type empty ;
                        mandatory true ;
                      }
                    }
                    container colors {
                      description 'Configure WRED thresholds based on color'
                                  ;
                      list color {
                        description 'Configure WRED thresholds based on color'
                                    ;
                        key color-type ;
                        leaf color-type {
                          description 'set WRED color, such as green, yellow, r'
                                    + 'ed'
                                      ;
                          type qos-color-type ;
                        }
                        leaf min-threshold {
                          status obsolete {
                            ncd:revise-date 2019-08-05 ;
                          }
                          description 'Set the minimum threshold in percent, su'
                                    + 'pport <1-100>'
                                      ;
                          type uint32 {
                            range 1..100 {
                              description 'The minimum threshold in percent, support <1-100>'
                                          ;
                            }
                          }
                          mandatory true ;
                        }
                        leaf max-threshold {
                          status obsolete {
                            ncd:revise-date 2019-08-05 ;
                          }
                          description 'Set the maximum threshold in percent, su'
                                    + 'pport <1-100>'
                                      ;
                          type uint32 {
                            range 1..100 {
                              description 'The maximum threshold in percent, support <1-100>'
                                          ;
                            }
                          }
                          mandatory true ;
                        }
                        choice threshold {
                          description 'Set the threshold'
                                      ;
                          case threshold-value {
                            description 'Set the threshold value'
                                        ;
                            leaf min-threshold-value {
                              description 'Set the minimum threshold in kilobytes, support <1-1024000>'
                                          ;
                              type uint32 {
                                range 1..1024000 {
                                  description 'The minimum threshold in kilobytes, support <1-1024000>'
                                              ;
                                }
                              }
                              units KB ;
                              mandatory true ;
                            }
                            leaf max-threshold-value {
                              description 'Set the maximum threshold in kilobytes, support <1-1024000>'
                                          ;
                              type uint32 {
                                range 1..1024000 {
                                  description 'The maximum threshold in kilobytes, support <1-1024000>'
                                              ;
                                }
                              }
                              units KB ;
                              mandatory true ;
                            }
                            ncd:revise-date 2021-01-18 ;
                          }
                          case threshold-percentage {
                            description 'Set the threshold percentage'
                                        ;
                            container threshold-percentage {
                              description 'Set the threshold percentage'
                                          ;
                              leaf min-threshold-percentage {
                                description 'Set the minimum threshold percentage, support <1-100>'
                                            ;
                                type uint32 {
                                  range 1..100 {
                                    description 'The minimum threshold percentage, support <1-100>'
                                                ;
                                  }
                                }
                                mandatory true ;
                              }
                              leaf max-threshold-percentage {
                                description 'Set the maximum threshold percentage, support <1-100>'
                                            ;
                                type uint32 {
                                  range 1..100 {
                                    description 'The maximum threshold percentage, support <1-100>'
                                                ;
                                  }
                                }
                                mandatory true ;
                              }
                            }
                            ncd:revise-date 2019-08-05 ;
                          }
                          ncd:revise-date 2019-08-05 ;
                        }
                        leaf probability {
                          description 'Set mark probability denominator, suppor'
                                    + 't <1-100>'
                                      ;
                          type uint8 {
                            range 1..100 {
                              description 'Set mark probability denominator, support <1-100>'
                                          ;
                            }
                          }
                          mandatory true ;
                        }
                      }
                    }
                    container precedences {
                      description 'Configure WRED thresholds based on precedence'
                                  ;
                      list precedence {
                        description 'Configure WRED thresholds based on precede'
                                  + 'nce'
                                    ;
                        key prec-value ;
                        leaf prec-value {
                          description 'Set the precedence value, such as MPLS E'
                                    + 'XP, VLAN 802.1p, IP DSCP, IP Precedence,'
                                    + ' support <0-7>'
                                      ;
                          type uint16 {
                            range 0..7 {
                              description 'The IP-Precedence value, support <0-7>'
                                          ;
                            }
                          }
                        }
                        choice threshold {
                          description 'Set the threshold'
                                      ;
                          case threshold-value {
                            description 'Set the threshold value'
                                        ;
                            leaf min-threshold {
                              description 'Set the minimum threshold (default: kilobytes)'
                                          ;
                              type uint32 {
                                range 1..4294967295 {
                                  description 'The minimum threshold (default: kilobytes), support <1-4294967295>'
                                              ;
                                }
                              }
                              mandatory true ;
                            }
                            leaf min-threshold-unit {
                              description 'set min-threshold unit, such as kbytes, mbytes, gbytes'
                                          ;
                              type qos-threshold-unit-type ;
                            }
                            leaf max-threshold {
                              description 'Set the maximum threshold (default: kilobytes)'
                                          ;
                              type uint32 {
                                range 1..4294967295 {
                                  description 'The maximum threshold (default: kilobytes), support <1-4294967295>.'
                                              ;
                                }
                              }
                              mandatory true ;
                            }
                            leaf max-threshold-unit {
                              description 'set max-threshold unit, such as kbytes, mbytes, gbytes'
                                          ;
                              type qos-threshold-unit-type ;
                            }
                          }
                          case threshold-percentage {
                            description 'Set the threshold percentage'
                                        ;
                            container threshold-percentage {
                              description 'Set the threshold percentage'
                                          ;
                              leaf min-threshold-percentage {
                                description 'Set the minimum threshold percentage, support <1-100>'
                                            ;
                                type uint32 {
                                  range 1..100 {
                                    description 'The minimum threshold percentage, support <1-100>'
                                                ;
                                  }
                                }
                                mandatory true ;
                              }
                              leaf max-threshold-percentage {
                                description 'Set the maximum threshold percentage, support <1-100>'
                                            ;
                                type uint32 {
                                  range 1..100 {
                                    description 'The maximum threshold percentage, support <1-100>'
                                                ;
                                  }
                                }
                                mandatory true ;
                              }
                            }
                          }
                        }
                        leaf probability {
                          description 'Set mark probability denominator, suppor'
                                    + 't <1-100>'
                                      ;
                          type uint32 {
                            range 1..100 {
                              description 'Set mark probability denominator, support <1-100>'
                                          ;
                            }
                          }
                          mandatory true ;
                        }
                      }
                      ncd:revise-date 2021-01-18 ;
                    }
                    container weight {
                      description 'Configure WRED exponential weight factor'
                                  ;
                      presence 'Configure WRED exponential weight factor'
                               ;
                      leaf weight-value {
                        description 'Specify exponent used in weighted average '
                                  + 'calculation, support <1-16>'
                                    ;
                        type uint16 {
                          range 1..16 {
                            description 'Exponent used in weighted average calculation'
                                        ;
                          }
                        }
                        mandatory true ;
                      }
                      ncd:revise-date 2021-01-18 ;
                    }
                    ncd:revise-date 2018-08-18 ;
                  }
                  container service-policy {
                    description 'Configure hierarchical service policy'
                                ;
                    presence 'Configure hierarchical service policy'
                             ;
                    leaf hpolicy-name {
                      description 'Name of the hierarchical policy, support 1-3'
                                + '1 characters'
                                  ;
                      type string {
                        length 1..31 {
                          description 'Name of the hierarchical policy, support'
                                    + ' 1-31 characters'
                                      ;
                        }
                      }
                      mandatory true ;
                    }
                    ncd:revise-date 2021-01-11 ;
                  }
                }
              }
              container pmap-description {
                description 'Description of a policy map, support 1-79 characte'
                          + 'rs.'
                            ;
                presence 'Specify description of policy map'
                         ;
                leaf pmap-description {
                  description 'Description of a policy map, support 1-79 charac'
                            + 'ters.'
                              ;
                  type ncd:string-with-blank {
                    length 1..79 {
                      description 'Description of a policy map, support 1-79 ch'
                                + 'aracters.'
                                  ;
                    }
                  }
                  mandatory true ;
                }
                ncd:revise-date 2020-06-18 ;
              }
            }
          }
        }
        container sub-interface-based {
          if-feature sub-interface-mode ;
          description 'Policy map based on sub-interface'
                      ;
          container policy-maps {
            description 'Configure H-QoS policy map lists'
                        ;
            list policy-map {
              description 'Configure H-QoS policy maps'
                          ;
              key pmap-name ;
              leaf pmap-name {
                description 'Name of the policy map, support 1-31 characters'
                            ;
                type string {
                  length 1..31 {
                    description 'Name of the policy map, support 1-31 characters'
                                ;
                  }
                }
              }
              container class-maps {
                description 'Configure H-QoS policy class'
                            ;
                list class-map {
                  description 'Configure H-QoS policy class'
                              ;
                  key cmap-name ;
                  leaf cmap-name {
                    description 'Name of the class map, support 1-31 characters'
                                ;
                    type string {
                      length 1..31 {
                        description 'Name of the class map, support 1-31 charac'
                                  + 'ters'
                                    ;
                      }
                    }
                  }
                  container bandwidth {
                    description 'Configure minimum guaranteed bandwidth'
                                ;
                    presence 'Configure minimum guaranteed bandwidth'
                             ;
                    leaf percentage {
                      description 'Set the exact bandwidth percentage, support '
                                + '<1-100>'
                                  ;
                      type uint16 {
                        range 1..100 {
                          description 'The exact bandwidth percentage, support '
                                    + '<1-100>'
                                      ;
                        }
                      }
                      mandatory true ;
                    }
                  }
                  container priority-level {
                    description 'Configure PQ(Priority Queuing) priority level'
                                ;
                    presence 'Configure PQ priority level'
                             ;
                    leaf priority-value {
                      description 'Set the priority level of PQ, support <1-4>'
                                  ;
                      type uint16 {
                        range 1..4 {
                          description 'The priority level of PQ, support <1-4>'
                                      ;
                        }
                      }
                      mandatory true ;
                    }
                  }
                  container priority-llq {
                    description 'Configure LLQ(Low Latency Queuing) priority'
                                ;
                    presence 'Configure LLQ priority'
                             ;
                    leaf priority-llq {
                      description 'Specify LLQ'
                                  ;
                      type empty ;
                      mandatory true ;
                    }
                  }
                  container police {
                    description 'Configure traffic policing'
                                ;
                    presence 'Configure traffic policing'
                             ;
                    leaf cir {
                      description 'Configure the CIR(Committed Information Rate'
                                + ') value (default: kilobits per second)'
                                  ;
                      type uint32 {
                        range 8..4294967295 {
                          description 'The CIR value (default: kilobits per sec'
                                    + 'ond), support <8-4294967295>'
                                      ;
                        }
                      }
                      mandatory true ;
                    }
                    leaf cir-unit {
                      description 'set cir unit, such as kbps, mbps, gbps'
                                  ;
                      type qos-rate-unit-type ;
                    }
                    leaf cbs {
                      description 'Configure the CBS(Committed Burst Size) size'
                                + ' (default: KB)'
                                  ;
                      type uint32 {
                        range 1..4294967295 {
                          description 'The CBS(Committed Burst Size) size (defa'
                                    + 'ult: KB), support <1-4294967295>'
                                      ;
                        }
                      }
                    }
                    leaf cbs-unit {
                      description 'set cbs unit, such as kb, mb, gb'
                                  ;
                      type qos-bucket-unit-type ;
                    }
                    container pir-pbs {
                      description 'Configure PIR and PBS'
                                  ;
                      presence 'Configure pir and pbs'
                               ;
                      leaf pir {
                        description 'Configure the PIR(Peak Information Rate) v'
                                  + 'alue (default: kilobits per second)'
                                    ;
                        type uint32 {
                          range 8..4294967295 {
                            description 'The PIR(Peak Information Rate) value (default: kilobits per second), support <'
                                      + '8-4294967295>'
                                        ;
                          }
                        }
                        mandatory true ;
                      }
                      leaf pir-unit {
                        description 'set pir unit, such as kbps, mbps, gbps'
                                    ;
                        type qos-rate-unit-type ;
                      }
                      leaf pbs {
                        description 'Configure the PBS(Peak Burst Size) size (d'
                                  + 'efault: KB)'
                                    ;
                        type uint32 {
                          range 1..4294967295 {
                            description 'The PBS(Peak Burst Size) size (default: KB), support <1-4294967295>'
                                        ;
                          }
                        }
                      }
                      leaf pbs-unit {
                        description 'set pbs unit, such as kb, mb, gb'
                                    ;
                        type qos-bucket-unit-type ;
                      }
                    }
                  }
                }
                container class-default {
                  description 'Select the default class'
                              ;
                  presence 'Specify the default class'
                           ;
                  leaf class-default {
                    description 'Specify the default class'
                                ;
                    type empty ;
                    mandatory true ;
                  }
                  container bandwidth {
                    description 'Configure minimum guaranteed bandwidth'
                                ;
                    presence 'Configure minimum guaranteed bandwidth'
                             ;
                    leaf percentage {
                      description 'Set the exact bandwidth percentage, support '
                                + '<1-100>'
                                  ;
                      type uint16 {
                        range 1..100 {
                          description 'The exact bandwidth percentage, support '
                                    + '<1-100>'
                                      ;
                        }
                      }
                      mandatory true ;
                    }
                  }
                  container priority-level {
                    description 'Configure PQ(Priority Queuing) priority level'
                                ;
                    presence 'Configure PQ priority level'
                             ;
                    leaf priority-value {
                      description 'Set the priority level of PQ, support <1-4>'
                                  ;
                      type uint16 {
                        range 1..4 {
                          description 'The priority level of PQ, support <1-4>'
                                      ;
                        }
                      }
                      mandatory true ;
                    }
                  }
                  container priority-llq {
                    description 'Configure LLQ(Low Latency Queuing) priority'
                                ;
                    presence 'Configure LLQ priority'
                             ;
                    leaf priority-llq {
                      description 'Specify LLQ'
                                  ;
                      type empty ;
                      mandatory true ;
                    }
                  }
                  container police {
                    description 'Configure traffic policing'
                                ;
                    presence 'Configure traffic policing'
                             ;
                    leaf cir {
                      description 'Configure the CIR(Committed Information Rate'
                                + ') value (default: kilobits per second)'
                                  ;
                      type uint32 {
                        range 8..4294967295 {
                          description 'The CIR value (default: kilobits per sec'
                                    + 'ond), support <8-4294967295>'
                                      ;
                        }
                      }
                      mandatory true ;
                    }
                    leaf cir-unit {
                      description 'set cir unit, such as kbps, mbps, gbps'
                                  ;
                      type qos-rate-unit-type ;
                    }
                    leaf cbs {
                      description 'Configure the CBS(Committed Burst Size) size'
                                + ' (default: KB)'
                                  ;
                      type uint32 {
                        range 1..4294967295 {
                          description 'The PBS(Peak Burst Size) size (default: '
                                    + 'KB), support <1-4294967295>'
                                      ;
                        }
                      }
                    }
                    leaf cbs-unit {
                      description 'set cbs unit, such as kb, mb, gb'
                                  ;
                      type qos-bucket-unit-type ;
                    }
                    container pir-pbs {
                      description 'Configure PIR and PBS'
                                  ;
                      presence 'Configure pir and pbs'
                               ;
                      leaf pir {
                        description 'Configure the PIR(Peak Information Rate) v'
                                  + 'alue (default: kilobits per second)'
                                    ;
                        type uint32 {
                          range 8..4294967295 {
                            description 'The PIR(Peak Information Rate) value (default: kilobits per second), support <'
                                      + '8-4294967295>'
                                        ;
                          }
                        }
                        mandatory true ;
                      }
                      leaf pir-unit {
                        description 'set pir unit, such as kbps, mbps, gbps'
                                    ;
                        type qos-rate-unit-type ;
                      }
                      leaf pbs {
                        description 'Configure the PBS(Peak Burst Size) size (d'
                                  + 'efault: KB)'
                                    ;
                        type uint32 {
                          range 1..4294967295 {
                            description 'The PBS(Peak Burst Size) size (default: KB), support <1-4294967295>'
                                        ;
                          }
                        }
                      }
                      leaf pbs-unit {
                        description 'set pbs unit, such as kb, mb, gb'
                                    ;
                        type qos-bucket-unit-type ;
                      }
                    }
                  }
                }
              }
              container pmap-description {
                description 'Description of a policy map, support 1-79 characte'
                          + 'rs.'
                            ;
                presence 'Specify description of policy map'
                         ;
                leaf pmap-description {
                  description 'Description of a policy map, support 1-79 charac'
                            + 'ters.'
                              ;
                  type ncd:string-with-blank {
                    length 1..79 {
                      description 'Description of a policy map, support 1-79 ch'
                                + 'aracters.'
                                  ;
                    }
                  }
                  mandatory true ;
                }
                ncd:revise-date 2020-06-18 ;
              }
            }
          }
        }
        container switch-fabric-based {
          if-feature switch-fabric-mode ;
          description 'Policy map based on switch-fabric'
                      ;
          container policy-maps {
            description 'Configure H-QoS policy map lists'
                        ;
            list policy-map {
              description 'Configure H-QoS policy maps'
                          ;
              key pmap-name ;
              leaf pmap-name {
                description 'Name of the policy map, support 1-31 characters'
                            ;
                type string {
                  length 1..31 {
                    description 'Name of the policy map, support 1-31 characters'
                                ;
                  }
                }
              }
              container class-maps {
                description 'Configure H-QoS policy class'
                            ;
                list class-map {
                  description 'Configure H-QoS policy class'
                              ;
                  key cmap-name ;
                  leaf cmap-name {
                    description 'Name of the class map, support 1-31 characters'
                                ;
                    type string {
                      length 1..31 ;
                    }
                  }
                  container bandwidth {
                    description 'Configure minimum guaranteed bandwidth'
                                ;
                    presence 'Configure minimum guaranteed bandwidth'
                             ;
                    leaf percentage {
                      description 'Set the exact bandwidth percentage, support '
                                + '<1-100>'
                                  ;
                      type uint16 {
                        range 1..100 {
                          description 'The exact bandwidth percentage, support '
                                    + '<1-100>'
                                      ;
                        }
                      }
                      mandatory true ;
                    }
                  }
                  container priority-level {
                    description 'Configure PQ(Priority Queuing) priority level'
                                ;
                    presence 'Configure PQ priority level'
                             ;
                    leaf priority-value {
                      description 'Set the priority level of PQ, support <1-4>'
                                  ;
                      type uint16 {
                        range 1..4 {
                          description 'The priority level of PQ, support <1-4>'
                                      ;
                        }
                      }
                      mandatory true ;
                    }
                  }
                  container police {
                    description 'Configure traffic policing'
                                ;
                    presence 'Configure traffic policing'
                             ;
                    leaf cir {
                      description 'Configure the CIR(Committed Information Rate'
                                + ') value (default: kilobits per second)'
                                  ;
                      type uint32 {
                        range 8..4294967295 {
                          description 'The CIR value (default: kilobits per sec'
                                    + 'ond), support <8-4294967295>'
                                      ;
                        }
                      }
                      mandatory true ;
                    }
                    leaf cir-unit {
                      description 'set cir unit, such as kbps, mbps, gbps'
                                  ;
                      type qos-rate-unit-type ;
                    }
                    leaf cbs {
                      description 'Configure the CBS(Committed Burst Size) size'
                                + ' (default: KB)'
                                  ;
                      type uint32 {
                        range 1..4294967295 {
                          description 'The CBS(Committed Burst Size) size (defa'
                                    + 'ult: KB), support <1-4294967295>'
                                      ;
                        }
                      }
                      mandatory true ;
                    }
                    leaf cbs-unit {
                      description 'set cbs unit, such as kb, mb, gb'
                                  ;
                      type qos-bucket-unit-type ;
                    }
                  }
                  container random-detect {
                    description 'Configure WRED(Weighted Random Early Detection'
                              + ') information'
                                ;
                    container enable {
                      description 'Configure WRED enable'
                                  ;
                      presence 'Configure WRED enable'
                               ;
                      leaf enable {
                        description 'Specify WRED enable'
                                    ;
                        type empty ;
                        mandatory true ;
                      }
                    }
                    container colors {
                      description 'Configure WRED thresholds based on color'
                                  ;
                      list color {
                        description 'Configure WRED thresholds based on color'
                                    ;
                        key color-type ;
                        leaf color-type {
                          description 'set WRED color, such as green, yellow, r'
                                    + 'ed'
                                      ;
                          type qos-color-type ;
                        }
                        leaf min-threshold {
                          description 'Set the minimum threshold in kilobytes, '
                                    + 'support <1-1024000>'
                                      ;
                          type uint32 {
                            range 1..1024000 {
                              description 'The minimum threshold in kilobytes, support <1-1024000>'
                                          ;
                            }
                          }
                          units KB ;
                          mandatory true ;
                        }
                        leaf max-threshold {
                          description 'Set the maximum threshold in kilobytes, '
                                    + 'support <1-1024000>'
                                      ;
                          type uint32 {
                            range 1..1024000 {
                              description 'The maximum threshold in kilobytes, support <1-1024000>'
                                          ;
                            }
                          }
                          units KB ;
                          mandatory true ;
                        }
                        leaf probability {
                          description 'Set mark probability denominator, suppor'
                                    + 't <1-100>'
                                      ;
                          type uint8 {
                            range 1..100 {
                              description 'Set mark probability denominator, support <1-100>'
                                          ;
                            }
                          }
                          mandatory true ;
                        }
                      }
                    }
                    container precedences {
                      description 'Configure WRED thresholds based on precedence'
                                  ;
                      list precedence {
                        description 'Configure WRED thresholds based on precede'
                                  + 'nce'
                                    ;
                        key prec-value ;
                        leaf prec-value {
                          description 'Set the precedence value, such as MPLS E'
                                    + 'XP, VLAN 802.1p, IP DSCP, IP Precedence,'
                                    + ' support <0-7>'
                                      ;
                          type uint16 {
                            range 0..7 {
                              description 'The precedence value, support <0-7>'
                                          ;
                            }
                          }
                        }
                        leaf min-threshold {
                          description 'Set the minimum threshold (default: kilo'
                                    + 'bytes)'
                                      ;
                          type uint32 {
                            range 1..4294967295 {
                              description 'The minimum threshold (default: kilobytes), support <1-4294967295>'
                                          ;
                            }
                          }
                          mandatory true ;
                        }
                        leaf min-threshold-unit {
                          description 'set min-threshold unit, such as kbytes, '
                                    + 'mbytes, gbytes'
                                      ;
                          type qos-threshold-unit-type ;
                        }
                        leaf max-threshold {
                          description 'Set the maximum threshold (default: kilo'
                                    + 'bytes)'
                                      ;
                          type uint32 {
                            range 1..4294967295 {
                              description 'The maximum threshold (default: kilobytes), support <1-4294967295>'
                                          ;
                            }
                          }
                          mandatory true ;
                        }
                        leaf max-threshold-unit {
                          description 'set max-threshold unit, such as kbytes, '
                                    + 'mbytes, gbytes'
                                      ;
                          type qos-threshold-unit-type ;
                        }
                        leaf probability {
                          description 'Set mark probability denominator, suppor'
                                    + 't <1-100>'
                                      ;
                          type uint32 {
                            range 1..100 {
                              description 'Set mark probability denominator, support <1-100>'
                                          ;
                            }
                          }
                          mandatory true ;
                        }
                      }
                    }
                    container weight {
                      description 'Configure WRED exponential weight factor'
                                  ;
                      presence 'Configure WRED exponential weight factor'
                               ;
                      leaf weight-value {
                        description 'Specify exponent used in weighted average '
                                  + 'calculation, support <1-16>'
                                    ;
                        type uint16 {
                          range 1..16 {
                            description 'Exponent used in weighted average calculation'
                                        ;
                          }
                        }
                        mandatory true ;
                      }
                    }
                  }
                  container service-policy {
                    description 'Configure hierarchical service policy'
                                ;
                    presence 'Configure hierarchical service policy'
                             ;
                    leaf hpolicy-name {
                      description 'Name of the hierarchical policy, support 1-3'
                                + '1 characters'
                                  ;
                      type string {
                        length 1..31 {
                          description 'Name of the hierarchical policy, support'
                                    + ' 1-31 characters'
                                      ;
                        }
                      }
                      mandatory true ;
                    }
                  }
                  container map {
                    description 'Set the packet level'
                                ;
                    presence 'Set the packet level'
                             ;
                    leaf map-priority {
                      description 'Map the packet priority, such as high, middl'
                                + 'e, normal, low'
                                  ;
                      type enumeration {
                        enum high {
                          value 1 ;
                          description 'High priority'
                                      ;
                        }
                        enum middle {
                          value 2 ;
                          description 'Middle priority'
                                      ;
                        }
                        enum normal {
                          value 3 ;
                          description 'Normal priority'
                                      ;
                        }
                        enum low {
                          value 4 ;
                          description 'Low priority'
                                      ;
                        }
                      }
                      mandatory true ;
                    }
                  }
                }
                container class-default {
                  description 'Select the default class'
                              ;
                  presence 'Specify the default class'
                           ;
                  leaf class-default {
                    description 'Specify the default class'
                                ;
                    type empty ;
                    mandatory true ;
                  }
                  container bandwidth {
                    description 'Configure minimum guaranteed bandwidth'
                                ;
                    presence 'Configure minimum guaranteed bandwidth'
                             ;
                    leaf percentage {
                      description 'Set the exact bandwidth percentage, support '
                                + '<1-100>'
                                  ;
                      type uint16 {
                        range 1..100 {
                          description 'The exact bandwidth percentage, support '
                                    + '<1-100>'
                                      ;
                        }
                      }
                      mandatory true ;
                    }
                  }
                  container priority-level {
                    description 'Configure PQ(Priority Queuing) priority level'
                                ;
                    presence 'Configure PQ priority level'
                             ;
                    leaf priority-value {
                      description 'Set the priority level of PQ, support <1-4>'
                                  ;
                      type uint16 {
                        range 1..4 {
                          description 'The priority level of PQ, support <1-4>'
                                      ;
                        }
                      }
                      mandatory true ;
                    }
                  }
                  container police {
                    description 'Configure traffic policing'
                                ;
                    presence 'Configure traffic policing'
                             ;
                    leaf cir {
                      description 'Configure the CIR(Committed Information Rate'
                                + ') value (default: kilobits per second)'
                                  ;
                      type uint32 {
                        range 8..4294967295 {
                          description 'The CIR value (default: kilobits per sec'
                                    + 'ond), support <8-4294967295>'
                                      ;
                        }
                      }
                      mandatory true ;
                    }
                    leaf cir-unit {
                      description 'set cir unit, such as kbps, mbps, gbps'
                                  ;
                      type qos-rate-unit-type ;
                    }
                    leaf cbs {
                      description 'Configure the CBS(Committed Burst Size) size'
                                + ' (default: KB)'
                                  ;
                      type uint32 {
                        range 1..4294967295 {
                          description 'The CBS(Committed Burst Size) size (defa'
                                    + 'ult: KB), support <1-4294967295>'
                                      ;
                        }
                      }
                      mandatory true ;
                    }
                    leaf cbs-unit {
                      description 'set cbs unit, such as kb, mb, gb'
                                  ;
                      type qos-bucket-unit-type ;
                    }
                  }
                  container random-detect {
                    description 'Configure WRED(Weighted Random Early Detection'
                              + ') information'
                                ;
                    container enable {
                      description 'Configure WRED enable'
                                  ;
                      presence 'Configure WRED enable'
                               ;
                      leaf enable {
                        description 'Specify WRED enable'
                                    ;
                        type empty ;
                        mandatory true ;
                      }
                    }
                    container colors {
                      description 'Configure WRED thresholds based on color'
                                  ;
                      list color {
                        description 'Configure WRED thresholds based on color'
                                    ;
                        key color-type ;
                        leaf color-type {
                          description 'set WRED color, such as green, yellow, r'
                                    + 'ed'
                                      ;
                          type qos-color-type ;
                        }
                        leaf min-threshold {
                          description 'Set the minimum threshold in kilobytes, '
                                    + 'support <1-1024000>'
                                      ;
                          type uint32 {
                            range 1..1024000 {
                              description 'The minimum threshold in kilobytes, support <1-1024000>'
                                          ;
                            }
                          }
                          units KB ;
                          mandatory true ;
                        }
                        leaf max-threshold {
                          description 'Set the maximum threshold in kilobytes, '
                                    + 'support <1-1024000>'
                                      ;
                          type uint32 {
                            range 1..1024000 {
                              description 'The maximum threshold in kilobytes, support <1-1024000>'
                                          ;
                            }
                          }
                          units KB ;
                          mandatory true ;
                        }
                        leaf probability {
                          description 'Set mark probability denominator, suppor'
                                    + 't <1-100>'
                                      ;
                          type uint8 {
                            range 1..100 ;
                          }
                          mandatory true ;
                        }
                      }
                    }
                    container precedences {
                      description 'Configure WRED thresholds based on precedence'
                                  ;
                      list precedence {
                        description 'Configure WRED thresholds based on precede'
                                  + 'nce'
                                    ;
                        key prec-value ;
                        leaf prec-value {
                          description 'Set the precedence value, such as MPLS E'
                                    + 'XP, VLAN 802.1p, IP DSCP, IP Precedence,'
                                    + ' support <0-7>'
                                      ;
                          type uint16 {
                            range 0..7 {
                              description 'The precedence value, support <0-7>'
                                          ;
                            }
                          }
                        }
                        leaf min-threshold {
                          description 'Set the minimum threshold (default: kilo'
                                    + 'bytes)'
                                      ;
                          type uint32 {
                            range 1..4294967295 {
                              description 'The minimum threshold (default: kilobytes), support <1-4294967295>'
                                          ;
                            }
                          }
                          mandatory true ;
                        }
                        leaf min-threshold-unit {
                          description 'set min-threshold unit, such as kbytes, '
                                    + 'mbps, gbps'
                                      ;
                          type qos-threshold-unit-type ;
                        }
                        leaf max-threshold {
                          description 'Set the maximum threshold (default: kilo'
                                    + 'bytes)'
                                      ;
                          type uint32 {
                            range 1..4294967295 {
                              description 'The maximum threshold (default: kilobytes), support <1-4294967295>'
                                          ;
                            }
                          }
                          mandatory true ;
                        }
                        leaf max-threshold-unit {
                          description 'set max-threshold unit, such as kbytes, '
                                    + 'mbytes, gbytes'
                                      ;
                          type qos-threshold-unit-type ;
                        }
                        leaf probability {
                          description 'Set mark probability denominator, suppor'
                                    + 't <1-100>'
                                      ;
                          type uint32 {
                            range 1..100 {
                              description 'Set mark probability denominator, support <1-100>'
                                          ;
                            }
                          }
                          mandatory true ;
                        }
                      }
                    }
                    container weight {
                      description 'Configure WRED exponential weight factor'
                                  ;
                      presence 'Configure WRED exponential weight factor'
                               ;
                      leaf weight-value {
                        description 'Specify exponent used in weighted average '
                                  + 'calculation, support <1-16>'
                                    ;
                        type uint16 {
                          range 1..16 {
                            description 'Exponent used in weighted average calculation'
                                        ;
                          }
                        }
                        mandatory true ;
                      }
                    }
                  }
                  container service-policy {
                    description 'Configure hierarchical service policy'
                                ;
                    presence 'Configure hierarchical service policy'
                             ;
                    leaf hpolicy-name {
                      description 'Name of the hierarchical policy, support 1-3'
                                + '1 characters'
                                  ;
                      type string {
                        length 1..31 {
                          description 'Name of the hierarchical policy, support'
                                    + ' 1-31 characters'
                                      ;
                        }
                      }
                      mandatory true ;
                    }
                  }
                  container map {
                    description 'Set the packet level'
                                ;
                    presence 'Set the packet level'
                             ;
                    leaf map-priority {
                      description 'Map the packet priority, such as high, middl'
                                + 'e, normal, low'
                                  ;
                      type enumeration {
                        enum high {
                          value 1 ;
                          description 'High priority'
                                      ;
                        }
                        enum middle {
                          value 2 ;
                          description 'Middle priority'
                                      ;
                        }
                        enum normal {
                          value 3 ;
                          description 'Normal priority'
                                      ;
                        }
                        enum low {
                          value 4 ;
                          description 'Low priority'
                                      ;
                        }
                      }
                      mandatory true ;
                    }
                  }
                }
              }
            }
          }
        }
        container flowspec-based {
          description 'Policy map based on flowspec.'
                      ;
          container policy-maps {
            description 'Configure H-QoS policy map lists'
                        ;
            list policy-map {
              description 'Configure H-QoS policy maps'
                          ;
              key pmap-name ;
              leaf pmap-name {
                description 'Name of the policy map, support 1-31 characters.'
                            ;
                type string {
                  length 1..31 {
                    description 'Name of the policy map, support 1-31 character'
                              + 's.'
                                ;
                  }
                }
              }
              container class-maps {
                description 'Configure H-QoS policy class'
                            ;
                list class-map {
                  description 'Configure H-QoS policy class'
                              ;
                  key cmap-name ;
                  leaf cmap-name {
                    description 'Name of the class map, support 1-31 characters.'
                                ;
                    type string {
                      length 1..31 {
                        description 'Name of the class map, support 1-31 charac'
                                  + 'ters.'
                                    ;
                      }
                    }
                  }
                  container drop {
                    description 'Configure drop'
                                ;
                    presence 'Configure drop'
                             ;
                    leaf drop {
                      description 'Specify drop.'
                                  ;
                      type empty ;
                      mandatory true ;
                    }
                  }
                  container police {
                    description 'Configure traffic policing.'
                                ;
                    presence 'Configure traffic policing'
                             ;
                    leaf rate {
                      description 'Set the rate value(default:kilobits per seco'
                                + 'nd).'
                                  ;
                      type uint32 {
                        range 8..4294967295 {
                          description 'Set the rate value(default:kilobits per '
                                    + 'second).'
                                      ;
                        }
                      }
                      mandatory true ;
                    }
                    leaf rate-unit {
                      description 'Set rate unit, such as kbps, mbps, gbps.'
                                  ;
                      type qos-rate-unit-type ;
                    }
                  }
                  container redirect-nexthop {
                    description 'Redirect a packet.'
                                ;
                    presence 'Redirect a packet'
                             ;
                    choice next-hop {
                      description 'Set next hop.'
                                  ;
                      mandatory true ;
                      case ip-address {
                        description 'Configurate IPv4 address as next-hop.'
                                    ;
                        container ip-address {
                          description 'Configurate IPv4 address as next-hop.'
                                      ;
                          leaf ipv4-address {
                            description 'IPv4 address.'
                                        ;
                            type ncd:ipv4-address ;
                            mandatory true ;
                          }
                          choice ipaddr-nexthop {
                            description 'Set next hop based on IPv4 Address.'
                                        ;
                            case global {
                              description 'Global route.'
                                          ;
                              leaf global {
                                description 'Global route.'
                                            ;
                                type empty ;
                              }
                            }
                            case route-target {
                              description 'Configurate route-target as next-hop.'
                                          ;
                              container route-target {
                                description 'Configurate route-target as next-hop.'
                                            ;
                                presence 'Configurate route-target as next-hop'
                                         ;
                                leaf route-target {
                                  description 'Configurate route-target as next-hop.'
                                              ;
                                  type empty ;
                                  mandatory true ;
                                }
                                choice rt-pattern {
                                  description 'route-target pattern, such as <0-65535>:<0-4294967295>, A.B.C.D:<0-65535'
                                            + '>, <1-65535>.<0-65535>:<0-65535>.'
                                              ;
                                  mandatory true ;
                                  case asn-nn {
                                    description 'Route target, <0-65535>:<0-4294967295>.'
                                                ;
                                    leaf asn-nn {
                                      description 'Route target, <0-65535>:<0-4294967295>.'
                                                  ;
                                      type ncd:asn-nn ;
                                      mandatory true ;
                                    }
                                  }
                                  case ipadd-nn {
                                    description 'Route target, A.B.C.D:<0-65535>.'
                                                ;
                                    leaf ipadd-nn {
                                      description 'Route target, A.B.C.D:<0-65535>.'
                                                  ;
                                      type ncd:ipadd-nn ;
                                      mandatory true ;
                                    }
                                  }
                                  case asnd-nn {
                                    description 'Route target, <1-65535>.<0-65535>:<0-65535>.'
                                                ;
                                    leaf asnd-nn {
                                      description 'Route target, <1-65535>.<0-65535>:<0-65535>.'
                                                  ;
                                      type ncd:asnd-nn ;
                                      mandatory true ;
                                    }
                                  }
                                }
                              }
                            }
                            case vrf {
                              description 'Configurate virtual route forwarding as next-hop.'
                                          ;
                              container vrf {
                                description 'Configurate virtual route forwarding as next-hop.'
                                            ;
                                presence 'Configurate virtual route forwarding as next-hop'
                                         ;
                                leaf vrf-name {
                                  description 'Virtual route forwarding name, support 1-32 characters.'
                                              ;
                                  type string {
                                    length 1..32 {
                                      description 'Virtual route forwarding name, support 1-32 characters.'
                                                  ;
                                    }
                                  }
                                  mandatory true ;
                                }
                              }
                            }
                          }
                          leaf copy {
                            description 'Copy flag.'
                                        ;
                            type empty ;
                            ncd:revise-date 2020-07-17 ;
                          }
                        }
                      }
                      case route-target {
                        description 'Configurate route-target as next-hop.'
                                    ;
                        container route-target {
                          description 'Configurate route-target as next-hop.'
                                      ;
                          leaf route-target {
                            description 'Configurate route-target as next-hop.'
                                        ;
                            type empty ;
                            mandatory true ;
                          }
                          choice rt-pattern {
                            description 'route-target pattern, such as <0-65535>:<0-4294967295>, A.B.C.D:<0-65535>, <1-'
                                      + '65535>.<0-65535>:<0-65535>.'
                                        ;
                            mandatory true ;
                            case asn-nn {
                              description 'Route target, <0-65535>:<0-4294967295>.'
                                          ;
                              leaf asn-nn {
                                description 'Route target, <0-65535>:<0-4294967295>.'
                                            ;
                                type ncd:asn-nn ;
                                mandatory true ;
                              }
                            }
                            case ipadd-nn {
                              description 'Route target, A.B.C.D:<0-65535>.'
                                          ;
                              leaf ipadd-nn {
                                description 'Route target, A.B.C.D:<0-65535>.'
                                            ;
                                type ncd:ipadd-nn ;
                                mandatory true ;
                              }
                            }
                            case asnd-nn {
                              description 'Route target, <1-65535>.<0-65535>:<0-65535>.'
                                          ;
                              leaf asnd-nn {
                                description 'Route target, <1-65535>.<0-65535>:<0-65535>.'
                                            ;
                                type ncd:asnd-nn ;
                                mandatory true ;
                              }
                            }
                          }
                        }
                      }
                      case vrf {
                        description 'Configurate virtual route forwarding as ne'
                                  + 'xt-hop.'
                                    ;
                        container vrf {
                          description 'Configurate virtual route forwarding as '
                                    + 'next-hop.'
                                      ;
                          leaf vrf-name {
                            description 'Virtual route forwarding name, support 1-32 characters.'
                                        ;
                            type string {
                              length 1..32 {
                                description 'Virtual route forwarding name, support 1-32 characters.'
                                            ;
                              }
                            }
                            mandatory true ;
                          }
                        }
                      }
                      case ipv6-address {
                        description 'Configurate IPv6 address as next-hop.'
                                    ;
                        container ipv6-address {
                          description 'Configurate IPv6 address as next-hop.'
                                      ;
                          leaf ipv6-address {
                            description 'IPv6 address.'
                                        ;
                            type ncd:ipv6-address ;
                            mandatory true ;
                          }
                          choice ipaddr-nexthop {
                            description 'Set next hop based on IPv6 Address.'
                                        ;
                            case global {
                              description 'Global route.'
                                          ;
                              leaf global {
                                description 'Global route.'
                                            ;
                                type empty ;
                              }
                            }
                            case route-target {
                              description 'Configurate route-target as next-hop.'
                                          ;
                              container route-target {
                                description 'Configurate route-target as next-hop.'
                                            ;
                                presence 'Configurate route-target as next-hop'
                                         ;
                                leaf route-target {
                                  description 'Configurate route-target as next-hop.'
                                              ;
                                  type empty ;
                                  mandatory true ;
                                }
                                choice rt-pattern {
                                  description 'route-target pattern, such as <0-65535>:<0-4294967295>, A.B.C.D:<0-65535'
                                            + '>, <1-65535>.<0-65535>:<0-65535>.'
                                              ;
                                  mandatory true ;
                                  case asn-nn {
                                    description 'Route target, <0-65535>:<0-4294967295>.'
                                                ;
                                    leaf asn-nn {
                                      description 'Route target, <0-65535>:<0-4294967295>.'
                                                  ;
                                      type ncd:asn-nn ;
                                      mandatory true ;
                                    }
                                  }
                                  case ipadd-nn {
                                    description 'Route target, A.B.C.D:<0-65535>.'
                                                ;
                                    leaf ipadd-nn {
                                      description 'Route target, A.B.C.D:<0-65535>.'
                                                  ;
                                      type ncd:ipadd-nn ;
                                      mandatory true ;
                                    }
                                  }
                                  case asnd-nn {
                                    description 'Route target, <1-65535>.<0-65535>:<0-65535>.'
                                                ;
                                    leaf asnd-nn {
                                      description 'Route target, <1-65535>.<0-65535>:<0-65535>.'
                                                  ;
                                      type ncd:asnd-nn ;
                                      mandatory true ;
                                    }
                                  }
                                }
                              }
                            }
                            case vrf {
                              description 'Configurate virtual route forwarding as next-hop.'
                                          ;
                              container vrf {
                                description 'Configurate virtual route forwarding as next-hop.'
                                            ;
                                presence 'Configurate virtual route forwarding as next-hop'
                                         ;
                                leaf vrf-name {
                                  description 'Virtual route forwarding name, support 1-32 characters.'
                                              ;
                                  type string {
                                    length 1..32 {
                                      description 'Virtual route forwarding name, support 1-32 characters.'
                                                  ;
                                    }
                                  }
                                  mandatory true ;
                                }
                              }
                            }
                            case color-sid {
                              description 'Configurate color and prefix-sid as next-hop.'
                                          ;
                              container color-sid {
                                description 'Configurate color and prefix-sid as next-hop.'
                                            ;
                                presence 'Configurate color and prefix-sid as next-hop'
                                         ;
                                leaf color {
                                  description 'Color value, support 1-4294967295.'
                                              ;
                                  type uint32 {
                                    range 1..4294967295 ;
                                  }
                                  mandatory true ;
                                }
                                leaf prefix-sid {
                                  description 'Prefix SID value, <X:X:X:X:X:X:X:X>.'
                                              ;
                                  type ncd:ipv6-address ;
                                  mandatory true ;
                                }
                              }
                              ncd:revise-date 2020-10-20 ;
                            }
                          }
                          leaf copy {
                            description 'Copy flag.'
                                        ;
                            type empty ;
                          }
                        }
                        ncd:revise-date 2020-07-17 ;
                      }
                    }
                  }
                  container sampler {
                    description 'Configure sampler.'
                                ;
                    presence 'Configure sampler'
                             ;
                    leaf sampler {
                      description 'Specify sampler.'
                                  ;
                      type empty ;
                      mandatory true ;
                    }
                  }
                  container set {
                    description 'Mark a packet.'
                                ;
                    presence 'Mark a packet'
                             ;
                    container dscp {
                      description 'Select DSCP as mark type.'
                                  ;
                      presence 'Select DSCP as mark type'
                               ;
                      leaf dscp-value {
                        description 'DSCP value, support <0-63>.'
                                    ;
                        type uint16 {
                          range 0..63 {
                            description 'DSCP value, support <0-63>'
                                        ;
                          }
                        }
                        mandatory true ;
                      }
                    }
                  }
                  container redirect-rsvp-te {
                    status obsolete {
                      ncd:revise-date 2020-12-02 ;
                    }
                    description 'Redirect RSVP-TE.'
                                ;
                    presence 'Redirect RSVP-TE'
                             ;
                    leaf tunnel-id {
                      description 'Tunnel ID.'
                                  ;
                      type uint32 {
                        range 1..65535 ;
                      }
                      mandatory true ;
                    }
                    choice address {
                      description 'Tunnel address.'
                                  ;
                      mandatory true ;
                      case ipv4 {
                        description 'Choose IPv4 address.'
                                    ;
                        leaf ipv4-sender-address {
                          description 'IPv4 sender address.'
                                      ;
                          type ncd:ipv4-address ;
                          mandatory true ;
                        }
                        leaf ipv4-end-address {
                          description 'IPv4 end point address.'
                                      ;
                          type ncd:ipv4-address ;
                          mandatory true ;
                        }
                      }
                      case ipv6 {
                        description 'Choose IPv6 address.'
                                    ;
                        leaf ipv6-sender-address {
                          description 'IPv6 sender address.'
                                      ;
                          type ncd:ipv6-address ;
                          mandatory true ;
                        }
                        leaf ipv6-end-address {
                          description 'IPv6 end point address.'
                                      ;
                          type ncd:ipv6-address ;
                          mandatory true ;
                        }
                      }
                    }
                    leaf copy {
                      description 'Copy flag.'
                                  ;
                      type empty ;
                    }
                    ncd:revise-date 2020-02-03 ;
                  }
                  container redirect-sr-te {
                    status obsolete {
                      ncd:revise-date 2020-12-02 ;
                    }
                    description 'Redirect SR-TE.'
                                ;
                    presence 'Redirect SR-TE'
                             ;
                    leaf tunnel-id {
                      description 'Tunnel ID.'
                                  ;
                      type uint32 {
                        range 1..65535 ;
                      }
                      mandatory true ;
                    }
                    choice address {
                      description 'Tunnel address.'
                                  ;
                      mandatory true ;
                      case ipv4 {
                        description 'Choose IPv4 address.'
                                    ;
                        leaf ipv4-sender-address {
                          description 'IPv4 sender address.'
                                      ;
                          type ncd:ipv4-address ;
                          mandatory true ;
                        }
                        leaf ipv4-end-address {
                          description 'IPv4 end point address.'
                                      ;
                          type ncd:ipv4-address ;
                          mandatory true ;
                        }
                      }
                      case ipv6 {
                        description 'Choose IPv6 address.'
                                    ;
                        leaf ipv6-sender-address {
                          description 'IPv6 sender address.'
                                      ;
                          type ncd:ipv6-address ;
                          mandatory true ;
                        }
                        leaf ipv6-end-address {
                          description 'IPv6 end point address.'
                                      ;
                          type ncd:ipv6-address ;
                          mandatory true ;
                        }
                      }
                    }
                    leaf copy {
                      description 'Copy flag.'
                                  ;
                      type empty ;
                    }
                    ncd:revise-date 2020-02-03 ;
                  }
                  container redirect-tunnel-id {
                    description 'Redirect tunnel ID.'
                                ;
                    presence 'Redirect tunnel ID'
                             ;
                    leaf indirection-id {
                      description 'Indirection ID.'
                                  ;
                      type uint32 {
                        range 1..4294967295 ;
                      }
                      mandatory true ;
                    }
                    leaf copy {
                      description 'Copy flag.'
                                  ;
                      type empty ;
                    }
                    ncd:revise-date 2020-12-02 ;
                  }
                }
              }
              container pmap-description {
                description 'Description of a policy map, support 1-79 characte'
                          + 'rs.'
                            ;
                presence 'Specify description of policy map'
                         ;
                leaf pmap-description {
                  description 'Description of a policy map, support 1-79 charac'
                            + 'ters.'
                              ;
                  type ncd:string-with-blank {
                    length 1..79 {
                      description 'Description of a policy map, support 1-79 ch'
                                + 'aracters.'
                                  ;
                    }
                  }
                  mandatory true ;
                }
                ncd:revise-date 2020-06-18 ;
              }
            }
          }
          ncd:revise-date 2017-06-12 ;
        }
        container policy-map-id {
          description 'H-QoS policy map lists id, only for the query'
                      ;
          container policy-maps {
            description 'H-QoS policy map lists'
                        ;
            list policy-map {
              description 'H-QoS policy map list'
                          ;
              key pmap-name ;
              leaf pmap-name {
                description 'Name of the policy map, support 1-31 characters'
                            ;
                type string {
                  length 1..31 {
                    description 'Name of the policy map, support 1-31 characters'
                                ;
                  }
                }
              }
              leaf pmap-id {
                description 'H-QoS policy map list id'
                            ;
                type uint32 {
                  range 1..4000 {
                    description 'H-QoS policy map list id'
                                ;
                  }
                }
              }
            }
          }
          ncd:revise-date 2015-03-31 ;
        }
        container flow-behavior {
          description 'Policy map based on flow-behavior.'
                      ;
          container policy-maps {
            description 'Configure H-QoS policy map lists'
                        ;
            list policy-map {
              description 'Configure H-QoS policy maps'
                          ;
              key pmap-name ;
              leaf pmap-name {
                description 'Name of the policy map, support 1-31 characters.'
                            ;
                type string {
                  length 1..31 {
                    description 'Name of the policy map, support 1-31 character'
                              + 's.'
                                ;
                  }
                }
              }
              container class-maps {
                description 'Configure H-QoS policy class'
                            ;
                list class-map {
                  description 'Configure H-QoS policy class'
                              ;
                  key cmap-name ;
                  leaf cmap-name {
                    description 'Name of the class map, support 1-31 characters.'
                                ;
                    type string {
                      length 1..31 {
                        description 'Name of the class map, support 1-31 charac'
                                  + 'ters.'
                                    ;
                      }
                    }
                  }
                  container set {
                    description 'Mark a packet.'
                                ;
                    presence 'Mark a packet'
                             ;
                    container default-action {
                      description 'Configure default action'
                                  ;
                      presence 'Configure default action'
                               ;
                      leaf default-action {
                        description 'Set default action.'
                                    ;
                        type empty ;
                        mandatory true ;
                      }
                    }
                    container next-hop {
                      description 'Set next hop.'
                                  ;
                      presence 'Set next hop'
                               ;
                      choice next-hop {
                        description 'Set next hop.'
                                    ;
                        mandatory true ;
                        case ip-address {
                          description 'Configurate IP address as next-hop.'
                                      ;
                          container ip-address {
                            description 'Configurate IP address as next-hop.'
                                        ;
                            choice v4-v6-address {
                              description 'Configurate IP address as next-hop.'
                                          ;
                              mandatory true ;
                              case v4-addr {
                                description 'Configurate IPv4 address as next-hop.'
                                            ;
                                container ipv4-address {
                                  description 'Configurate IPv4 address as next-hop.'
                                              ;
                                  leaf ipv4-address {
                                    description 'IPv4 address.'
                                                ;
                                    type ncd:ipv4-address ;
                                    mandatory true ;
                                  }
                                  choice ipaddr-nexthop {
                                    description 'Set next hop based on IPv4 Address.'
                                                ;
                                    case vrf {
                                      description 'Configurate virtual route forwarding as next-hop.'
                                                  ;
                                      container vrf {
                                        description 'Configurate virtual route forwarding as next-hop.'
                                                    ;
                                        presence 'Configurate virtual route forwarding as next-hop'
                                                 ;
                                        leaf vrf-name {
                                          description 'Virtual route forwarding name, support 1-32 characters.'
                                                      ;
                                          type string {
                                            length 1..32 {
                                              description 'Virtual route forwarding name, support 1-32 characters.'
                                                          ;
                                            }
                                          }
                                          mandatory true ;
                                        }
                                      }
                                    }
                                    case interface {
                                      description 'Configurate interface as next-hop.'
                                                  ;
                                      container interface {
                                        description 'Configurate interface as next-hop.'
                                                    ;
                                        presence 'Configurate interface as next-hop'
                                                 ;
                                        leaf if-name {
                                          description 'Set interface name'
                                                      ;
                                          type ncd:ifname ;
                                          mandatory true ;
                                        }
                                      }
                                    }
                                  }
                                }
                              }
                              case v6-addr {
                                description 'Configurate IPv6 address as next-hop.'
                                            ;
                                container ipv6-address {
                                  description 'Configurate IPv6 address as next-hop.'
                                              ;
                                  leaf ipv6-address {
                                    description 'IPv6 address.'
                                                ;
                                    type ncd:ipv6-address ;
                                    mandatory true ;
                                  }
                                  choice ipaddr-nexthop {
                                    description 'Set next hop based on IPv4 Address.'
                                                ;
                                    case vrf {
                                      description 'Configurate virtual route forwarding as next-hop.'
                                                  ;
                                      container vrf {
                                        description 'Configurate virtual route forwarding as next-hop.'
                                                    ;
                                        presence 'Configurate virtual route forwarding as next-hop'
                                                 ;
                                        leaf vrf-name {
                                          description 'Virtual route forwarding name, support 1-32 characters.'
                                                      ;
                                          type string {
                                            length 1..32 {
                                              description 'Virtual route forwarding name, support 1-32 characters.'
                                                          ;
                                            }
                                          }
                                          mandatory true ;
                                        }
                                      }
                                    }
                                    case interface {
                                      description 'Configurate interface as next-hop.'
                                                  ;
                                      container interface {
                                        description 'Configurate interface as next-hop.'
                                                    ;
                                        presence 'Configurate interface as next-hop'
                                                 ;
                                        leaf if-name {
                                          description 'Set interface name'
                                                      ;
                                          type ncd:ifname ;
                                          mandatory true ;
                                        }
                                      }
                                    }
                                  }
                                }
                              }
                              ncd:revise-date 2019-06-27 ;
                            }
                          }
                        }
                        case interface {
                          description 'Configurate interface as next-hop.'
                                      ;
                          container interface {
                            description 'Configurate interface as next-hop..'
                                        ;
                            leaf if-name {
                              description 'Set interface name'
                                          ;
                              type ncd:ifname ;
                              mandatory true ;
                            }
                          }
                        }
                      }
                    }
                    container vxlan {
                      description 'Set VXLAN.'
                                  ;
                      presence 'Set VXLAN'
                               ;
                      choice v4-v6 {
                        description 'Select IPv4 or IPv6.'
                                    ;
                        mandatory true ;
                        case ipv4 {
                          description 'Specify IPv4'
                                      ;
                          container ipv4 {
                            description 'Specify IPv4'
                                        ;
                            leaf src-addr {
                              description 'Source address of VXLAN tunnel'
                                          ;
                              type ncd:ipv4-address ;
                              mandatory true ;
                            }
                            leaf dst-addr {
                              description 'Destination address of VXLAN tunnel'
                                          ;
                              type ncd:ipv4-address ;
                              mandatory true ;
                            }
                            leaf vni-id {
                              description 'VNI ID'
                                          ;
                              type uint32 {
                                range 1..16777215 {
                                  description 'VNI ID'
                                              ;
                                }
                              }
                              mandatory true ;
                            }
                          }
                        }
                        case ipv6 {
                          description 'Specify IPv6'
                                      ;
                          container ipv6 {
                            description 'Specify IPv6'
                                        ;
                            leaf src-addr {
                              description 'Source address of VXLAN tunnel'
                                          ;
                              type ncd:ipv6-address ;
                              mandatory true ;
                            }
                            leaf dst-addr {
                              description 'Destination address of VXLAN tunnel'
                                          ;
                              type ncd:ipv6-address ;
                              mandatory true ;
                            }
                            leaf vni-id {
                              description 'VNI ID'
                                          ;
                              type uint32 {
                                range 1..16777215 {
                                  description 'VNI ID'
                                              ;
                                }
                              }
                              mandatory true ;
                            }
                          }
                        }
                        ncd:revise-date 2020-03-05 ;
                      }
                    }
                  }
                }
              }
              container pmap-description {
                description 'Description of a policy map, support 1-79 characte'
                          + 'rs.'
                            ;
                presence 'Specify description of policy map'
                         ;
                leaf pmap-description {
                  description 'Description of a policy map, support 1-79 charac'
                            + 'ters.'
                              ;
                  type ncd:string-with-blank {
                    length 1..79 {
                      description 'Description of a policy map, support 1-79 ch'
                                + 'aracters.'
                                  ;
                    }
                  }
                  mandatory true ;
                }
                ncd:revise-date 2020-06-18 ;
              }
            }
          }
          ncd:revise-date 2019-04-15 ;
        }
        container traffic-based {
          description 'Policy map based on traffic'
                      ;
          container policy-maps {
            description 'Configure H-QoS policy map lists'
                        ;
            list policy-map {
              description 'Configure H-QoS policy maps'
                          ;
              key pmap-name ;
              leaf pmap-name {
                description 'Name of the policy map, support 1-31 characters'
                            ;
                type string {
                  length 1..31 {
                    description 'Name of the policy map, support 1-31 characters'
                                ;
                  }
                }
              }
              container class-maps {
                description 'Configure H-QoS policy class'
                            ;
                list class-map {
                  description 'Configure H-QoS policy class'
                              ;
                  key cmap-name ;
                  leaf cmap-name {
                    description 'Name of the class map, support 1-31 characters'
                                ;
                    type string {
                      length 1..31 {
                        description 'Name of the class map, support 1-31 charac'
                                  + 'ters'
                                    ;
                      }
                    }
                  }
                  container police {
                    description 'Configure traffic policing'
                                ;
                    presence 'Configure traffic policing'
                             ;
                    container mode {
                      description 'Set color mode'
                                  ;
                      presence 'Configure mode information'
                               ;
                      leaf mode-type {
                        description 'Color mode type, as follows,'+"\n"
                                  + '     blind   Color-Blind mode'+"\n"
                                  + '     aware   Color-Aware mode'
                                    ;
                        type enumeration {
                          enum blind {
                            value 1 ;
                            description 'Color-Blind mode'
                                        ;
                          }
                          enum aware {
                            value 2 ;
                            description 'Color-Aware mode'
                                        ;
                          }
                        }
                        mandatory true ;
                      }
                    }
                    choice buket-value-percent {
                      description 'Configure CIR, CBS, PIR and PBS.'
                                  ;
                      mandatory true ;
                      case buket-value {
                        description 'Configure CIR, CBS, PIR and PBS in numeric'
                                  + 'al form.'
                                    ;
                        container c-buket {
                          description 'Configure C-buket related parameters.'
                                      ;
                          container cir-value {
                            description 'Configure the CIR(Committed Information Rate).'
                                        ;
                            leaf cir {
                              description 'Configure the CIR(Committed Information Rate) value (default: kilobits per s'
                                        + 'econd)'
                                          ;
                              type uint32 {
                                range 8..4294967295 {
                                  description 'The CIR value (default: kilobits per second),support <8-4294967295>'
                                              ;
                                }
                              }
                              mandatory true ;
                            }
                            leaf cir-unit {
                              description 'set cir unit, such as kbps, mbps, gbps, pps.'
                                          ;
                              type qos-rate-unit-type-ex ;
                            }
                          }
                          container cbs-value {
                            description 'Configure the CBS(Committed Burst Size).'
                                        ;
                            presence cbs ;
                            leaf cbs {
                              description 'Configure the CBS(Committed Burst Size) value (default: kilobits)'
                                          ;
                              type uint32 {
                                range 1..4294967295 {
                                  description 'The CBS(Committed Burst Size) size in bytes, support <1-4294967295>'
                                              ;
                                }
                              }
                              mandatory true ;
                            }
                            leaf cbs-unit {
                              description 'set cbs unit, such as kb, mb, gb'
                                          ;
                              type qos-bucket-unit-type ;
                            }
                          }
                        }
                        container p-buket {
                          description 'Configure P-buket related parameters.'
                                      ;
                          presence p-buket ;
                          container pir-value {
                            description 'Configure the PIR(Peak Information Rate).'
                                        ;
                            leaf pir {
                              description 'Configure the PIR(Peak Information Rate) value (default: kilobits per second)'
                                          ;
                              type uint32 {
                                range 8..4294967295 {
                                  description 'The PIR(Peak Information Rate) value (default: kilobits per second), sup'
                                            + 'port <8-4294967295>'
                                              ;
                                }
                              }
                              mandatory true ;
                            }
                            leaf pir-unit {
                              description 'set pir unit, such as kbps, mbps, gbps, pps'
                                          ;
                              type qos-rate-unit-type-ex ;
                            }
                          }
                          container pbs-value {
                            description 'Configure the PBS(Peak Burst Size).'
                                        ;
                            presence pbs ;
                            leaf pbs {
                              description 'Configure the PBS(Peak Burst Size) value (default: kilobits).'
                                          ;
                              type uint32 {
                                range 1..4294967295 {
                                  description 'The PBS(Peak Burst Size) size in bytes, support <1-4294967295>'
                                              ;
                                }
                              }
                              mandatory true ;
                            }
                            leaf pbs-unit {
                              description 'set pbs unit, such as kb, mb, gb'
                                          ;
                              type qos-bucket-unit-type ;
                            }
                          }
                        }
                      }
                      case buket-percent {
                        description 'Configure CIR and PIR in percentage.'
                                    ;
                        container cir {
                          description 'Configure CIR in percentage.'
                                      ;
                          leaf cir-percent {
                            description 'Configure CIR in percentage.'
                                        ;
                            type uint8 {
                              range 1..100 {
                                description 'Configure CIR with percentage form'
                                            ;
                              }
                            }
                            mandatory true ;
                          }
                        }
                        container pir {
                          description 'Configure PIR in percentage.'
                                      ;
                          presence pir ;
                          leaf pir-percent {
                            description 'Configure PIR in percentage.'
                                        ;
                            type uint8 {
                              range 1..100 {
                                description 'Configure PIR with percentage form'
                                            ;
                              }
                            }
                            mandatory true ;
                          }
                        }
                      }
                    }
                    container action {
                      description 'Configure action to packets'
                                  ;
                      container conform-action {
                        description 'Action to packets that conform to the rate'
                                  + ' limit'
                                    ;
                        choice conform-action {
                          description 'Specify action to packets that conform t'
                                    + 'o the rate limit'
                                      ;
                          mandatory true ;
                          case ca-drop {
                            description 'Drop packet in conform-action'
                                        ;
                            leaf drop {
                              description 'Specify action to drop packet'
                                          ;
                              type empty ;
                              mandatory true ;
                            }
                          }
                          case ca-transmit {
                            description 'Transmit packet in conform-action'
                                        ;
                            leaf transmit {
                              description 'Specify action to transmit packet'
                                          ;
                              type empty ;
                              mandatory true ;
                            }
                          }
                          case ca-mpls-exp {
                            description 'Rewrite packet MPLS-EXP and transmit the packet'
                                        ;
                            leaf set-exp-transmit {
                              description 'Specify action to rewrite packet MPLS-EXP and transmit it'
                                          ;
                              type empty ;
                              mandatory true ;
                            }
                            leaf mpls-exp-value {
                              description 'Reset MPLS-EXP value in conform-action, support <0-7>'
                                          ;
                              type uint8 {
                                range 0..7 {
                                  description 'The MPLS-EXP value, support <0-7>'
                                              ;
                                }
                              }
                              mandatory true ;
                            }
                          }
                          case ca-precedence {
                            description 'Rewrite packet precedence and transmit the packet'
                                        ;
                            leaf set-prec-transmit {
                              description 'Specify action to rewrite packet precedence and transmit it'
                                          ;
                              type empty ;
                              mandatory true ;
                            }
                            leaf prec-value {
                              description 'Reset the IP-Precedence value in conform-action, support <0-7>'
                                          ;
                              type uint8 {
                                range 0..7 {
                                  description 'The IP-Precedence value, support <0-7>'
                                              ;
                                }
                              }
                              mandatory true ;
                            }
                          }
                          case ca-dscp {
                            description 'Rewrite packet DSCP and transmit the packet'
                                        ;
                            leaf set-dscp-transmit {
                              description 'Specify action to rewrite packet DSCP and transmit it'
                                          ;
                              type empty ;
                              mandatory true ;
                            }
                            leaf dscp-value {
                              description 'Reset DSCP in conform-action, support <0-63>'
                                          ;
                              type uint8 {
                                range 0..63 {
                                  description 'The DSCP value, support <0-63>'
                                              ;
                                }
                              }
                              mandatory true ;
                            }
                          }
                          case ca-8021p {
                            description 'Rewrite packet 802.1p and transmit the packet'
                                        ;
                            leaf set-8021p-transmit {
                              description 'Specify action to rewrite packet 802.1p and transmit it'
                                          ;
                              type empty ;
                              mandatory true ;
                            }
                            leaf value-8021p {
                              description 'Reset 802.1p in conform-action, support <0-7>'
                                          ;
                              type uint8 {
                                range 0..7 {
                                  description 'The 802.1p value, support <0-7>'
                                              ;
                                }
                              }
                              mandatory true ;
                            }
                          }
                          case ca-service-class {
                            description 'Specify action to rewrite packet service-class and transmit it'
                                        ;
                            leaf service-class-value {
                              description 'Reset service class in conform-action'
                                          ;
                              type qos-service-class ;
                              mandatory true ;
                            }
                          }
                        }
                      }
                      container exceed-action {
                        description 'Action to packets that exceed the rate lim'
                                  + 'it'
                                    ;
                        choice exceed-action {
                          description 'Specify action to packets that exceed th'
                                    + 'e rate limit'
                                      ;
                          mandatory true ;
                          case ea-drop {
                            description 'Drop packet in exceed-action'
                                        ;
                            leaf drop {
                              description 'Specify action to drop packet'
                                          ;
                              type empty ;
                              mandatory true ;
                            }
                          }
                          case ea-transmit {
                            description 'Transmit packet in exceed-action'
                                        ;
                            leaf transmit {
                              description 'Specify action to transmit packet'
                                          ;
                              type empty ;
                              mandatory true ;
                            }
                          }
                          case ea-mpls-exp {
                            description 'Rewrite packet MPLS-EXP and transmit the packet'
                                        ;
                            leaf set-exp-transmit {
                              description 'Specify action to rewrite packet MPLS-EXP and transmit it'
                                          ;
                              type empty ;
                              mandatory true ;
                            }
                            leaf mpls-exp-value {
                              description 'Reset MPLS-EXP value in exceed-action, support <0-7>'
                                          ;
                              type uint8 {
                                range 0..7 {
                                  description 'The MPLS-EXP value, support <0-7>'
                                              ;
                                }
                              }
                              mandatory true ;
                            }
                          }
                          case ea-precedence {
                            description 'Rewrite packet precedence and transmit the packet'
                                        ;
                            leaf set-prec-transmit {
                              description 'Specify action to rewrite packet precedence and transmit it'
                                          ;
                              type empty ;
                              mandatory true ;
                            }
                            leaf prec-value {
                              description 'Reset the IP-Precedence value in exceed-action, support <0-7>'
                                          ;
                              type uint8 {
                                range 0..7 {
                                  description 'The IP-Precedence value, support <0-7>'
                                              ;
                                }
                              }
                              mandatory true ;
                            }
                          }
                          case ea-dscp {
                            description 'Rewrite packet DSCP and transmit the packet'
                                        ;
                            leaf set-dscp-transmit {
                              description 'Specify action to rewrite packet DSCP and transmit it'
                                          ;
                              type empty ;
                              mandatory true ;
                            }
                            leaf dscp-value {
                              description 'Reset DSCP in exceed-action, support <0-63>'
                                          ;
                              type uint8 {
                                range 0..63 {
                                  description 'The DSCP value, support <0-63>'
                                              ;
                                }
                              }
                              mandatory true ;
                            }
                          }
                          case ea-8021p {
                            description 'Rewrite packet 802.1p and transmit the packet'
                                        ;
                            leaf set-8021p-transmit {
                              description 'Specify action to rewrite packet 802.1p and transmit it'
                                          ;
                              type empty ;
                              mandatory true ;
                            }
                            leaf value-8021p {
                              description 'Reset 802.1p in exceed-action, support <0-7>'
                                          ;
                              type uint8 {
                                range 0..7 {
                                  description 'The 802.1p value, support <0-7>'
                                              ;
                                }
                              }
                              mandatory true ;
                            }
                          }
                          case ea-service-class {
                            description 'Specify action to rewrite packet service class and transmit it'
                                        ;
                            leaf service-class-value {
                              description 'Reset service class in exceed-action'
                                          ;
                              type qos-service-class ;
                              mandatory true ;
                            }
                          }
                        }
                      }
                      container violate-action {
                        description 'Action to packets that violate the rate li'
                                  + 'mit'
                                    ;
                        choice violate-action {
                          description 'Specify action to packets that violate t'
                                    + 'he rate limit'
                                      ;
                          mandatory true ;
                          case va-drop {
                            description 'Drop packet in violate-action'
                                        ;
                            leaf drop {
                              description 'Specify action to drop packet'
                                          ;
                              type empty ;
                              mandatory true ;
                            }
                          }
                          case va-transmit {
                            description 'Transmit packet in violate-action'
                                        ;
                            leaf transmit {
                              description 'Specify action to transmit packet'
                                          ;
                              type empty ;
                              mandatory true ;
                            }
                          }
                          case va-mpls-exp {
                            description 'Rewrite packet MPLS-EXP and transmit the packet'
                                        ;
                            leaf set-exp-transmit {
                              description 'Specify action to rewrite packet MPLS-EXP and transmit it'
                                          ;
                              type empty ;
                              mandatory true ;
                            }
                            leaf mpls-exp-value {
                              description 'Reset MPLS-EXP value in violate-action, support <0-7>'
                                          ;
                              type uint8 {
                                range 0..7 {
                                  description 'The MPLS-EXP value, support <0-7>'
                                              ;
                                }
                              }
                              mandatory true ;
                            }
                          }
                          case va-precedence {
                            description 'Rewrite packet precedence and transmit the packet'
                                        ;
                            leaf set-prec-transmit {
                              description 'Specify action to rewrite packet precedence and transmit it'
                                          ;
                              type empty ;
                              mandatory true ;
                            }
                            leaf prec-value {
                              description 'Reset the IP-Precedence value in violate-action, support <0-7>'
                                          ;
                              type uint8 {
                                range 0..7 {
                                  description 'The IP-Precedence value, support <0-7>'
                                              ;
                                }
                              }
                              mandatory true ;
                            }
                          }
                          case va-dscp {
                            description 'Rewrite packet DSCP and transmit the packet'
                                        ;
                            leaf set-dscp-transmit {
                              description 'Specify action to rewrite packet DSCP and transmit it'
                                          ;
                              type empty ;
                              mandatory true ;
                            }
                            leaf dscp-value {
                              description 'Reset DSCP in violate-action, support <0-63>'
                                          ;
                              type uint8 {
                                range 0..63 {
                                  description 'The DSCP value, support <0-63>'
                                              ;
                                }
                              }
                              mandatory true ;
                            }
                          }
                          case va-8021p {
                            description 'Rewrite packet 802.1p and transmit the packet'
                                        ;
                            leaf set-8021p-transmit {
                              description 'Specify action to rewrite packet 802.1p and transmit it'
                                          ;
                              type empty ;
                              mandatory true ;
                            }
                            leaf value-8021p {
                              description 'Reset 802.1p in violate-action, support <0-7>'
                                          ;
                              type uint8 {
                                range 0..7 {
                                  description 'The 802.1p value, support <0-7>'
                                              ;
                                }
                              }
                              mandatory true ;
                            }
                          }
                          case va-service-class {
                            description 'Specify action to rewrite packet service class and transmit it'
                                        ;
                            leaf service-class-value {
                              description 'Reset service class in violate-action'
                                          ;
                              type qos-service-class ;
                              mandatory true ;
                            }
                          }
                        }
                      }
                    }
                  }
                  container mirror {
                    description 'Configure mirror.'
                                ;
                    presence 'Configure mirror'
                             ;
                    leaf session-id {
                      description 'Set the session id.'
                                  ;
                      type uint32 {
                        range 1..4294967295 {
                          description 'Set the session id.'
                                      ;
                        }
                      }
                      mandatory true ;
                    }
                  }
                  container set {
                    description 'Mark a packet'
                                ;
                    container service-class {
                      description 'Configure service class'
                                  ;
                      presence 'Configure service function path'
                               ;
                      leaf service-class {
                        description 'Select service class of PHB info, see belo'
                                  + 'w:'+"\n"
                                  + '  be (1) Best effort'+"\n"
                                  + '  af1(2) Assured forwarding class 1'+"\n"
                                  + '  af2(3) Assured forwarding class 2'+"\n"
                                  + '  af3(4) Assured forwarding class 3'+"\n"
                                  + '  af4(5) Assured forwarding class 4'+"\n"
                                  + '  ef (6) Expedited forward'+"\n"
                                  + '  cs6(7) Internetwork control service clas'
                                  + 's'+"\n"
                                  + '  cs7(8) Network control service class'
                                    ;
                        type qos-service-class ;
                        mandatory true ;
                      }
                      leaf color-type {
                        description 'Specify packets color, support <green,yell'
                                  + 'ow,red>'
                                    ;
                        type qos-color-type ;
                      }
                    }
                    container dscp {
                      description 'Select DSCP as mark type'
                                  ;
                      presence 'Select DSCP as mark typ'
                               ;
                      choice method {
                        description 'Specify the method to set DSCP'
                                    ;
                        mandatory true ;
                        case set-value {
                          description 'Set the DSCP value directly'
                                      ;
                          container set-value {
                            description 'Set the DSCP value directly'
                                        ;
                            leaf dscp-value {
                              description 'DSCP value, support <0-63>'
                                          ;
                              type uint16 {
                                range 0..63 {
                                  description 'DSCP value, support <0-63>'
                                              ;
                                }
                              }
                              mandatory true ;
                            }
                          }
                        }
                        case inherit {
                          status obsolete ;
                          description 'Set the DSCP value by inheriting'
                                      ;
                          container inherit {
                            description 'Set the DSCP value by inheriting'
                                        ;
                            leaf inherit-type {
                              description 'Specify the source inherit type, such as precedence, mpls-exp, 8021p, dscp, '
                                        + 'pay-load 8021p'
                                          ;
                              type enumeration {
                                enum precedence {
                                  value 1 ;
                                  description 'Select precedence as source inherit'
                                              ;
                                }
                                enum mpls-exp {
                                  value 2 ;
                                  description 'Select MPLS-EXP as source inherit'
                                              ;
                                }
                                enum 8021p {
                                  value 3 ;
                                  description 'Select 802.1p as source inherit'
                                              ;
                                }
                                enum dscp {
                                  value 4 ;
                                  description 'Select dscp as source inherit'
                                              ;
                                }
                                enum pay-load-8021p {
                                  value 6 ;
                                  description 'Select inner 802.1p as source inherit'
                                              ;
                                }
                              }
                              mandatory true ;
                            }
                          }
                        }
                      }
                      ncd:revise-date 2021-01-25 ;
                    }
                    container precedence {
                      description 'Select precedence as mark type'
                                  ;
                      presence 'Select precedence as mark type'
                               ;
                      choice method {
                        description 'Specify the method to set IP Precedence'
                                    ;
                        mandatory true ;
                        case set-value {
                          description 'Set the IP Precedence value directly'
                                      ;
                          container set-value {
                            description 'Set the IP Precedence value directly'
                                        ;
                            leaf prec-value {
                              description 'IP Precedence value, support <0-7>'
                                          ;
                              type uint16 {
                                range 0..7 {
                                  description 'IP Precedence value, support <0-7>'
                                              ;
                                }
                              }
                              mandatory true ;
                            }
                          }
                        }
                        case inherit {
                          status obsolete ;
                          description 'Set the IP Precedence value by inheriting'
                                      ;
                          container inherit {
                            description 'Set the IP Precedence value by inheriting'
                                        ;
                            leaf inherit-type {
                              description 'Specify the source inherit type, such as precedence, mpls-exp, 8021p, dscp'
                                          ;
                              type enumeration {
                                enum precedence {
                                  value 1 ;
                                  description 'Select precedence as source inherit'
                                              ;
                                }
                                enum mpls-exp {
                                  value 2 ;
                                  description 'Select MPLS-EXP as source inherit'
                                              ;
                                }
                                enum 8021p {
                                  value 3 ;
                                  description 'Select 802.1p as source inherit'
                                              ;
                                }
                                enum dscp {
                                  value 4 ;
                                  description 'Select dscp as source inherit'
                                              ;
                                }
                              }
                              mandatory true ;
                            }
                          }
                        }
                      }
                      ncd:revise-date 2021-01-25 ;
                    }
                    container pri-8021p {
                      description 'Select 802.1p as mark type'
                                  ;
                      presence 'Select 802.1p as mark type'
                               ;
                      choice method {
                        description 'Specify the method to set 802.1p'
                                    ;
                        mandatory true ;
                        case set-value {
                          description 'Set the 802.1p value directly'
                                      ;
                          container set-value {
                            description 'Set the 802.1p value directly'
                                        ;
                            leaf value-8021p {
                              description '802.1p value, support <0-7>'
                                          ;
                              type uint16 {
                                range 0..7 {
                                  description '802.1p value, support <0-7>'
                                              ;
                                }
                              }
                              mandatory true ;
                            }
                            leaf inner-outer {
                              description 'Set 8021p inner or outer flag.If vlaue is 0, it means outer flag. If value i'
                                        + 's 1,it means inner and outer flag.'
                                          ;
                              type uint8 {
                                range 0..1 {
                                  description 'Inner or outer flag. 0 is outer. 1 is inner and outer'
                                              ;
                                }
                              }
                              default 0 ;
                            }
                          }
                        }
                        case inherit {
                          status obsolete ;
                          description 'Set the 802.1p value by inheriting'
                                      ;
                          container inherit {
                            description 'Set the 802.1p value by inheriting'
                                        ;
                            leaf inherit-type {
                              description 'Specify the source inherit type, such as precedence, mpls-exp, 8021p, dscp'
                                          ;
                              type enumeration {
                                enum precedence {
                                  value 1 ;
                                  description 'Select precedence as source inherit'
                                              ;
                                }
                                enum mpls-exp {
                                  value 2 ;
                                  description 'Select MPLS-EXP as source inherit'
                                              ;
                                }
                                enum 8021p {
                                  value 3 ;
                                  description 'Select 802.1p as source inherit'
                                              ;
                                }
                                enum dscp {
                                  value 4 ;
                                  description 'Select dscp as source inherit'
                                              ;
                                }
                              }
                              mandatory true ;
                            }
                            leaf inner-outer {
                              description 'Set 8021p inner or outer flag.If vlaue is 0, it means outer flag. If value i'
                                        + 's 1,it means inner and outer flag.'
                                          ;
                              type uint8 {
                                range 0..1 {
                                  description 'Inner or outer flag. 0 is outer. 1 is inner and outer'
                                              ;
                                }
                              }
                              default 0 ;
                            }
                          }
                        }
                      }
                      ncd:revise-date 2021-01-25 ;
                    }
                    container mpls-exp {
                      description 'Select MPLS-EXP as mark type'
                                  ;
                      presence 'Select MPLS-EXP as mark type'
                               ;
                      leaf label-type {
                        if-feature policy-action-set-label ;
                        description 'Select MPLS-EXP label position, such as '+"\n"
                                  + '    default    The default for topmost lab'
                                  + 'el'+"\n"
                                  + '    topmost    Set the MPLS-EXP value on t'
                                  + 'opmost label'+"\n"
                                  + '    imposition Set the MPLS-EXP value on a'
                                  + 'll imposed labels'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on all imposed labels'
                                        ;
                          }
                          enum default {
                            value 0 ;
                            description 'The default for topmost label'
                                        ;
                          }
                          enum inner {
                            value 3 ;
                            description 'Set the MPLS-EXP value on inner label'
                                        ;
                          }
                        }
                      }
                      choice method {
                        description 'Specify the method to set MPLS-EXP'
                                    ;
                        mandatory true ;
                        case set-value {
                          description 'Set the MPLS-EXP value directly'
                                      ;
                          container set-value {
                            description 'Set the MPLS-EXP value directly'
                                        ;
                            leaf mpls-exp-value {
                              description 'MPLS-EXP value, support <0-7>'
                                          ;
                              type uint16 {
                                range 0..7 {
                                  description 'MPLS-EXP value, support <0-7>'
                                              ;
                                }
                              }
                              mandatory true ;
                            }
                          }
                        }
                        case inherit {
                          status obsolete ;
                          description 'Set the MPLS-EXP value by inheriting'
                                      ;
                          container inherit {
                            description 'Set the MPLS-EXP value by inheriting'
                                        ;
                            leaf inherit-type {
                              description 'Specify the source inherit type, such as precedence, mpls-exp, 8021p, dscp'
                                          ;
                              type enumeration {
                                enum precedence {
                                  value 1 ;
                                  description 'Select precedence as source inherit'
                                              ;
                                }
                                enum mpls-exp {
                                  value 2 ;
                                  description 'Select MPLS-EXP as source inherit'
                                              ;
                                }
                                enum 8021p {
                                  value 3 ;
                                  description 'Select 802.1p as source inherit'
                                              ;
                                }
                                enum dscp {
                                  value 4 ;
                                  description 'Select dscp as source inherit'
                                              ;
                                }
                              }
                              mandatory true ;
                            }
                          }
                        }
                      }
                      ncd:revise-date 2021-01-25 ;
                    }
                    container vlan-id {
                      description 'Configure VLAN ID'
                                  ;
                      presence 'Configure VLAN ID'
                               ;
                      leaf vlan-value {
                        description 'Set VLAN ID, support <1-4094>'
                                    ;
                        type uint16 {
                          range 1..4094 ;
                        }
                        mandatory true ;
                      }
                      ncd:revise-date 2021-01-25 ;
                    }
                  }
                  container urpf-type {
                    description 'Configure URPF(Unicast Reverse Path Forwarding'
                              + ') type:IPv4 urpf or IPv6 urpf.'
                                ;
                    presence 'Configure URPF type'
                             ;
                    choice ip-type {
                      description 'Configure the IP protocol type of URPF(Unica'
                                + 'st Reverse Path Forwarding):IPv4 or IPv6.'
                                  ;
                      mandatory true ;
                      case ipv4 {
                        description 'Configure IPv4 URPF(Unicast Reverse Path F'
                                  + 'orwarding) type.'
                                    ;
                        leaf ipv4 {
                          description 'IPv4 URPF type.'
                                      ;
                          type empty ;
                          mandatory true ;
                        }
                      }
                      case ipv6 {
                        description 'Configure IPv6 URPF(Unicast Reverse Path F'
                                  + 'orwarding) type.'
                                    ;
                        leaf ipv6 {
                          description 'IPv6 URPF type.'
                                      ;
                          type empty ;
                          mandatory true ;
                        }
                      }
                    }
                  }
                  container statistics {
                    description 'Configure the statistics function of class.'
                                ;
                    presence 'Configure statistics function'
                             ;
                    leaf statis-enable {
                      description 'Enable the statistics function.'
                                  ;
                      type empty ;
                      mandatory true ;
                    }
                  }
                  container drop {
                    description 'Configure drop'
                                ;
                    presence 'Configure drop'
                             ;
                    leaf drop {
                      description 'Specify drop'
                                  ;
                      type empty ;
                      mandatory true ;
                    }
                    ncd:revise-date 2021-01-11 ;
                  }
                  container redirect {
                    if-feature policy-action-rediret-route-map ;
                    description 'Configure redirect route-map'
                                ;
                    container route-map {
                      description 'Configure redirect route-map'
                                  ;
                      presence 'Configure redirect route-map'
                               ;
                      leaf route-map-name {
                        description 'The name of route-map'
                                    ;
                        type string {
                          length 1..200 ;
                        }
                        mandatory true ;
                      }
                      leaf route-map-type {
                        description 'The type of route-map,IPv4 or IPv6'
                                    ;
                        type enumeration {
                          enum ipv4 {
                            value 1 ;
                          }
                          enum ipv6 {
                            value 2 ;
                          }
                        }
                        mandatory true ;
                      }
                      leaf vrf-name {
                        description 'VRF name'
                                    ;
                        type string {
                          length 1..32 ;
                        }
                      }
                    }
                    ncd:revise-date 2021-01-25 ;
                  }
                  container vlan-stacking {
                    if-feature policy-action-vlan-stacking ;
                    description 'Configure vlan-stacking'
                                ;
                    presence 'Configure vlan-stacking'
                             ;
                    leaf value {
                      description 'Set the value of vlan-stack'
                                  ;
                      type uint16 {
                        range 1..4094 ;
                      }
                      mandatory true ;
                    }
                    leaf priority {
                      description 'Set the priority of vlan-stack'
                                  ;
                      type uint8 {
                        range 0..7 ;
                      }
                      mandatory true ;
                    }
                    ncd:revise-date 2021-01-25 ;
                  }
                }
                container class-default {
                  description 'Select the default class'
                              ;
                  presence 'Specify the default class'
                           ;
                  leaf class-default {
                    description 'Specify the default class'
                                ;
                    type empty ;
                    mandatory true ;
                  }
                  container police {
                    description 'Configure traffic policing'
                                ;
                    presence 'Configure traffic policing'
                             ;
                    container mode {
                      description 'Set color mode'
                                  ;
                      presence 'Configure mode information'
                               ;
                      leaf mode-type {
                        description 'Color mode type, as follows,'+"\n"
                                  + '     blind   Color-Blind mode'+"\n"
                                  + '     aware   Color-Aware mode'
                                    ;
                        type enumeration {
                          enum blind {
                            value 1 ;
                            description 'Color-Blind mode'
                                        ;
                          }
                          enum aware {
                            value 2 ;
                            description 'Color-Aware mode'
                                        ;
                          }
                        }
                        mandatory true ;
                      }
                    }
                    choice buket-value-percent {
                      description 'Configure CIR, CBS, PIR and PBS.'
                                  ;
                      mandatory true ;
                      case buket-value {
                        description 'Configure CIR, CBS, PIR and PBS in numeric'
                                  + 'al form.'
                                    ;
                        container c-buket {
                          description 'Configure C-buket related parameters.'
                                      ;
                          container cir-value {
                            description 'Configure the CIR(Committed Information Rate).'
                                        ;
                            leaf cir {
                              description 'Configure the CIR(Committed Information Rate) value (default: kilobits per s'
                                        + 'econd)'
                                          ;
                              type uint32 {
                                range 8..4294967295 {
                                  description 'The CIR value (default: kilobits per second),support <8-4294967295>'
                                              ;
                                }
                              }
                              mandatory true ;
                            }
                            leaf cir-unit {
                              description 'set cir unit, such as kbps, mbps, gbps, pps'
                                          ;
                              type qos-rate-unit-type-ex ;
                            }
                          }
                          container cbs-value {
                            description 'Configure the CBS(Committed Burst Size).'
                                        ;
                            presence cbs ;
                            leaf cbs {
                              description 'Configure the CBS(Committed Burst Size) value (default: kilobits)'
                                          ;
                              type uint32 {
                                range 1..4294967295 {
                                  description 'The CBS(Committed Burst Size) size in bytes, support <1-4294967295>'
                                              ;
                                }
                              }
                              mandatory true ;
                            }
                            leaf cbs-unit {
                              description 'set cbs unit, such as kb, mb, gb'
                                          ;
                              type qos-bucket-unit-type ;
                            }
                          }
                        }
                        container p-buket {
                          description 'Configure P-buket related parameters.'
                                      ;
                          presence p-buket ;
                          container pir-value {
                            description 'Configure the PIR(Peak Information Rate).'
                                        ;
                            leaf pir {
                              description 'Configure the PIR(Peak Information Rate) value (default: kilobits per second)'
                                          ;
                              type uint32 {
                                range 8..4294967295 {
                                  description 'The PIR(Peak Information Rate) value (default: kilobits per second), sup'
                                            + 'port <8-4294967295>'
                                              ;
                                }
                              }
                              mandatory true ;
                            }
                            leaf pir-unit {
                              description 'set pir unit, such as kbps, mbps, gbps, pps'
                                          ;
                              type qos-rate-unit-type-ex ;
                            }
                          }
                          container pbs-value {
                            description 'Configure the PBS(Peak Burst Size).'
                                        ;
                            presence pbs ;
                            leaf pbs {
                              description 'Configure the PBS(Peak Burst Size) value (default: kilobits).'
                                          ;
                              type uint32 {
                                range 1..4294967295 {
                                  description 'The PBS(Peak Burst Size) size in bytes, support <1-4294967295>'
                                              ;
                                }
                              }
                              mandatory true ;
                            }
                            leaf pbs-unit {
                              description 'set pbs unit, such as kb, mb, gb'
                                          ;
                              type qos-bucket-unit-type ;
                            }
                          }
                        }
                      }
                      case buket-percent {
                        description 'Configure CIR and PIR in percentage.'
                                    ;
                        container cir {
                          description 'Configure CIR in percentage.'
                                      ;
                          leaf cir-percent {
                            description 'Configure CIR in percentage.'
                                        ;
                            type uint8 {
                              range 1..100 {
                                description 'Configure CIR with percentage form'
                                            ;
                              }
                            }
                            mandatory true ;
                          }
                        }
                        container pir {
                          description 'Configure PIR in percentage.'
                                      ;
                          presence pir ;
                          leaf pir-percent {
                            description 'Configure PIR in percentage.'
                                        ;
                            type uint8 {
                              range 1..100 {
                                description 'Configure PIR with percentage form'
                                            ;
                              }
                            }
                            mandatory true ;
                          }
                        }
                      }
                    }
                    container action {
                      description 'Configure action to packets'
                                  ;
                      container conform-action {
                        description 'Action to packets that conform to the rate'
                                  + ' limit'
                                    ;
                        choice conform-action {
                          description 'Specify action to packets that conform t'
                                    + 'o the rate limit'
                                      ;
                          mandatory true ;
                          case ca-drop {
                            description 'Drop packet in conform-action'
                                        ;
                            leaf drop {
                              description 'Specify action to drop packet'
                                          ;
                              type empty ;
                              mandatory true ;
                            }
                          }
                          case ca-transmit {
                            description 'Transmit packet in conform-action'
                                        ;
                            leaf transmit {
                              description 'Specify action to transmit packet'
                                          ;
                              type empty ;
                              mandatory true ;
                            }
                          }
                          case ca-mpls-exp {
                            description 'Rewrite packet MPLS-EXP and transmit the packet'
                                        ;
                            leaf set-exp-transmit {
                              description 'Specify action to rewrite packet MPLS-EXP and transmit it'
                                          ;
                              type empty ;
                              mandatory true ;
                            }
                            leaf mpls-exp-value {
                              description 'Reset MPLS-EXP value in conform-action, support <0-7>'
                                          ;
                              type uint8 {
                                range 0..7 {
                                  description 'The MPLS-EXP value, support <0-7>'
                                              ;
                                }
                              }
                              mandatory true ;
                            }
                          }
                          case ca-precedence {
                            description 'Rewrite packet precedence and transmit the packet'
                                        ;
                            leaf set-prec-transmit {
                              description 'Specify action to rewrite packet precedence and transmit it'
                                          ;
                              type empty ;
                              mandatory true ;
                            }
                            leaf prec-value {
                              description 'Reset the IP-Precedence value in conform-action, support <0-7>'
                                          ;
                              type uint8 {
                                range 0..7 {
                                  description 'The IP-Precedence value, support <0-7>'
                                              ;
                                }
                              }
                              mandatory true ;
                            }
                          }
                          case ca-dscp {
                            description 'Rewrite packet DSCP and transmit the packet'
                                        ;
                            leaf set-dscp-transmit {
                              description 'Specify action to rewrite packet DSCP and transmit it'
                                          ;
                              type empty ;
                              mandatory true ;
                            }
                            leaf dscp-value {
                              description 'Reset DSCP in conform-action, support <0-63>'
                                          ;
                              type uint8 {
                                range 0..63 {
                                  description 'The DSCP value, support <0-63>'
                                              ;
                                }
                              }
                              mandatory true ;
                            }
                          }
                          case ca-8021p {
                            description 'Rewrite packet 802.1p and transmit the packet'
                                        ;
                            leaf set-8021p-transmit {
                              description 'Specify action to rewrite packet 802.1p and transmit it'
                                          ;
                              type empty ;
                              mandatory true ;
                            }
                            leaf value-8021p {
                              description 'Reset 802.1p in conform-action, support <0-7>'
                                          ;
                              type uint8 {
                                range 0..7 {
                                  description 'The 802.1p value, support <0-7>'
                                              ;
                                }
                              }
                              mandatory true ;
                            }
                          }
                          case ca-service-class {
                            description 'Specify action to rewrite packet service-class and transmit it'
                                        ;
                            leaf service-class-value {
                              description 'Reset service class in conform-action'
                                          ;
                              type qos-service-class ;
                              mandatory true ;
                            }
                          }
                        }
                      }
                      container exceed-action {
                        description 'Action to packets that exceed the rate lim'
                                  + 'it'
                                    ;
                        choice exceed-action {
                          description 'Specify action to packets that exceed th'
                                    + 'e rate limit'
                                      ;
                          mandatory true ;
                          case ea-drop {
                            description 'Drop packet in exceed-action'
                                        ;
                            leaf drop {
                              description 'Specify action to drop packet'
                                          ;
                              type empty ;
                              mandatory true ;
                            }
                          }
                          case ea-transmit {
                            description 'Transmit packet in exceed-action'
                                        ;
                            leaf transmit {
                              description 'Specify action to transmit packet'
                                          ;
                              type empty ;
                              mandatory true ;
                            }
                          }
                          case ea-mpls-exp {
                            description 'Rewrite packet MPLS-EXP and transmit the packet'
                                        ;
                            leaf set-exp-transmit {
                              description 'Specify action to rewrite packet MPLS-EXP and transmit it'
                                          ;
                              type empty ;
                              mandatory true ;
                            }
                            leaf mpls-exp-value {
                              description 'Reset MPLS-EXP value in exceed-action, support <0-7>'
                                          ;
                              type uint8 {
                                range 0..7 {
                                  description 'The MPLS-EXP value, support <0-7>'
                                              ;
                                }
                              }
                              mandatory true ;
                            }
                          }
                          case ea-precedence {
                            description 'Rewrite packet precedence and transmit the packet'
                                        ;
                            leaf set-prec-transmit {
                              description 'Specify action to rewrite packet precedence and transmit it'
                                          ;
                              type empty ;
                              mandatory true ;
                            }
                            leaf prec-value {
                              description 'Reset the IP-Precedence value in exceed-action, support <0-7>'
                                          ;
                              type uint8 {
                                range 0..7 {
                                  description 'The IP-Precedence value, support <0-7>'
                                              ;
                                }
                              }
                              mandatory true ;
                            }
                          }
                          case ea-dscp {
                            description 'Rewrite packet DSCP and transmit the packet'
                                        ;
                            leaf set-dscp-transmit {
                              description 'Specify action to rewrite packet DSCP and transmit it'
                                          ;
                              type empty ;
                              mandatory true ;
                            }
                            leaf dscp-value {
                              description 'Reset DSCP in exceed-action, support <0-63>'
                                          ;
                              type uint8 {
                                range 0..63 {
                                  description 'The DSCP value, support <0-63>'
                                              ;
                                }
                              }
                              mandatory true ;
                            }
                          }
                          case ea-8021p {
                            description 'Rewrite packet 802.1p and transmit the packet'
                                        ;
                            leaf set-8021p-transmit {
                              description 'Specify action to rewrite packet 802.1p and transmit it'
                                          ;
                              type empty ;
                              mandatory true ;
                            }
                            leaf value-8021p {
                              description 'Reset 802.1p in exceed-action, support <0-7>'
                                          ;
                              type uint8 {
                                range 0..7 {
                                  description 'The 802.1p value, support <0-7>'
                                              ;
                                }
                              }
                              mandatory true ;
                            }
                          }
                          case ea-service-class {
                            description 'Specify action to rewrite packet service class and transmit it'
                                        ;
                            leaf service-class-value {
                              description 'Reset service class in exceed-action'
                                          ;
                              type qos-service-class ;
                              mandatory true ;
                            }
                          }
                        }
                      }
                      container violate-action {
                        description 'Action to packets that violate the rate li'
                                  + 'mit'
                                    ;
                        choice violate-action {
                          description 'Specify action to packets that violate t'
                                    + 'he rate limit'
                                      ;
                          mandatory true ;
                          case va-drop {
                            description 'Drop packet in violate-action'
                                        ;
                            leaf drop {
                              description 'Specify action to drop packet'
                                          ;
                              type empty ;
                              mandatory true ;
                            }
                          }
                          case va-transmit {
                            description 'Transmit packet in violate-action'
                                        ;
                            leaf transmit {
                              description 'Specify action to transmit packet'
                                          ;
                              type empty ;
                              mandatory true ;
                            }
                          }
                          case va-mpls-exp {
                            description 'Rewrite packet MPLS-EXP and transmit the packet'
                                        ;
                            leaf set-exp-transmit {
                              description 'Specify action to rewrite packet MPLS-EXP and transmit it'
                                          ;
                              type empty ;
                              mandatory true ;
                            }
                            leaf mpls-exp-value {
                              description 'Reset MPLS-EXP value in violate-action, support <0-7>'
                                          ;
                              type uint8 {
                                range 0..7 {
                                  description 'The MPLS-EXP value, support <0-7>'
                                              ;
                                }
                              }
                              mandatory true ;
                            }
                          }
                          case va-precedence {
                            description 'Rewrite packet precedence and transmit the packet'
                                        ;
                            leaf set-prec-transmit {
                              description 'Specify action to rewrite packet precedence and transmit it'
                                          ;
                              type empty ;
                              mandatory true ;
                            }
                            leaf prec-value {
                              description 'Reset the IP-Precedence value in violate-action, support <0-7>'
                                          ;
                              type uint8 {
                                range 0..7 {
                                  description 'The IP-Precedence value, support <0-7>'
                                              ;
                                }
                              }
                              mandatory true ;
                            }
                          }
                          case va-dscp {
                            description 'Rewrite packet DSCP and transmit the packet'
                                        ;
                            leaf set-dscp-transmit {
                              description 'Specify action to rewrite packet DSCP and transmit it'
                                          ;
                              type empty ;
                              mandatory true ;
                            }
                            leaf dscp-value {
                              description 'Reset DSCP in violate-action, support <0-63>'
                                          ;
                              type uint8 {
                                range 0..63 {
                                  description 'The DSCP value, support <0-63>'
                                              ;
                                }
                              }
                              mandatory true ;
                            }
                          }
                          case va-8021p {
                            description 'Rewrite packet 802.1p and transmit the packet'
                                        ;
                            leaf set-8021p-transmit {
                              description 'Specify action to rewrite packet 802.1p and transmit it'
                                          ;
                              type empty ;
                              mandatory true ;
                            }
                            leaf value-8021p {
                              description 'Reset 802.1p in violate-action, support <0-7>'
                                          ;
                              type uint8 {
                                range 0..7 {
                                  description 'The 802.1p value, support <0-7>'
                                              ;
                                }
                              }
                              mandatory true ;
                            }
                          }
                          case va-service-class {
                            description 'Specify action to rewrite packet service class and transmit it'
                                        ;
                            leaf service-class-value {
                              description 'Reset service class in violate-action'
                                          ;
                              type qos-service-class ;
                              mandatory true ;
                            }
                          }
                        }
                      }
                    }
                  }
                  container mirror {
                    description 'Configure mirror.'
                                ;
                    presence 'Configure mirror'
                             ;
                    leaf session-id {
                      description 'Set the session id.'
                                  ;
                      type uint32 {
                        range 1..4294967295 {
                          description 'Set the session id.'
                                      ;
                        }
                      }
                      mandatory true ;
                    }
                  }
                  container set {
                    description 'Mark a packet'
                                ;
                    container service-class {
                      description 'Configure service class'
                                  ;
                      presence 'Configure service function path'
                               ;
                      leaf service-class {
                        description 'Select service class of PHB info, see belo'
                                  + 'w:'+"\n"
                                  + '  be (1) Best effort'+"\n"
                                  + '  af1(2) Assured forwarding class 1'+"\n"
                                  + '  af2(3) Assured forwarding class 2'+"\n"
                                  + '  af3(4) Assured forwarding class 3'+"\n"
                                  + '  af4(5) Assured forwarding class 4'+"\n"
                                  + '  ef (6) Expedited forward'+"\n"
                                  + '  cs6(7) Internetwork control service clas'
                                  + 's'+"\n"
                                  + '  cs7(8) Network control service class'
                                    ;
                        type qos-service-class ;
                        mandatory true ;
                      }
                      leaf color-type {
                        description 'Specify packets color, support <green,yell'
                                  + 'ow,red>'
                                    ;
                        type qos-color-type ;
                      }
                    }
                    container dscp {
                      description 'Select DSCP as mark type'
                                  ;
                      presence 'Select DSCP as mark typ'
                               ;
                      choice method {
                        description 'Specify the method to set DSCP'
                                    ;
                        mandatory true ;
                        case set-value {
                          description 'Set the DSCP value directly'
                                      ;
                          container set-value {
                            description 'Set the DSCP value directly'
                                        ;
                            leaf dscp-value {
                              description 'DSCP value, support <0-63>'
                                          ;
                              type uint16 {
                                range 0..63 {
                                  description 'DSCP value, support <0-63>'
                                              ;
                                }
                              }
                              mandatory true ;
                            }
                          }
                        }
                        case inherit {
                          status obsolete ;
                          description 'Set the DSCP value by inheriting'
                                      ;
                          container inherit {
                            description 'Set the DSCP value by inheriting'
                                        ;
                            leaf inherit-type {
                              description 'Specify the source inherit type, such as precedence, mpls-exp, 8021p, dscp, '
                                        + 'pay-load 8021p'
                                          ;
                              type enumeration {
                                enum precedence {
                                  value 1 ;
                                  description 'Select precedence as source inherit'
                                              ;
                                }
                                enum mpls-exp {
                                  value 2 ;
                                  description 'Select MPLS-EXP as source inherit'
                                              ;
                                }
                                enum 8021p {
                                  value 3 ;
                                  description 'Select 802.1p as source inherit'
                                              ;
                                }
                                enum dscp {
                                  value 4 ;
                                  description 'Select dscp as source inherit'
                                              ;
                                }
                                enum pay-load-8021p {
                                  value 6 ;
                                  description 'Select inner 802.1p as source inherit'
                                              ;
                                }
                              }
                              mandatory true ;
                            }
                          }
                        }
                      }
                      ncd:revise-date 2021-01-25 ;
                    }
                    container precedence {
                      description 'Select precedence as mark type'
                                  ;
                      presence 'Select precedence as mark type'
                               ;
                      choice method {
                        description 'Specify the method to set IP Precedence'
                                    ;
                        mandatory true ;
                        case set-value {
                          description 'Set the IP Precedence value directly'
                                      ;
                          container set-value {
                            description 'Set the IP Precedence value directly'
                                        ;
                            leaf prec-value {
                              description 'IP Precedence value, support <0-7>'
                                          ;
                              type uint16 {
                                range 0..7 {
                                  description 'IP Precedence value, support <0-7>'
                                              ;
                                }
                              }
                              mandatory true ;
                            }
                          }
                        }
                        case inherit {
                          status obsolete ;
                          description 'Set the IP Precedence value by inheriting'
                                      ;
                          container inherit {
                            description 'Set the IP Precedence value by inheriting'
                                        ;
                            leaf inherit-type {
                              description 'Specify the source inherit type, such as precedence, mpls-exp, 8021p, dscp'
                                          ;
                              type enumeration {
                                enum precedence {
                                  value 1 ;
                                  description 'Select precedence as source inherit'
                                              ;
                                }
                                enum mpls-exp {
                                  value 2 ;
                                  description 'Select MPLS-EXP as source inherit'
                                              ;
                                }
                                enum 8021p {
                                  value 3 ;
                                  description 'Select 802.1p as source inherit'
                                              ;
                                }
                                enum dscp {
                                  value 4 ;
                                  description 'Select dscp as source inherit'
                                              ;
                                }
                              }
                              mandatory true ;
                            }
                          }
                        }
                      }
                      ncd:revise-date 2021-01-25 ;
                    }
                    container pri-8021p {
                      description 'Select 802.1p as mark type'
                                  ;
                      presence 'Select 802.1p as mark type'
                               ;
                      choice method {
                        description 'Specify the method to set 802.1p'
                                    ;
                        mandatory true ;
                        case set-value {
                          description 'Set the 802.1p value directly'
                                      ;
                          container set-value {
                            description 'Set the 802.1p value directly'
                                        ;
                            leaf value-8021p {
                              description '802.1p value, support <0-7>'
                                          ;
                              type uint16 {
                                range 0..7 {
                                  description '802.1p value, support <0-7>'
                                              ;
                                }
                              }
                              mandatory true ;
                            }
                            leaf inner-outer {
                              description 'Set 8021p inner or outer flag.If vlaue is 0, it means outer flag. If value i'
                                        + 's 1,it means inner and outer flag.'
                                          ;
                              type uint8 {
                                range 0..1 {
                                  description 'Inner or outer flag. 0 is outer. 1 is inner and outer'
                                              ;
                                }
                              }
                              default 0 ;
                            }
                          }
                        }
                        case inherit {
                          status obsolete ;
                          description 'Set the 802.1p value by inheriting'
                                      ;
                          container inherit {
                            description 'Set the 802.1p value by inheriting'
                                        ;
                            leaf inherit-type {
                              description 'Specify the source inherit type, such as precedence, mpls-exp, 8021p, dscp'
                                          ;
                              type enumeration {
                                enum precedence {
                                  value 1 ;
                                  description 'Select precedence as source inherit'
                                              ;
                                }
                                enum mpls-exp {
                                  value 2 ;
                                  description 'Select MPLS-EXP as source inherit'
                                              ;
                                }
                                enum 8021p {
                                  value 3 ;
                                  description 'Select 802.1p as source inherit'
                                              ;
                                }
                                enum dscp {
                                  value 4 ;
                                  description 'Select dscp as source inherit'
                                              ;
                                }
                              }
                              mandatory true ;
                            }
                            leaf inner-outer {
                              description 'Set 8021p inner or outer flag.If vlaue is 0, it means outer flag. If value i'
                                        + 's 1,it means inner and outer flag.'
                                          ;
                              type uint8 {
                                range 0..1 {
                                  description 'Inner or outer flag. 0 is outer. 1 is inner and outer'
                                              ;
                                }
                              }
                              default 0 ;
                            }
                          }
                        }
                      }
                      ncd:revise-date 2021-01-25 ;
                    }
                    container mpls-exp {
                      description 'Select MPLS-EXP as mark type'
                                  ;
                      presence 'Select MPLS-EXP as mark type'
                               ;
                      leaf label-type {
                        if-feature policy-action-set-label ;
                        description 'Select MPLS-EXP label position, such as '+"\n"
                                  + '    default    The default for topmost lab'
                                  + 'el'+"\n"
                                  + '    topmost    Set the MPLS-EXP value on t'
                                  + 'opmost label'+"\n"
                                  + '    imposition Set the MPLS-EXP value on a'
                                  + 'll imposed labels'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on all imposed labels'
                                        ;
                          }
                          enum default {
                            value 0 ;
                            description 'The default for topmost label'
                                        ;
                          }
                          enum inner {
                            value 3 ;
                            description 'Set the MPLS-EXP value on inner label'
                                        ;
                          }
                        }
                      }
                      choice method {
                        description 'Specify the method to set MPLS-EXP'
                                    ;
                        mandatory true ;
                        case set-value {
                          description 'Set the MPLS-EXP value directly'
                                      ;
                          container set-value {
                            description 'Set the MPLS-EXP value directly'
                                        ;
                            leaf mpls-exp-value {
                              description 'MPLS-EXP value, support <0-7>'
                                          ;
                              type uint16 {
                                range 0..7 {
                                  description 'MPLS-EXP value, support <0-7>'
                                              ;
                                }
                              }
                              mandatory true ;
                            }
                          }
                        }
                        case inherit {
                          status obsolete ;
                          description 'Set the MPLS-EXP value by inheriting'
                                      ;
                          container inherit {
                            description 'Set the MPLS-EXP value by inheriting'
                                        ;
                            leaf inherit-type {
                              description 'Specify the source inherit type, such as precedence, mpls-exp, 8021p, dscp'
                                          ;
                              type enumeration {
                                enum precedence {
                                  value 1 ;
                                  description 'Select precedence as source inherit'
                                              ;
                                }
                                enum mpls-exp {
                                  value 2 ;
                                  description 'Select MPLS-EXP as source inherit'
                                              ;
                                }
                                enum 8021p {
                                  value 3 ;
                                  description 'Select 802.1p as source inherit'
                                              ;
                                }
                                enum dscp {
                                  value 4 ;
                                  description 'Select dscp as source inherit'
                                              ;
                                }
                              }
                              mandatory true ;
                            }
                          }
                        }
                      }
                      ncd:revise-date 2021-01-25 ;
                    }
                    container vlan-id {
                      description 'Configure VLAN ID'
                                  ;
                      presence 'Configure VLAN ID'
                               ;
                      leaf vlan-value {
                        description 'Set VLAN ID, support <1-4094>'
                                    ;
                        type uint16 {
                          range 1..4094 ;
                        }
                        mandatory true ;
                      }
                      ncd:revise-date 2021-01-25 ;
                    }
                  }
                  container urpf-type {
                    description 'Configure URPF(Unicast Reverse Path Forwarding'
                              + ') type:IPv4 urpf or IPv6 urpf.'
                                ;
                    presence 'Configure URPF type'
                             ;
                    choice ip-type {
                      description 'Configure URPF(Unicast Reverse Path Forwardi'
                                + 'ng) type:IPv4 urpf or IPv6 urpf.'
                                  ;
                      mandatory true ;
                      case ipv4 {
                        description 'Configure IPv4 URPF(Unicast Reverse Path F'
                                  + 'orwarding) type.'
                                    ;
                        leaf ipv4 {
                          description 'IPv4 URPF type.'
                                      ;
                          type empty ;
                          mandatory true ;
                        }
                      }
                      case ipv6 {
                        description 'Configure IPv6 URPF(Unicast Reverse Path F'
                                  + 'orwarding) type.'
                                    ;
                        leaf ipv6 {
                          description 'IPv6 URPF type.'
                                      ;
                          type empty ;
                          mandatory true ;
                        }
                      }
                    }
                  }
                  container statistics {
                    description 'Configure the statistics function of class.'
                                ;
                    presence 'Configure statistics function'
                             ;
                    leaf statis-enable {
                      description 'Enable the statistics function.'
                                  ;
                      type empty ;
                      mandatory true ;
                    }
                  }
                  container drop {
                    description 'Configure drop'
                                ;
                    presence 'Configure drop'
                             ;
                    leaf drop {
                      description 'Specify drop'
                                  ;
                      type empty ;
                      mandatory true ;
                    }
                    ncd:revise-date 2021-01-11 ;
                  }
                  container vlan-stacking {
                    if-feature policy-action-vlan-stacking ;
                    description 'Configure vlan-stacking'
                                ;
                    presence 'Configure vlan-stacking'
                             ;
                    leaf value {
                      description 'Set the value of vlan-stack'
                                  ;
                      type uint16 {
                        range 1..4094 ;
                      }
                    }
                    leaf priority {
                      description 'Set the priority of vlan-stack'
                                  ;
                      type uint8 {
                        range 0..7 ;
                      }
                    }
                    ncd:revise-date 2021-01-25 ;
                  }
                  container redirect {
                    if-feature policy-action-rediret-route-map ;
                    description 'Configure redirect route-map'
                                ;
                    container route-map {
                      description 'Configure redirect route-map'
                                  ;
                      presence 'Configure redirect route-map'
                               ;
                      leaf route-map-name {
                        description 'The name of route-map'
                                    ;
                        type string {
                          length 1..200 ;
                        }
                      }
                      leaf route-map-type {
                        description 'The type of route-map,IPv4 or IPv6'
                                    ;
                        type enumeration {
                          enum ipv4 {
                            value 1 ;
                          }
                          enum ipv6 {
                            value 2 ;
                          }
                        }
                      }
                      leaf vrf-name {
                        description 'VRF name'
                                    ;
                        type string {
                          length 1..32 ;
                        }
                      }
                    }
                    ncd:revise-date 2021-01-25 ;
                  }
                }
              }
              container pmap-description {
                description 'Description of a policy map, support 1-79 characte'
                          + 'rs.'
                            ;
                presence 'Specify description of policy map'
                         ;
                leaf pmap-description {
                  description 'Description of a policy map, support 1-79 charac'
                            + 'ters.'
                              ;
                  type ncd:string-with-blank {
                    length 1..79 {
                      description 'Description of a policy map, support 1-79 ch'
                                + 'aracters.'
                                  ;
                    }
                  }
                  mandatory true ;
                }
                ncd:revise-date 2021-01-18 ;
              }
            }
          }
          ncd:revise-date 2020-12-23 ;
        }
        container cps-based {
          description 'Policy map based on control-plane-security'
                      ;
          container policy-maps {
            description 'Configure H-QoS policy map lists'
                        ;
            list policy-map {
              description 'Configure H-QoS policy maps'
                          ;
              key pmap-name ;
              leaf pmap-name {
                description 'Name of the policy map, support 1-31 characters'
                            ;
                type string {
                  length 1..31 {
                    description 'Name of the policy map, support 1-31 characters'
                                ;
                  }
                }
              }
              container class-maps {
                description 'Configure H-QoS policy class'
                            ;
                list class-map {
                  description 'Configure H-QoS policy class'
                              ;
                  key cmap-name ;
                  leaf cmap-name {
                    description 'Name of the class map, support 1-31 characters'
                                ;
                    type string {
                      length 1..31 {
                        description 'Name of the class map, support 1-31 charac'
                                  + 'ters'
                                    ;
                      }
                    }
                  }
                  container police {
                    description 'Configure traffic policing'
                                ;
                    presence 'Configure traffic policing'
                             ;
                    container c-bucket {
                      description 'Configure C-bucket related parameters.'
                                  ;
                      container cir-value {
                        description 'Configure the CIR(Committed Information Ra'
                                  + 'te).'
                                    ;
                        leaf cir {
                          description 'Configure the CIR(Committed Information '
                                    + 'Rate) value (Unit: packets per second)'
                                      ;
                          type uint32 {
                            range 1..4294967295 {
                              description 'The CIR value (Unit: packets per second)'
                                          ;
                            }
                          }
                          mandatory true ;
                        }
                      }
                    }
                  }
                  container drop {
                    description 'Configure drop'
                                ;
                    presence 'Configure drop'
                             ;
                    leaf drop {
                      description 'Specify drop'
                                  ;
                      type empty ;
                      mandatory true ;
                    }
                  }
                  container priority-level {
                    description 'Configure PQ(Priority Queuing) priority level'
                                ;
                    presence 'Configure PQ priority level'
                             ;
                    leaf priority-value {
                      description 'Set the priority level of PQ'
                                  ;
                      type uint16 {
                        range 1..65535 {
                          description 'The priority level of PQ'
                                      ;
                        }
                      }
                      mandatory true ;
                    }
                  }
                }
                container class-default {
                  description 'Select the default class'
                              ;
                  presence 'Specify the default class'
                           ;
                  leaf class-default {
                    description 'Specify the default class'
                                ;
                    type empty ;
                    mandatory true ;
                  }
                  container police {
                    description 'Configure traffic policing'
                                ;
                    presence 'Configure traffic policing'
                             ;
                    container c-bucket {
                      description 'Configure C-bucket related parameters.'
                                  ;
                      container cir-value {
                        description 'Configure the CIR(Committed Information Ra'
                                  + 'te).'
                                    ;
                        leaf cir {
                          description 'Configure the CIR(Committed Information '
                                    + 'Rate) value (Unit: packets per second)'
                                      ;
                          type uint32 {
                            range 1..4294967295 {
                              description 'The CIR value (Unit: packets per second)'
                                          ;
                            }
                          }
                          mandatory true ;
                        }
                      }
                    }
                  }
                  container drop {
                    description 'Configure drop'
                                ;
                    presence 'Configure drop'
                             ;
                    leaf drop {
                      description 'Specify drop'
                                  ;
                      type empty ;
                      mandatory true ;
                    }
                  }
                  container priority-level {
                    description 'Configure PQ(Priority Queuing) priority level'
                                ;
                    presence 'Configure PQ priority level'
                             ;
                    leaf priority-value {
                      description 'Set the priority level of PQ'
                                  ;
                      type uint16 {
                        range 1..65535 {
                          description 'The priority level of PQ'
                                      ;
                        }
                      }
                      mandatory true ;
                    }
                  }
                }
              }
              container pmap-description {
                description 'Description of a policy map, support 1-79 characte'
                          + 'rs.'
                            ;
                presence 'Specify description of policy map'
                         ;
                leaf pmap-description {
                  description 'Description of a policy map, support 1-79 charac'
                            + 'ters.'
                              ;
                  type ncd:string-with-blank {
                    length 1..79 {
                      description 'Description of a policy map, support 1-79 ch'
                                + 'aracters.'
                                  ;
                    }
                  }
                  mandatory true ;
                }
              }
            }
          }
          ncd:revise-date 2021-04-18 ;
        }
      }
      container service-policys {
        if-feature service-policy ;
        description 'Bind H-QoS policys to the interface'
                    ;
        list service-policy {
          description 'Bind H-QoS policys to the interface'
                      ;
          key 'if-name if-direction bound-type'
              ;
          leaf if-name {
            description 'Configure the name of the attaching interface'
                        ;
            type ncd:ifname {
              length 1..31 {
                description 'Name of the attaching interface, support 1-31 char'
                          + 'acters'
                            ;
              }
            }
          }
          leaf if-direction {
            description 'Configure the interface direction, as follows,'+"\n"
                      + '     input  Attaches to the input interface'+"\n"
                      + '     output Attaches to the output interface'
                        ;
            type enumeration {
              enum input {
                value 1 ;
                description 'Attaches to the input interface'
                            ;
              }
              enum output {
                value 2 ;
                description 'Attaches to the output interface'
                            ;
              }
            }
          }
          leaf bound-type {
            description 'Specify the bind mode, as follows,'+"\n"
                      + '     normal    Set policies bound on link-ports with n'
                      + 'ormal'+"\n"
                      + '     overwrite Set policies bound on link-ports with o'
                      + 'verwrite'+"\n"
                      + '     multiple-level-qos Set multiple level qos mode'
                        ;
            type enumeration {
              enum normal {
                value 1 ;
                description 'Set policies bound on link-ports with normal'
                            ;
              }
              enum overwrite {
                value 2 ;
                description 'Set policies bound on link-ports with overwrite'
                            ;
              }
              enum multiple-level-qos {
                value 4 ;
                description 'Set multiple level qos mode'
                            ;
              }
            }
          }
          leaf pmap-name {
            description 'Name of the policy map bound on the interface, support'
                      + ' 1-31 characters'
                        ;
            type string {
              length 1..31 {
                description 'Name of the policy map, support 1-31 characters'
                            ;
              }
            }
            mandatory true ;
          }
          leaf statistical-share {
            description 'Set statistical share, as follows,'+"\n"
                      + '     false  statistical-share is not configured'+"\n"
                      + '     ture   statistical-share is configured'
                        ;
            type boolean ;
            default false ;
          }
          leaf share-group {
            description 'Specify share group ID.'
                        ;
            type uint32 {
              range 1..4000 ;
            }
            ncd:revise-date 2021-01-18 ;
          }
          container shape {
            description 'Configure shape'
                        ;
            presence 'Configure shape'
                     ;
            leaf rate {
              description 'Rate in kilobits per second, support <8-100000000>'
                          ;
              type uint32 {
                range 8..100000000 {
                  description 'Rate in kilobits per second'
                              ;
                }
              }
              units kbps ;
              mandatory true ;
            }
            container burst {
              description 'Configure burst and exburst size in KB'
                          ;
              presence 'Configure burst and exburst size in KB'
                       ;
              leaf burst-size {
                description 'Burst size in KB, support <2-250000000>'
                            ;
                type uint32 {
                  range 2..250000000 {
                    description 'Burst size in KB, support <2-250000000>'
                                ;
                  }
                }
                units KB ;
                mandatory true ;
              }
            }
            ncd:revise-date 2021-03-22 ;
          }
        }
      }
      container traffic-policy-interfaces {
        if-feature traffic-policy ;
        description 'Bind QoS policys to the interface'
                    ;
        list traffic-policy-interface {
          description 'Bind QoS policys to the interface'
                      ;
          key 'if-name if-direction'
              ;
          leaf if-name {
            description 'Configure the name of the attaching interface'
                        ;
            type ncd:ifname {
              length 1..31 {
                description 'Name of the attaching interface, support 1-31 char'
                          + 'acters'
                            ;
              }
            }
          }
          leaf if-direction {
            description 'Configure the interface direction, as follows,'+"\n"
                      + '     input  Attaches to the input interface'+"\n"
                      + '     output Attaches to the output interface'
                        ;
            type enumeration {
              enum input {
                value 1 ;
                description 'Attaches to the input interface'
                            ;
              }
              enum output {
                value 2 ;
                description 'Attaches to the output interface'
                            ;
              }
            }
          }
          leaf bound-type {
            description 'Specify the bind mode, as follows,'+"\n"
                      + '     normal    Set policies bound on link-ports with n'
                      + 'ormal'+"\n"
                      + '     overwrite Set policies bound on link-ports with o'
                      + 'verwrite'
                        ;
            type enumeration {
              enum overwrite {
                value 2 ;
                description 'Set policies bound on link-ports with overwrite'
                            ;
              }
              enum normal {
                value 1 ;
                description 'Set policies bound on link-ports with normal'
                            ;
              }
            }
            default normal ;
          }
          leaf pmap-name {
            description 'Name of the policy map bound on the interface, support'
                      + ' 1-31 characters'
                        ;
            type string {
              length 1..31 {
                description 'Name of the policy map, support 1-31 characters'
                            ;
              }
            }
            mandatory true ;
          }
          leaf statistical-share {
            description 'Set statistical share, as follows,'+"\n"
                      + '     false  statistical-share is not configured'+"\n"
                      + '     ture   statistical-share is configured'
                        ;
            type boolean ;
            default false ;
          }
        }
        ncd:revise-date 2021-01-25 ;
      }
      container rate-limit {
        description 'Configure interface rate limit parameters'
                    ;
        container unicasts {
          description 'Match unicast, only for VPLS'
                      ;
          list unicast {
            description 'Configure interface rate limit based on matching unica'
                      + 'st'
                        ;
            key 'if-name if-direct'
                ;
            leaf if-name {
              description 'Configure the name of the attaching interface'
                          ;
              type ncd:ifname {
                length 1..31 {
                  description 'Name of the attaching interface, support 1-31 ch'
                            + 'aracters'
                              ;
                }
              }
            }
            leaf if-direct {
              description 'Specify the direction of interface, as follows,'+"\n"
                        + '     input  Rate limit on input'+"\n"
                        + '     output Rate limit on output'
                          ;
              type enumeration {
                enum input {
                  value 1 ;
                  description 'Rate limit on input'
                              ;
                }
                enum output {
                  value 2 ;
                  description 'Rate limit on output'
                              ;
                }
              }
            }
            leaf rate-limit-desc {
              description 'Description of rate limit, support 1-79 characters.'
                          ;
              type ncd:string-with-blank {
                length 1..79 {
                  description 'Description of rate limit, support 1-79 characte'
                            + 'rs.'
                              ;
                }
              }
              ncd:revise-date 2020-06-18 ;
            }
            choice unit-style {
              description "Specify unit's style"
                          ;
              mandatory true ;
              case unit-value {
                description 'Configure the value style'
                            ;
                leaf cir {
                  description 'Configure the CIR(Committed Information Rate) va'
                            + 'lue (default: kilobits per second)'
                              ;
                  type uint32 {
                    range 8..4294967295 {
                      description 'The CIR value (default: kilobits per second)'
                                + ',support <8-4294967295>'
                                  ;
                    }
                  }
                  mandatory true ;
                }
                leaf cir-unit {
                  description 'set cir unit, such as kbps, mbps, gbps'
                              ;
                  type qos-rate-unit-type ;
                }
                leaf cbs {
                  description 'Configure the CBS(Committed Burst Size) size in '
                            + 'bytes.'
                              ;
                  type uint32 {
                    range 1..4294967295 {
                      description 'The CBS(Committed Burst Size) size in bytes,'
                                + ' support <1-4294967295>.'
                                  ;
                    }
                  }
                  units byte ;
                }
                leaf pir {
                  description 'Configure the PIR(Peak Information Rate) value ('
                            + 'default: kilobits per second)'
                              ;
                  type uint32 {
                    range 8..4294967295 {
                      description 'The PIR(Peak Information Rate) value (defaul'
                                + 't: kilobits per second), support <8-42949672'
                                + '95>'
                                  ;
                    }
                  }
                  mandatory true ;
                }
                leaf pir-unit {
                  description 'set pir unit, such as kbps, mbps, gbps'
                              ;
                  type qos-rate-unit-type ;
                }
                leaf pbs {
                  description 'Configure the PBS(Peak Burst Size) size in bytes.'
                              ;
                  type uint32 {
                    range 1..4294967295 {
                      description 'The PBS(Peak Burst Size) size in KB, support'
                                + ' <1-4294967295>'
                                  ;
                    }
                  }
                  units byte ;
                }
              }
              case unit-percentage {
                description 'Configure the percentage style'
                            ;
                leaf cir-percentage {
                  description 'Configure the CIR(Committed Information Rate) pe'
                            + 'rcentage (Set the accuracy rate per hundred (1%)'
                            + ')'
                              ;
                  type uint32 {
                    range 1..100 {
                      description 'The CIR percentage, support <1-100>'
                                  ;
                    }
                  }
                  mandatory true ;
                }
                leaf pir-percentage {
                  description 'Configure the PIR(Peak Information Rate) percent'
                            + 'age (Set the accuracy rate per hundred (1%))'
                              ;
                  type uint32 {
                    range 1..100 {
                      description 'The PIR percentage, support <1-100>'
                                  ;
                    }
                  }
                  mandatory true ;
                }
                ncd:revise-date 2020-12-23 ;
              }
            }
            choice buket-value-percent {
              if-feature car-buket-value-percent ;
              description 'Configure CIR, CBS, PIR and PBS.'
                          ;
              mandatory true ;
              case buket-value {
                description 'Configure CIR, CBS, PIR and PBS in numerical form.'
                            ;
                container c-buket {
                  description 'Configure C-buket related parameters.'
                              ;
                  container cir-value {
                    description 'Configure the CIR(Committed Information Rate).'
                                ;
                    leaf cir {
                      description 'Configure the CIR(Committed Information Rate'
                                + ') value (default: kilobits per second)'
                                  ;
                      type uint32 {
                        range 8..4294967295 {
                          description 'The CIR value (default: kilobits per sec'
                                    + 'ond),support <8-4294967295>'
                                      ;
                        }
                      }
                      mandatory true ;
                    }
                    leaf cir-unit {
                      description 'set cir unit, such as kbps, mbps, gbps, pps.'
                                  ;
                      type qos-rate-unit-type-ex ;
                    }
                  }
                  container cbs-value {
                    description 'Configure the CBS(Committed Burst Size).'
                                ;
                    presence cbs ;
                    leaf cbs {
                      description 'Configure the CBS(Committed Burst Size) valu'
                                + 'e in bytes.'
                                  ;
                      type uint32 {
                        range 1..4294967295 {
                          description 'The CBS(Committed Burst Size) size in by'
                                    + 'tes, support <1-4294967295>'
                                      ;
                        }
                      }
                      units byte ;
                      mandatory true ;
                    }
                  }
                }
                container p-buket {
                  description 'Configure P-buket related parameters.'
                              ;
                  presence p-buket ;
                  container pir-value {
                    description 'Configure the PIR(Peak Information Rate).'
                                ;
                    leaf pir {
                      description 'Configure the PIR(Peak Information Rate) val'
                                + 'ue (default: kilobits per second)'
                                  ;
                      type uint32 {
                        range 8..4294967295 {
                          description 'The PIR(Peak Information Rate) value (de'
                                    + 'fault: kilobits per second), support <8-'
                                    + '4294967295>'
                                      ;
                        }
                      }
                      mandatory true ;
                    }
                    leaf pir-unit {
                      description 'set pir unit, such as kbps, mbps, gbps, pps'
                                  ;
                      type qos-rate-unit-type-ex ;
                    }
                  }
                  container pbs-value {
                    description 'Configure the PBS(Peak Burst Size).'
                                ;
                    presence pbs ;
                    leaf pbs {
                      description 'Configure the PBS(Peak Burst Size) value in '
                                + 'bytes.'
                                  ;
                      type uint32 {
                        range 1..4294967295 {
                          description 'The PBS(Peak Burst Size) size in bytes, '
                                    + 'support <1-4294967295>'
                                      ;
                        }
                      }
                      units byte ;
                      mandatory true ;
                    }
                  }
                }
              }
              case buket-percent {
                description 'Configure CIR and PIR in percentage.'
                            ;
                container cir-percent {
                  description 'Configure CIR in percentage.'
                              ;
                  leaf cir-percent {
                    description 'Configure CIR in percentage.'
                                ;
                    type uint32 {
                      range 1..100 ;
                    }
                    mandatory true ;
                  }
                }
                container pir-percent {
                  description 'Configure PIR in percentage.'
                              ;
                  presence pir ;
                  leaf pir-percent {
                    description 'Configure PIR in percentage.'
                                ;
                    type uint32 {
                      range 1..100 ;
                    }
                    mandatory true ;
                  }
                }
              }
              ncd:revise-date 2021-01-25 ;
            }
            leaf statistical-share {
              description 'The flag of statistical-share, as follows,'+"\n"
                        + '    ture  Statistical-share is configured'+"\n"
                        + '    false Statistical-share is not configured'
                          ;
              type boolean ;
              default false ;
            }
            leaf token-bucket-id {
              description 'Set token bucket id'
                          ;
              type uint32 {
                range 1..4294967295 {
                  description 'Token bucket id'
                              ;
                }
              }
              ncd:revise-date 2019-10-28 ;
            }
            container mode {
              if-feature qos-car-mode ;
              description 'Set color mode'
                          ;
              presence 'Configure mode information'
                       ;
              leaf mode-type {
                description 'Color mode type, as follows,'+"\n"
                          + '     blind   Color-Blind mode'+"\n"
                          + '     aware   Color-Aware mode'
                            ;
                type enumeration {
                  enum blind {
                    value 1 ;
                    description 'Color-Blind mode'
                                ;
                  }
                  enum aware {
                    value 2 ;
                    description 'Color-Aware mode'
                                ;
                  }
                }
                mandatory true ;
              }
            }
            container conform-action {
              description 'Action to packets that conform to the rate limit'
                          ;
              choice action {
                description 'Specify action to packets that conform to the rate'
                          + ' limit'
                            ;
                mandatory true ;
                case ca-drop {
                  description 'Drop packet in conform-action'
                              ;
                  leaf drop {
                    description 'Specify action to drop packet'
                                ;
                    type empty ;
                    mandatory true ;
                  }
                }
                case ca-transmit {
                  description 'Transmit packet in conform-action'
                              ;
                  leaf transmit {
                    description 'Specify action to transmit packet'
                                ;
                    type empty ;
                    mandatory true ;
                  }
                }
                case ca-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in conform-action, supp'
                                + 'ort <0-7>'
                                  ;
                      type uint8 {
                        range 0..7 {
                          description 'The MPLS-EXP value, support <0-7>'
                                      ;
                        }
                      }
                      mandatory true ;
                    }
                  }
                }
                case ca-precedence {
                  description 'Rewrite packet precedence and transmit the packet'
                              ;
                  container set-prec-transmit {
                    description 'Specify action to rewrite packet precedence an'
                              + 'd transmit it'
                                ;
                    leaf prec-value {
                      description 'Reset the IP-Precedence value in conform-act'
                                + 'ion, support <0-7>'
                                  ;
                      type uint8 {
                        range 0..7 {
                          description 'The IP-Precedence value, support <0-7>'
                                      ;
                        }
                      }
                      mandatory true ;
                    }
                  }
                }
                case ca-dscp {
                  description 'Rewrite packet DSCP and transmit the packet'
                              ;
                  container set-dscp-transmit {
                    description 'Specify action to rewrite packet DSCP and tran'
                              + 'smit it'
                                ;
                    leaf dscp-value {
                      description 'Reset DSCP in conform-action, support <0-63>'
                                  ;
                      type uint8 {
                        range 0..63 {
                          description 'The DSCP value, support <0-63>'
                                      ;
                        }
                      }
                      mandatory true ;
                    }
                  }
                }
                case ca-8021p {
                  description 'Rewrite packet 802.1p and transmit the packet'
                              ;
                  container set-8021p-transmit {
                    description 'Specify action to rewrite packet 802.1p and tr'
                              + 'ansmit it'
                                ;
                    leaf value-8021p {
                      description 'Reset 802.1p in conform-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ca-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ca-service-class {
                  description 'Rewrite packet service class and transmit the pa'
                            + 'cket'
                              ;
                  container set-service-class-transmit {
                    description 'Specify action to rewrite packet service-class'
                              + ' and transmit it'
                                ;
                    leaf service-class-value {
                      description 'Reset service class in conform-action'
                                  ;
                      type qos-service-class ;
                      mandatory true ;
                    }
                  }
                  ncd:revise-date 2020-05-18 ;
                }
              }
            }
            container exceed-action {
              description 'Action to packets that exceed the rate limit'
                          ;
              choice action {
                description 'Specify action to packets that exceed the rate lim'
                          + 'it'
                            ;
                mandatory true ;
                case ea-drop {
                  description 'Drop packet in exceed-action'
                              ;
                  leaf drop {
                    description 'Specify action to drop packet'
                                ;
                    type empty ;
                    mandatory true ;
                  }
                }
                case ea-transmit {
                  description 'Transmit packet in exceed-action'
                              ;
                  leaf transmit {
                    description 'Specify action to transmit packet'
                                ;
                    type empty ;
                    mandatory true ;
                  }
                }
                case ea-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in exceed-action, suppo'
                                + 'rt <0-7>'
                                  ;
                      type uint8 {
                        range 0..7 {
                          description 'The MPLS-EXP value, support <0-7>'
                                      ;
                        }
                      }
                      mandatory true ;
                    }
                  }
                }
                case ea-precedence {
                  description 'Rewrite packet precedence and transmit the packet'
                              ;
                  container set-prec-transmit {
                    description 'Specify action to rewrite packet precedence an'
                              + 'd transmit it'
                                ;
                    leaf prec-value {
                      description 'Reset the IP-Precedence value in exceed-acti'
                                + 'on, support <0-7>'
                                  ;
                      type uint8 {
                        range 0..7 {
                          description 'The IP-Precedence value, support <0-7>'
                                      ;
                        }
                      }
                      mandatory true ;
                    }
                  }
                }
                case ea-dscp {
                  description 'Rewrite packet DSCP and transmit the packet'
                              ;
                  container set-dscp-transmit {
                    description 'Specify action to rewrite packet DSCP and tran'
                              + 'smit it'
                                ;
                    leaf dscp-value {
                      description 'Reset DSCP in exceed-action, support <0-63>'
                                  ;
                      type uint8 {
                        range 0..63 {
                          description 'The DSCP value, support <0-63>'
                                      ;
                        }
                      }
                      mandatory true ;
                    }
                  }
                }
                case ea-8021p {
                  description 'Rewrite packet 802.1p and transmit the packet'
                              ;
                  container set-8021p-transmit {
                    description 'Specify action to rewrite packet 802.1p and tr'
                              + 'ansmit it'
                                ;
                    leaf value-8021p {
                      description 'Reset 802.1p in exceed-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ea-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ea-service-class {
                  description 'Rewrite packet service class and transmit the pa'
                            + 'cket'
                              ;
                  container set-service-class-transmit {
                    description 'Specify action to rewrite packet service class'
                              + ' and transmit it'
                                ;
                    leaf service-class-value {
                      description 'Reset service class in exceed-action'
                                  ;
                      type qos-service-class ;
                      mandatory true ;
                    }
                  }
                  ncd:revise-date 2020-05-18 ;
                }
              }
            }
            container violate-action {
              description 'Action to packets that violate the rate limit'
                          ;
              choice action {
                description 'Specify action to packets that violate the rate li'
                          + 'mit'
                            ;
                mandatory true ;
                case va-drop {
                  description 'Drop packet in violate-action'
                              ;
                  leaf drop {
                    description 'Specify action to drop packet'
                                ;
                    type empty ;
                    mandatory true ;
                  }
                }
                case va-transmit {
                  description 'Transmit packet in violate-action'
                              ;
                  leaf transmit {
                    description 'Specify action to transmit packet'
                                ;
                    type empty ;
                    mandatory true ;
                  }
                }
                case va-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in violate-action, supp'
                                + 'ort <0-7>'
                                  ;
                      type uint8 {
                        range 0..7 {
                          description 'The MPLS-EXP value, support <0-7>'
                                      ;
                        }
                      }
                      mandatory true ;
                    }
                  }
                }
                case va-precedence {
                  description 'Rewrite packet precedence and transmit the packet'
                              ;
                  container set-prec-transmit {
                    description 'Specify action to rewrite packet precedence an'
                              + 'd transmit it'
                                ;
                    leaf prec-value {
                      description 'Reset the IP-Precedence value in violate-act'
                                + 'ion, support <0-7>'
                                  ;
                      type uint8 {
                        range 0..7 ;
                      }
                      mandatory true ;
                    }
                  }
                }
                case va-dscp {
                  description 'Rewrite packet DSCP and transmit the packet'
                              ;
                  container set-dscp-transmit {
                    description 'Specify action to rewrite packet DSCP and tran'
                              + 'smit it'
                                ;
                    leaf dscp-value {
                      description 'Reset DSCP in violate-action, support <0-63>'
                                  ;
                      type uint8 {
                        range 0..63 {
                          description 'The DSCP value, support <0-63>'
                                      ;
                        }
                      }
                      mandatory true ;
                    }
                  }
                }
                case va-8021p {
                  description 'Rewrite packet 802.1p and transmit the packet'
                              ;
                  container set-8021p-transmit {
                    description 'Specify action to rewrite packet 802.1p and tr'
                              + 'ansmit it'
                                ;
                    leaf value-8021p {
                      description 'Reset 802.1p in violate-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case va-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case va-service-class {
                  description 'Rewrite packet service class and transmit the pa'
                            + 'cket'
                              ;
                  container set-service-class-transmit {
                    description 'Specify action to rewrite packet service class'
                              + ' and transmit it'
                                ;
                    leaf service-class-value {
                      description 'Reset service class in violate-action'
                                  ;
                      type qos-service-class ;
                      mandatory true ;
                    }
                  }
                  ncd:revise-date 2020-05-18 ;
                }
              }
            }
          }
        }
        container unknown-unicasts {
          description 'Match unknown unicast'
                      ;
          list unknown-unicast {
            description 'Configure interface rate limit based on matching unkno'
                      + 'wn unicast'
                        ;
            key 'if-name if-direct'
                ;
            leaf if-name {
              description 'Configure the name of the attaching interface'
                          ;
              type ncd:ifname {
                length 1..31 {
                  description 'Name of the attaching interface, support 1-31 ch'
                            + 'aracters'
                              ;
                }
              }
            }
            leaf if-direct {
              description 'Specify the direction of interface, as follows,'+"\n"
                        + '     input  Rate limit on input'+"\n"
                        + '     output Rate limit on output'
                          ;
              type enumeration {
                enum input {
                  value 1 ;
                  description 'Rate limit on input'
                              ;
                }
                enum output {
                  value 2 ;
                  description 'Rate limit on output'
                              ;
                }
              }
            }
            leaf rate-limit-desc {
              description 'Description of rate limit, support 1-79 characters.'
                          ;
              type ncd:string-with-blank {
                length 1..79 {
                  description 'Description of rate limit, support 1-79 characte'
                            + 'rs.'
                              ;
                }
              }
              ncd:revise-date 2020-06-18 ;
            }
            choice unit-style {
              description "Specify unit's style"
                          ;
              mandatory true ;
              case unit-value {
                description 'Configure the value style'
                            ;
                leaf cir {
                  description 'Configure the CIR(Committed Information Rate) va'
                            + 'lue (default: kilobits per second)'
                              ;
                  type uint32 {
                    range 8..4294967295 {
                      description 'The CIR value (default: kilobits per second)'
                                + ',support <8-4294967295>'
                                  ;
                    }
                  }
                  mandatory true ;
                }
                leaf cir-unit {
                  description 'set cir unit, such as kbps, mbps, gbps'
                              ;
                  type qos-rate-unit-type ;
                }
                leaf cbs {
                  description 'Configure the CBS(Committed Burst Size) size in '
                            + 'bytes.'
                              ;
                  type uint32 {
                    range 1..4294967295 {
                      description 'The CBS(Committed Burst Size) size in bytes,'
                                + ' support <1-4294967295>.'
                                  ;
                    }
                  }
                  units byte ;
                }
                leaf pir {
                  description 'Configure the PIR(Peak Information Rate) value ('
                            + 'default: kilobits per second)'
                              ;
                  type uint32 {
                    range 8..4294967295 {
                      description 'The PIR(Peak Information Rate) value (defaul'
                                + 't: kilobits per second), support <8-42949672'
                                + '95>'
                                  ;
                    }
                  }
                  mandatory true ;
                }
                leaf pir-unit {
                  description 'set pir unit, such as kbps, mbps, gbps'
                              ;
                  type qos-rate-unit-type ;
                }
                leaf pbs {
                  description 'Configure the PBS(Peak Burst Size) size in bytes.'
                              ;
                  type uint32 {
                    range 1..4294967295 {
                      description 'The PBS(Peak Burst Size) size in KB, support'
                                + ' <1-4294967295>'
                                  ;
                    }
                  }
                  units byte ;
                }
              }
              case unit-percentage {
                description 'Configure the percentage style'
                            ;
                leaf cir-percentage {
                  description 'Configure the CIR(Committed Information Rate) pe'
                            + 'rcentage (Set the accuracy rate per hundred (1%)'
                            + ')'
                              ;
                  type uint32 {
                    range 1..100 {
                      description 'The CIR percentage, support <1-100>'
                                  ;
                    }
                  }
                  mandatory true ;
                }
                leaf pir-percentage {
                  description 'Configure the PIR(Peak Information Rate) percent'
                            + 'age (Set the accuracy rate per hundred (1%))'
                              ;
                  type uint32 {
                    range 1..100 {
                      description 'The PIR percentage, support <1-100>'
                                  ;
                    }
                  }
                  mandatory true ;
                }
                ncd:revise-date 2020-12-23 ;
              }
            }
            choice buket-value-percent {
              if-feature car-buket-value-percent ;
              description 'Configure CIR, CBS, PIR and PBS.'
                          ;
              mandatory true ;
              case buket-value {
                description 'Configure CIR, CBS, PIR and PBS in numerical form.'
                            ;
                container c-buket {
                  description 'Configure C-buket related parameters.'
                              ;
                  container cir-value {
                    description 'Configure the CIR(Committed Information Rate).'
                                ;
                    leaf cir {
                      description 'Configure the CIR(Committed Information Rate'
                                + ') value (default: kilobits per second)'
                                  ;
                      type uint32 {
                        range 8..4294967295 {
                          description 'The CIR value (default: kilobits per sec'
                                    + 'ond),support <8-4294967295>'
                                      ;
                        }
                      }
                      mandatory true ;
                    }
                    leaf cir-unit {
                      description 'set cir unit, such as kbps, mbps, gbps, pps.'
                                  ;
                      type qos-rate-unit-type-ex ;
                    }
                  }
                  container cbs-value {
                    description 'Configure the CBS(Committed Burst Size).'
                                ;
                    presence cbs ;
                    leaf cbs {
                      description 'Configure the CBS(Committed Burst Size) valu'
                                + 'e in bytes.'
                                  ;
                      type uint32 {
                        range 1..4294967295 {
                          description 'The CBS(Committed Burst Size) size in by'
                                    + 'tes, support <1-4294967295>'
                                      ;
                        }
                      }
                      units byte ;
                      mandatory true ;
                    }
                  }
                }
                container p-buket {
                  description 'Configure P-buket related parameters.'
                              ;
                  presence p-buket ;
                  container pir-value {
                    description 'Configure the PIR(Peak Information Rate).'
                                ;
                    leaf pir {
                      description 'Configure the PIR(Peak Information Rate) val'
                                + 'ue (default: kilobits per second)'
                                  ;
                      type uint32 {
                        range 8..4294967295 {
                          description 'The PIR(Peak Information Rate) value (de'
                                    + 'fault: kilobits per second), support <8-'
                                    + '4294967295>'
                                      ;
                        }
                      }
                      mandatory true ;
                    }
                    leaf pir-unit {
                      description 'set pir unit, such as kbps, mbps, gbps, pps'
                                  ;
                      type qos-rate-unit-type-ex ;
                    }
                  }
                  container pbs-value {
                    description 'Configure the PBS(Peak Burst Size).'
                                ;
                    presence pbs ;
                    leaf pbs {
                      description 'Configure the PBS(Peak Burst Size) value in '
                                + 'bytes.'
                                  ;
                      type uint32 {
                        range 1..4294967295 {
                          description 'The PBS(Peak Burst Size) size in bytes, '
                                    + 'support <1-4294967295>'
                                      ;
                        }
                      }
                      units byte ;
                      mandatory true ;
                    }
                  }
                }
              }
              case buket-percent {
                description 'Configure CIR and PIR in percentage.'
                            ;
                container cir-percent {
                  description 'Configure CIR in percentage.'
                              ;
                  leaf cir-percent {
                    description 'Configure CIR in percentage.'
                                ;
                    type uint32 {
                      range 1..100 ;
                    }
                    mandatory true ;
                  }
                }
                container pir-percent {
                  description 'Configure PIR in percentage.'
                              ;
                  presence pir ;
                  leaf pir-percent {
                    description 'Configure PIR in percentage.'
                                ;
                    type uint32 {
                      range 1..100 ;
                    }
                    mandatory true ;
                  }
                }
              }
              ncd:revise-date 2021-01-25 ;
            }
            leaf statistical-share {
              description 'The flag of statistical-share, as follows,'+"\n"
                        + '    ture  Statistical-share is configured'+"\n"
                        + '    false Statistical-share is not configured'
                          ;
              type boolean ;
              default false ;
            }
            leaf token-bucket-id {
              description 'Set token bucket id'
                          ;
              type uint32 {
                range 1..4294967295 {
                  description 'Token bucket id'
                              ;
                }
              }
              ncd:revise-date 2019-10-28 ;
            }
            container mode {
              if-feature qos-car-mode ;
              description 'Set color mode'
                          ;
              presence 'Configure mode information'
                       ;
              leaf mode-type {
                description 'Color mode type, as follows,'+"\n"
                          + '     blind   Color-Blind mode'+"\n"
                          + '     aware   Color-Aware mode'
                            ;
                type enumeration {
                  enum blind {
                    value 1 ;
                    description 'Color-Blind mode'
                                ;
                  }
                  enum aware {
                    value 2 ;
                    description 'Color-Aware mode'
                                ;
                  }
                }
                mandatory true ;
              }
            }
            container conform-action {
              description 'Action to packets that conform to the rate limit'
                          ;
              choice action {
                description 'Specify action to packets that conform to the rate'
                          + ' limit'
                            ;
                mandatory true ;
                case ca-drop {
                  description 'Drop packet in conform-action'
                              ;
                  leaf drop {
                    description 'Specify action to drop packet'
                                ;
                    type empty ;
                    mandatory true ;
                  }
                }
                case ca-transmit {
                  description 'Transmit packet in conform-action'
                              ;
                  leaf transmit {
                    description 'Specify action to transmit packet'
                                ;
                    type empty ;
                    mandatory true ;
                  }
                }
                case ca-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in conform-action, supp'
                                + 'ort <0-7>'
                                  ;
                      type uint8 {
                        range 0..7 {
                          description 'The MPLS-EXP value, support <0-7>'
                                      ;
                        }
                      }
                      mandatory true ;
                    }
                  }
                }
                case ca-precedence {
                  description 'Rewrite packet precedence and transmit the packet'
                              ;
                  container set-prec-transmit {
                    description 'Specify action to rewrite packet precedence an'
                              + 'd transmit it'
                                ;
                    leaf prec-value {
                      description 'Reset the IP-Precedence value in conform-act'
                                + 'ion, support <0-7>'
                                  ;
                      type uint8 {
                        range 0..7 {
                          description 'The IP-Precedence value, support <0-7>'
                                      ;
                        }
                      }
                      mandatory true ;
                    }
                  }
                }
                case ca-dscp {
                  description 'Rewrite packet DSCP and transmit the packet'
                              ;
                  container set-dscp-transmit {
                    description 'Specify action to rewrite packet DSCP and tran'
                              + 'smit it'
                                ;
                    leaf dscp-value {
                      description 'Reset DSCP in conform-action, support <0-63>'
                                  ;
                      type uint8 {
                        range 0..63 {
                          description 'The DSCP value, support <0-63>'
                                      ;
                        }
                      }
                      mandatory true ;
                    }
                  }
                }
                case ca-8021p {
                  description 'Rewrite packet 802.1p and transmit the packet'
                              ;
                  container set-8021p-transmit {
                    description 'Specify action to rewrite packet 802.1p and tr'
                              + 'ansmit it'
                                ;
                    leaf value-8021p {
                      description 'Reset 802.1p in conform-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ca-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ca-service-class {
                  description 'Rewrite packet service class and transmit the pa'
                            + 'cket'
                              ;
                  container set-service-class-transmit {
                    description 'Specify action to rewrite packet service class'
                              + ' and transmit it'
                                ;
                    leaf service-class-value {
                      description 'Reset service class in conform-action'
                                  ;
                      type qos-service-class ;
                      mandatory true ;
                    }
                  }
                  ncd:revise-date 2020-05-18 ;
                }
              }
            }
            container exceed-action {
              description 'Action to packets that exceed the rate limit'
                          ;
              choice action {
                description 'Specify action to packets that exceed the rate lim'
                          + 'it'
                            ;
                mandatory true ;
                case ea-drop {
                  description 'Drop packet in exceed-action'
                              ;
                  leaf drop {
                    description 'Specify action to drop packet'
                                ;
                    type empty ;
                    mandatory true ;
                  }
                }
                case ea-transmit {
                  description 'Transmit packet in exceed-action'
                              ;
                  leaf transmit {
                    description 'Specify action to transmit packet'
                                ;
                    type empty ;
                    mandatory true ;
                  }
                }
                case ea-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in exceed-action, suppo'
                                + 'rt <0-7>'
                                  ;
                      type uint8 {
                        range 0..7 {
                          description 'The MPLS-EXP value, support <0-7>'
                                      ;
                        }
                      }
                      mandatory true ;
                    }
                  }
                }
                case ea-precedence {
                  description 'Rewrite packet precedence and transmit the packet'
                              ;
                  container set-prec-transmit {
                    description 'Specify action to rewrite packet precedence an'
                              + 'd transmit it'
                                ;
                    leaf prec-value {
                      description 'Reset the IP-Precedence value in exceed-acti'
                                + 'on, support <0-7>'
                                  ;
                      type uint8 {
                        range 0..7 {
                          description 'The IP-Precedence value, support <0-7>'
                                      ;
                        }
                      }
                      mandatory true ;
                    }
                  }
                }
                case ea-dscp {
                  description 'Rewrite packet DSCP and transmit the packet'
                              ;
                  container set-dscp-transmit {
                    description 'Specify action to rewrite packet DSCP and tran'
                              + 'smit it'
                                ;
                    leaf dscp-value {
                      description 'Reset DSCP in exceed-action, support <0-63>'
                                  ;
                      type uint8 {
                        range 0..63 {
                          description 'The DSCP value, support <0-63>'
                                      ;
                        }
                      }
                      mandatory true ;
                    }
                  }
                }
                case ea-8021p {
                  description 'Rewrite packet 802.1p and transmit the packet'
                              ;
                  container set-8021p-transmit {
                    description 'Specify action to rewrite packet 802.1p and tr'
                              + 'ansmit it'
                                ;
                    leaf value-8021p {
                      description 'Reset 802.1p in exceed-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ea-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ea-service-class {
                  description 'Rewrite packet service class and transmit the pa'
                            + 'cket'
                              ;
                  container set-service-class-transmit {
                    description 'Specify action to rewrite packet service class'
                              + ' and transmit it'
                                ;
                    leaf service-class-value {
                      description 'Reset service class in exceed-action'
                                  ;
                      type qos-service-class ;
                      mandatory true ;
                    }
                  }
                  ncd:revise-date 2020-05-18 ;
                }
              }
            }
            container violate-action {
              description 'Action to packets that violate the rate limit'
                          ;
              choice action {
                description 'Specify action to packets that violate the rate li'
                          + 'mit'
                            ;
                mandatory true ;
                case va-drop {
                  description 'Drop packet in violate-action'
                              ;
                  leaf drop {
                    description 'Specify action to drop packet'
                                ;
                    type empty ;
                    mandatory true ;
                  }
                }
                case va-transmit {
                  description 'Transmit packet in violate-action'
                              ;
                  leaf transmit {
                    description 'Specify action to transmit packet'
                                ;
                    type empty ;
                    mandatory true ;
                  }
                }
                case va-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in violate-action, supp'
                                + 'ort <0-7>'
                                  ;
                      type uint8 {
                        range 0..7 {
                          description 'The MPLS-EXP value, support <0-7>'
                                      ;
                        }
                      }
                      mandatory true ;
                    }
                  }
                }
                case va-precedence {
                  description 'Rewrite packet precedence and transmit the packet'
                              ;
                  container set-prec-transmit {
                    description 'Specify action to rewrite packet precedence an'
                              + 'd transmit it'
                                ;
                    leaf prec-value {
                      description 'Reset the IP-Precedence value in violate-act'
                                + 'ion, support <0-7>'
                                  ;
                      type uint8 {
                        range 0..7 ;
                      }
                      mandatory true ;
                    }
                  }
                }
                case va-dscp {
                  description 'Rewrite packet DSCP and transmit the packet'
                              ;
                  container set-dscp-transmit {
                    description 'Specify action to rewrite packet DSCP and tran'
                              + 'smit it'
                                ;
                    leaf dscp-value {
                      description 'Reset DSCP in violate-action, support <0-63>'
                                  ;
                      type uint8 {
                        range 0..63 {
                          description 'The DSCP value, support <0-63>'
                                      ;
                        }
                      }
                      mandatory true ;
                    }
                  }
                }
                case va-8021p {
                  description 'Rewrite packet 802.1p and transmit the packet'
                              ;
                  container set-8021p-transmit {
                    description 'Specify action to rewrite packet 802.1p and tr'
                              + 'ansmit it'
                                ;
                    leaf value-8021p {
                      description 'Reset 802.1p in violate-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case va-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case va-service-class {
                  description 'Rewrite packet service class and transmit the pa'
                            + 'cket'
                              ;
                  container set-service-class-transmit {
                    description 'Specify action to rewrite packet service class'
                              + ' and transmit it'
                                ;
                    leaf service-class-value {
                      description 'Reset service class in violate-action'
                                  ;
                      type qos-service-class ;
                      mandatory true ;
                    }
                  }
                  ncd:revise-date 2020-05-18 ;
                }
              }
            }
          }
          ncd:revise-date 2015-10-28 ;
        }
        container multicasts {
          description 'Match multicast, only for VPLS'
                      ;
          list multicast {
            description 'Configure interface rate limit based on matching multi'
                      + 'cast'
                        ;
            key 'if-name if-direct'
                ;
            leaf if-name {
              description 'Configure the name of the attaching interface'
                          ;
              type ncd:ifname {
                length 1..31 {
                  description 'Name of the attaching interface, support 1-31 ch'
                            + 'aracters'
                              ;
                }
              }
            }
            leaf if-direct {
              description 'Specify the direction of interface, as follows,'+"\n"
                        + '     input  Rate limit on input'+"\n"
                        + '     output Rate limit on output'
                          ;
              type enumeration {
                enum input {
                  value 1 ;
                  description 'Rate limit on input'
                              ;
                }
                enum output {
                  value 2 ;
                  description 'Rate limit on output'
                              ;
                }
              }
            }
            leaf rate-limit-desc {
              description 'Description of rate limit, support 1-79 characters.'
                          ;
              type ncd:string-with-blank {
                length 1..79 {
                  description 'Description of rate limit, support 1-79 characte'
                            + 'rs.'
                              ;
                }
              }
              ncd:revise-date 2020-06-18 ;
            }
            choice unit-style {
              description "Specify unit's style"
                          ;
              mandatory true ;
              case unit-value {
                description 'Configure the value style'
                            ;
                leaf cir {
                  description 'Configure the CIR(Committed Information Rate) va'
                            + 'lue (default: kilobits per second)'
                              ;
                  type uint32 {
                    range 8..4294967295 {
                      description 'The CIR value (default: kilobits per second)'
                                + ',support <8-4294967295>'
                                  ;
                    }
                  }
                  mandatory true ;
                }
                leaf cir-unit {
                  description 'set cir unit, such as kbps, mbps, gbps'
                              ;
                  type qos-rate-unit-type ;
                }
                leaf cbs {
                  description 'Configure the CBS(Committed Burst Size) size in '
                            + 'bytes.'
                              ;
                  type uint32 {
                    range 1..4294967295 {
                      description 'The CBS(Committed Burst Size) size in bytes,'
                                + ' support <1-4294967295>.'
                                  ;
                    }
                  }
                  units byte ;
                }
                leaf pir {
                  description 'Configure the PIR(Peak Information Rate) value ('
                            + 'default: kilobits per second)'
                              ;
                  type uint32 {
                    range 8..4294967295 {
                      description 'The PIR(Peak Information Rate) value (defaul'
                                + 't: kilobits per second), support <8-42949672'
                                + '95>'
                                  ;
                    }
                  }
                  mandatory true ;
                }
                leaf pir-unit {
                  description 'set pir unit, such as kbps, mbps, gbps'
                              ;
                  type qos-rate-unit-type ;
                }
                leaf pbs {
                  description 'Configure the PBS(Peak Burst Size) size in bytes.'
                              ;
                  type uint32 {
                    range 1..4294967295 {
                      description 'The PBS(Peak Burst Size) size in KB, support'
                                + ' <1-4294967295>'
                                  ;
                    }
                  }
                  units byte ;
                }
              }
              case unit-percentage {
                description 'Configure the percentage style'
                            ;
                leaf cir-percentage {
                  description 'Configure the CIR(Committed Information Rate) pe'
                            + 'rcentage (Set the accuracy rate per hundred (1%)'
                            + ')'
                              ;
                  type uint32 {
                    range 1..100 {
                      description 'The CIR percentage, support <1-100>'
                                  ;
                    }
                  }
                  mandatory true ;
                }
                leaf pir-percentage {
                  description 'Configure the PIR(Peak Information Rate) percent'
                            + 'age (Set the accuracy rate per hundred (1%))'
                              ;
                  type uint32 {
                    range 1..100 {
                      description 'The PIR percentage, support <1-100>'
                                  ;
                    }
                  }
                  mandatory true ;
                }
                ncd:revise-date 2020-12-23 ;
              }
            }
            choice buket-value-percent {
              if-feature car-buket-value-percent ;
              description 'Configure CIR, CBS, PIR and PBS.'
                          ;
              mandatory true ;
              case buket-value {
                description 'Configure CIR, CBS, PIR and PBS in numerical form.'
                            ;
                container c-buket {
                  description 'Configure C-buket related parameters.'
                              ;
                  container cir-value {
                    description 'Configure the CIR(Committed Information Rate).'
                                ;
                    leaf cir {
                      description 'Configure the CIR(Committed Information Rate'
                                + ') value (default: kilobits per second)'
                                  ;
                      type uint32 {
                        range 8..4294967295 {
                          description 'The CIR value (default: kilobits per sec'
                                    + 'ond),support <8-4294967295>'
                                      ;
                        }
                      }
                      mandatory true ;
                    }
                    leaf cir-unit {
                      description 'set cir unit, such as kbps, mbps, gbps, pps.'
                                  ;
                      type qos-rate-unit-type-ex ;
                    }
                  }
                  container cbs-value {
                    description 'Configure the CBS(Committed Burst Size).'
                                ;
                    presence cbs ;
                    leaf cbs {
                      description 'Configure the CBS(Committed Burst Size) valu'
                                + 'e in bytes.'
                                  ;
                      type uint32 {
                        range 1..4294967295 {
                          description 'The CBS(Committed Burst Size) size in by'
                                    + 'tes, support <1-4294967295>'
                                      ;
                        }
                      }
                      units byte ;
                      mandatory true ;
                    }
                  }
                }
                container p-buket {
                  description 'Configure P-buket related parameters.'
                              ;
                  presence p-buket ;
                  container pir-value {
                    description 'Configure the PIR(Peak Information Rate).'
                                ;
                    leaf pir {
                      description 'Configure the PIR(Peak Information Rate) val'
                                + 'ue (default: kilobits per second)'
                                  ;
                      type uint32 {
                        range 8..4294967295 {
                          description 'The PIR(Peak Information Rate) value (de'
                                    + 'fault: kilobits per second), support <8-'
                                    + '4294967295>'
                                      ;
                        }
                      }
                      mandatory true ;
                    }
                    leaf pir-unit {
                      description 'set pir unit, such as kbps, mbps, gbps, pps'
                                  ;
                      type qos-rate-unit-type-ex ;
                    }
                  }
                  container pbs-value {
                    description 'Configure the PBS(Peak Burst Size).'
                                ;
                    presence pbs ;
                    leaf pbs {
                      description 'Configure the PBS(Peak Burst Size) value in '
                                + 'bytes.'
                                  ;
                      type uint32 {
                        range 1..4294967295 {
                          description 'The PBS(Peak Burst Size) size in bytes, '
                                    + 'support <1-4294967295>'
                                      ;
                        }
                      }
                      units byte ;
                      mandatory true ;
                    }
                  }
                }
              }
              case buket-percent {
                description 'Configure CIR and PIR in percentage.'
                            ;
                container cir-percent {
                  description 'Configure CIR in percentage.'
                              ;
                  leaf cir-percent {
                    description 'Configure CIR in percentage.'
                                ;
                    type uint32 {
                      range 1..100 ;
                    }
                    mandatory true ;
                  }
                }
                container pir-percent {
                  description 'Configure PIR in percentage.'
                              ;
                  presence pir ;
                  leaf pir-percent {
                    description 'Configure PIR in percentage.'
                                ;
                    type uint32 {
                      range 1..100 ;
                    }
                    mandatory true ;
                  }
                }
              }
              ncd:revise-date 2021-01-25 ;
            }
            leaf statistical-share {
              description 'The flag of statistical-share, as follows,'+"\n"
                        + '    ture  Statistical-share is configured'+"\n"
                        + '    false Statistical-share is not configured'
                          ;
              type boolean ;
              default false ;
            }
            leaf token-bucket-id {
              description 'Set token bucket id'
                          ;
              type uint32 {
                range 1..4294967295 {
                  description 'Token bucket id'
                              ;
                }
              }
              ncd:revise-date 2019-10-28 ;
            }
            container mode {
              if-feature qos-car-mode ;
              description 'Set color mode'
                          ;
              presence 'Configure mode information'
                       ;
              leaf mode-type {
                description 'Color mode type, as follows,'+"\n"
                          + '     blind   Color-Blind mode'+"\n"
                          + '     aware   Color-Aware mode'
                            ;
                type enumeration {
                  enum blind {
                    value 1 ;
                    description 'Color-Blind mode'
                                ;
                  }
                  enum aware {
                    value 2 ;
                    description 'Color-Aware mode'
                                ;
                  }
                }
                mandatory true ;
              }
            }
            container conform-action {
              description 'Action to packets that conform to the rate limit'
                          ;
              choice action {
                description 'Specify action to packets that conform to the rate'
                          + ' limit'
                            ;
                mandatory true ;
                case ca-drop {
                  description 'Drop packet in conform-action'
                              ;
                  leaf drop {
                    description 'Specify action to drop packet'
                                ;
                    type empty ;
                    mandatory true ;
                  }
                }
                case ca-transmit {
                  description 'Transmit packet in conform-action'
                              ;
                  leaf transmit {
                    description 'Specify action to transmit packet'
                                ;
                    type empty ;
                    mandatory true ;
                  }
                }
                case ca-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in conform-action, supp'
                                + 'ort <0-7>'
                                  ;
                      type uint8 {
                        range 0..7 {
                          description 'The MPLS-EXP value, support <0-7>'
                                      ;
                        }
                      }
                      mandatory true ;
                    }
                  }
                }
                case ca-precedence {
                  description 'Rewrite packet precedence and transmit the packet'
                              ;
                  container set-prec-transmit {
                    description 'Specify action to rewrite packet precedence an'
                              + 'd transmit it'
                                ;
                    leaf prec-value {
                      description 'Reset the IP-Precedence value in conform-act'
                                + 'ion, support <0-7>'
                                  ;
                      type uint8 {
                        range 0..7 {
                          description 'The IP-Precedence value, support <0-7>'
                                      ;
                        }
                      }
                      mandatory true ;
                    }
                  }
                }
                case ca-dscp {
                  description 'Rewrite packet DSCP and transmit the packet'
                              ;
                  container set-dscp-transmit {
                    description 'Specify action to rewrite packet DSCP and tran'
                              + 'smit it'
                                ;
                    leaf dscp-value {
                      description 'Reset DSCP in conform-action, support <0-63>'
                                  ;
                      type uint8 {
                        range 0..63 {
                          description 'The DSCP value, support <0-63>'
                                      ;
                        }
                      }
                      mandatory true ;
                    }
                  }
                }
                case ca-8021p {
                  description 'Rewrite packet 802.1p and transmit the packet'
                              ;
                  container set-8021p-transmit {
                    description 'Specify action to rewrite packet 802.1p and tr'
                              + 'ansmit it'
                                ;
                    leaf value-8021p {
                      description 'Reset 802.1p in conform-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ca-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ca-service-class {
                  description 'Rewrite packet service class and transmit the pa'
                            + 'cket'
                              ;
                  container set-service-class-transmit {
                    description 'Specify action to rewrite packet service class'
                              + ' and transmit it'
                                ;
                    leaf service-class-value {
                      description 'Reset service-class in conform-action'
                                  ;
                      type qos-service-class ;
                      mandatory true ;
                    }
                  }
                  ncd:revise-date 2020-05-18 ;
                }
              }
            }
            container exceed-action {
              description 'Action to packets that exceed the rate limit'
                          ;
              choice action {
                description 'Specify action to packets that exceed the rate lim'
                          + 'it'
                            ;
                mandatory true ;
                case ea-drop {
                  description 'Drop packet in exceed-action'
                              ;
                  leaf drop {
                    description 'Specify action to drop packet'
                                ;
                    type empty ;
                    mandatory true ;
                  }
                }
                case ea-transmit {
                  description 'Transmit packet in exceed-action'
                              ;
                  leaf transmit {
                    description 'Specify action to transmit packet'
                                ;
                    type empty ;
                    mandatory true ;
                  }
                }
                case ea-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in exceed-action, suppo'
                                + 'rt <0-7>'
                                  ;
                      type uint8 {
                        range 0..7 {
                          description 'The MPLS-EXP value, support <0-7>'
                                      ;
                        }
                      }
                      mandatory true ;
                    }
                  }
                }
                case ea-precedence {
                  description 'Rewrite packet precedence and transmit the packet'
                              ;
                  container set-prec-transmit {
                    description 'Specify action to rewrite packet precedence an'
                              + 'd transmit it'
                                ;
                    leaf prec-value {
                      description 'Reset the IP-Precedence value in exceed-acti'
                                + 'on, support <0-7>'
                                  ;
                      type uint8 {
                        range 0..7 {
                          description 'The IP-Precedence value, support <0-7>'
                                      ;
                        }
                      }
                      mandatory true ;
                    }
                  }
                }
                case ea-dscp {
                  description 'Rewrite packet DSCP and transmit the packet'
                              ;
                  container set-dscp-transmit {
                    description 'Specify action to rewrite packet DSCP and tran'
                              + 'smit it'
                                ;
                    leaf dscp-value {
                      description 'Reset DSCP in exceed-action, support <0-63>'
                                  ;
                      type uint8 {
                        range 0..63 {
                          description 'The DSCP value, support <0-63>'
                                      ;
                        }
                      }
                      mandatory true ;
                    }
                  }
                }
                case ea-8021p {
                  description 'Rewrite packet 802.1p and transmit the packet'
                              ;
                  container set-8021p-transmit {
                    description 'Specify action to rewrite packet 802.1p and tr'
                              + 'ansmit it'
                                ;
                    leaf value-8021p {
                      description 'Reset 802.1p in exceed-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ea-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ea-service-class {
                  description 'Rewrite packet service class and transmit the pa'
                            + 'cket'
                              ;
                  container set-service-class-transmit {
                    description 'Specify action to rewrite packet service class'
                              + ' and transmit it'
                                ;
                    leaf service-class-value {
                      description 'Reset service class in exceed-action'
                                  ;
                      type qos-service-class ;
                      mandatory true ;
                    }
                  }
                  ncd:revise-date 2020-05-18 ;
                }
              }
            }
            container violate-action {
              description 'Action to packets that violate the rate limit'
                          ;
              choice action {
                description 'Specify action to packets that violate the rate li'
                          + 'mit'
                            ;
                mandatory true ;
                case va-drop {
                  description 'Drop packet in violate-action'
                              ;
                  leaf drop {
                    description 'Specify action to drop packet'
                                ;
                    type empty ;
                    mandatory true ;
                  }
                }
                case va-transmit {
                  description 'Transmit packet in violate-action'
                              ;
                  leaf transmit {
                    description 'Specify action to transmit packet'
                                ;
                    type empty ;
                    mandatory true ;
                  }
                }
                case va-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in violate-action, supp'
                                + 'ort <0-7>'
                                  ;
                      type uint8 {
                        range 0..7 {
                          description 'The MPLS-EXP value, support <0-7>'
                                      ;
                        }
                      }
                      mandatory true ;
                    }
                  }
                }
                case va-precedence {
                  description 'Rewrite packet precedence and transmit the packet'
                              ;
                  container set-prec-transmit {
                    description 'Specify action to rewrite packet precedence an'
                              + 'd transmit it'
                                ;
                    leaf prec-value {
                      description 'Reset the IP-Precedence value in violate-act'
                                + 'ion, support <0-7>'
                                  ;
                      type uint8 {
                        range 0..7 ;
                      }
                      mandatory true ;
                    }
                  }
                }
                case va-dscp {
                  description 'Rewrite packet DSCP and transmit the packet'
                              ;
                  container set-dscp-transmit {
                    description 'Specify action to rewrite packet DSCP and tran'
                              + 'smit it'
                                ;
                    leaf dscp-value {
                      description 'Reset DSCP in violate-action, support <0-63>'
                                  ;
                      type uint8 {
                        range 0..63 {
                          description 'The DSCP value, support <0-63>'
                                      ;
                        }
                      }
                      mandatory true ;
                    }
                  }
                }
                case va-8021p {
                  description 'Rewrite packet 802.1p and transmit the packet'
                              ;
                  container set-8021p-transmit {
                    description 'Specify action to rewrite packet 802.1p and tr'
                              + 'ansmit it'
                                ;
                    leaf value-8021p {
                      description 'Reset 802.1p in violate-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case va-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case va-service-class {
                  description 'Rewrite packet service class and transmit the pa'
                            + 'cket'
                              ;
                  container set-service-class-transmit {
                    description 'Specify action to rewrite packet service class'
                              + ' and transmit it'
                                ;
                    leaf service-class-value {
                      description 'Reset service class in violate-action'
                                  ;
                      type qos-service-class ;
                      mandatory true ;
                    }
                  }
                  ncd:revise-date 2020-05-18 ;
                }
              }
            }
          }
        }
        container unknown-multicasts {
          description 'Match unknown multicast'
                      ;
          list unknown-multicast {
            description 'Configure interface rate limit based on matching unkno'
                      + 'wn multicast'
                        ;
            key 'if-name if-direct'
                ;
            leaf if-name {
              description 'Configure the name of the attaching interface'
                          ;
              type ncd:ifname {
                length 1..31 {
                  description 'Name of the attaching interface, support 1-31 ch'
                            + 'aracters'
                              ;
                }
              }
            }
            leaf if-direct {
              description 'Specify the direction of interface, as follows,'+"\n"
                        + '     input  Rate limit on input'+"\n"
                        + '     output Rate limit on output'
                          ;
              type enumeration {
                enum input {
                  value 1 ;
                  description 'Rate limit on input'
                              ;
                }
                enum output {
                  value 2 ;
                  description 'Rate limit on output'
                              ;
                }
              }
            }
            leaf rate-limit-desc {
              description 'Description of rate limit, support 1-79 characters.'
                          ;
              type ncd:string-with-blank {
                length 1..79 {
                  description 'Description of rate limit, support 1-79 characte'
                            + 'rs.'
                              ;
                }
              }
              ncd:revise-date 2020-06-18 ;
            }
            choice unit-style {
              description "Specify unit's style"
                          ;
              mandatory true ;
              case unit-value {
                description 'Configure the value style'
                            ;
                leaf cir {
                  description 'Configure the CIR(Committed Information Rate) va'
                            + 'lue (default: kilobits per second)'
                              ;
                  type uint32 {
                    range 8..4294967295 {
                      description 'The CIR value (default: kilobits per second)'
                                + ',support <8-4294967295>'
                                  ;
                    }
                  }
                  mandatory true ;
                }
                leaf cir-unit {
                  description 'set cir unit, such as kbps, mbps, gbps'
                              ;
                  type qos-rate-unit-type ;
                }
                leaf cbs {
                  description 'Configure the CBS(Committed Burst Size) size in '
                            + 'bytes.'
                              ;
                  type uint32 {
                    range 1..4294967295 {
                      description 'The CBS(Committed Burst Size) size in bytes,'
                                + ' support <1-4294967295>.'
                                  ;
                    }
                  }
                  units byte ;
                }
                leaf pir {
                  description 'Configure the PIR(Peak Information Rate) value ('
                            + 'default: kilobits per second)'
                              ;
                  type uint32 {
                    range 8..4294967295 {
                      description 'The PIR(Peak Information Rate) value (defaul'
                                + 't: kilobits per second), support <8-42949672'
                                + '95>'
                                  ;
                    }
                  }
                  mandatory true ;
                }
                leaf pir-unit {
                  description 'set pir unit, such as kbps, mbps, gbps'
                              ;
                  type qos-rate-unit-type ;
                }
                leaf pbs {
                  description 'Configure the PBS(Peak Burst Size) size in bytes.'
                              ;
                  type uint32 {
                    range 1..4294967295 {
                      description 'The PBS(Peak Burst Size) size in KB, support'
                                + ' <1-4294967295>'
                                  ;
                    }
                  }
                  units byte ;
                }
              }
              case unit-percentage {
                description 'Configure the percentage style'
                            ;
                leaf cir-percentage {
                  description 'Configure the CIR(Committed Information Rate) pe'
                            + 'rcentage (Set the accuracy rate per hundred (1%)'
                            + ')'
                              ;
                  type uint32 {
                    range 1..100 {
                      description 'The CIR percentage, support <1-100>'
                                  ;
                    }
                  }
                  mandatory true ;
                }
                leaf pir-percentage {
                  description 'Configure the PIR(Peak Information Rate) percent'
                            + 'age (Set the accuracy rate per hundred (1%))'
                              ;
                  type uint32 {
                    range 1..100 {
                      description 'The PIR percentage, support <1-100>'
                                  ;
                    }
                  }
                  mandatory true ;
                }
                ncd:revise-date 2020-12-23 ;
              }
            }
            choice buket-value-percent {
              if-feature car-buket-value-percent ;
              description 'Configure CIR, CBS, PIR and PBS.'
                          ;
              mandatory true ;
              case buket-value {
                description 'Configure CIR, CBS, PIR and PBS in numerical form.'
                            ;
                container c-buket {
                  description 'Configure C-buket related parameters.'
                              ;
                  container cir-value {
                    description 'Configure the CIR(Committed Information Rate).'
                                ;
                    leaf cir {
                      description 'Configure the CIR(Committed Information Rate'
                                + ') value (default: kilobits per second)'
                                  ;
                      type uint32 {
                        range 8..4294967295 {
                          description 'The CIR value (default: kilobits per sec'
                                    + 'ond),support <8-4294967295>'
                                      ;
                        }
                      }
                      mandatory true ;
                    }
                    leaf cir-unit {
                      description 'set cir unit, such as kbps, mbps, gbps, pps.'
                                  ;
                      type qos-rate-unit-type-ex ;
                    }
                  }
                  container cbs-value {
                    description 'Configure the CBS(Committed Burst Size).'
                                ;
                    presence cbs ;
                    leaf cbs {
                      description 'Configure the CBS(Committed Burst Size) valu'
                                + 'e in bytes.'
                                  ;
                      type uint32 {
                        range 1..4294967295 {
                          description 'The CBS(Committed Burst Size) size in by'
                                    + 'tes, support <1-4294967295>'
                                      ;
                        }
                      }
                      units byte ;
                      mandatory true ;
                    }
                  }
                }
                container p-buket {
                  description 'Configure P-buket related parameters.'
                              ;
                  presence p-buket ;
                  container pir-value {
                    description 'Configure the PIR(Peak Information Rate).'
                                ;
                    leaf pir {
                      description 'Configure the PIR(Peak Information Rate) val'
                                + 'ue (default: kilobits per second)'
                                  ;
                      type uint32 {
                        range 8..4294967295 {
                          description 'The PIR(Peak Information Rate) value (de'
                                    + 'fault: kilobits per second), support <8-'
                                    + '4294967295>'
                                      ;
                        }
                      }
                      mandatory true ;
                    }
                    leaf pir-unit {
                      description 'set pir unit, such as kbps, mbps, gbps, pps'
                                  ;
                      type qos-rate-unit-type-ex ;
                    }
                  }
                  container pbs-value {
                    description 'Configure the PBS(Peak Burst Size).'
                                ;
                    presence pbs ;
                    leaf pbs {
                      description 'Configure the PBS(Peak Burst Size) value in '
                                + 'bytes.'
                                  ;
                      type uint32 {
                        range 1..4294967295 {
                          description 'The PBS(Peak Burst Size) size in bytes, '
                                    + 'support <1-4294967295>'
                                      ;
                        }
                      }
                      units byte ;
                      mandatory true ;
                    }
                  }
                }
              }
              case buket-percent {
                description 'Configure CIR and PIR in percentage.'
                            ;
                container cir-percent {
                  description 'Configure CIR in percentage.'
                              ;
                  leaf cir-percent {
                    description 'Configure CIR in percentage.'
                                ;
                    type uint32 {
                      range 1..100 ;
                    }
                    mandatory true ;
                  }
                }
                container pir-percent {
                  description 'Configure PIR in percentage.'
                              ;
                  presence pir ;
                  leaf pir-percent {
                    description 'Configure PIR in percentage.'
                                ;
                    type uint32 {
                      range 1..100 ;
                    }
                    mandatory true ;
                  }
                }
              }
              ncd:revise-date 2021-01-25 ;
            }
            leaf statistical-share {
              description 'The flag of statistical-share, as follows,'+"\n"
                        + '    ture  Statistical-share is configured'+"\n"
                        + '    false Statistical-share is not configured'
                          ;
              type boolean ;
              default false ;
            }
            leaf token-bucket-id {
              description 'Set token bucket id'
                          ;
              type uint32 {
                range 1..4294967295 {
                  description 'Token bucket id'
                              ;
                }
              }
              ncd:revise-date 2019-10-28 ;
            }
            container mode {
              if-feature qos-car-mode ;
              description 'Set color mode'
                          ;
              presence 'Configure mode information'
                       ;
              leaf mode-type {
                description 'Color mode type, as follows,'+"\n"
                          + '     blind   Color-Blind mode'+"\n"
                          + '     aware   Color-Aware mode'
                            ;
                type enumeration {
                  enum blind {
                    value 1 ;
                    description 'Color-Blind mode'
                                ;
                  }
                  enum aware {
                    value 2 ;
                    description 'Color-Aware mode'
                                ;
                  }
                }
                mandatory true ;
              }
            }
            container conform-action {
              description 'Action to packets that conform to the rate limit'
                          ;
              choice action {
                description 'Specify action to packets that conform to the rate'
                          + ' limit'
                            ;
                mandatory true ;
                case ca-drop {
                  description 'Drop packet in conform-action'
                              ;
                  leaf drop {
                    description 'Specify action to drop packet'
                                ;
                    type empty ;
                    mandatory true ;
                  }
                }
                case ca-transmit {
                  description 'Transmit packet in conform-action'
                              ;
                  leaf transmit {
                    description 'Specify action to transmit packet'
                                ;
                    type empty ;
                    mandatory true ;
                  }
                }
                case ca-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in conform-action, supp'
                                + 'ort <0-7>'
                                  ;
                      type uint8 {
                        range 0..7 {
                          description 'The MPLS-EXP value, support <0-7>'
                                      ;
                        }
                      }
                      mandatory true ;
                    }
                  }
                }
                case ca-precedence {
                  description 'Rewrite packet precedence and transmit the packet'
                              ;
                  container set-prec-transmit {
                    description 'Specify action to rewrite packet precedence an'
                              + 'd transmit it'
                                ;
                    leaf prec-value {
                      description 'Reset the IP-Precedence value in conform-act'
                                + 'ion, support <0-7>'
                                  ;
                      type uint8 {
                        range 0..7 {
                          description 'The IP-Precedence value, support <0-7>'
                                      ;
                        }
                      }
                      mandatory true ;
                    }
                  }
                }
                case ca-dscpCopy {
                  description 'Rewrite packet DSCP and transmit the packet'
                              ;
                  container set-dscp-transmit {
                    description 'Specify action to rewrite packet DSCP and tran'
                              + 'smit it'
                                ;
                    leaf dscp-value {
                      description 'Reset DSCP in conform-action, support <0-63>'
                                  ;
                      type uint8 {
                        range 0..63 {
                          description 'The DSCP value, support <0-63>'
                                      ;
                        }
                      }
                      mandatory true ;
                    }
                  }
                  ncd:revise-date 2020-05-18 ;
                }
                case ca-8021p {
                  description 'Rewrite packet 802.1p and transmit the packet'
                              ;
                  container set-8021p-transmit {
                    description 'Specify action to rewrite packet 802.1p and tr'
                              + 'ansmit it'
                                ;
                    leaf value-8021p {
                      description 'Reset 802.1p in conform-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ca-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ca-service-class {
                  description 'Rewrite packet service class and transmit the pa'
                            + 'cket'
                              ;
                  container set-service-class-transmit {
                    description 'Specify action to rewrite packet service class'
                              + ' and transmit it'
                                ;
                    leaf service-class-value {
                      description 'Reset service class in conform-action'
                                  ;
                      type qos-service-class ;
                      mandatory true ;
                    }
                  }
                  ncd:revise-date 2020-05-18 ;
                }
              }
            }
            container exceed-action {
              description 'Action to packets that exceed the rate limit'
                          ;
              choice action {
                description 'Specify action to packets that exceed the rate lim'
                          + 'it'
                            ;
                mandatory true ;
                case ea-drop {
                  description 'Drop packet in exceed-action'
                              ;
                  leaf drop {
                    description 'Specify action to drop packet'
                                ;
                    type empty ;
                    mandatory true ;
                  }
                }
                case ea-transmit {
                  description 'Transmit packet in exceed-action'
                              ;
                  leaf transmit {
                    description 'Specify action to transmit packet'
                                ;
                    type empty ;
                    mandatory true ;
                  }
                }
                case ea-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in exceed-action, suppo'
                                + 'rt <0-7>'
                                  ;
                      type uint8 {
                        range 0..7 {
                          description 'The MPLS-EXP value, support <0-7>'
                                      ;
                        }
                      }
                      mandatory true ;
                    }
                  }
                }
                case ea-precedence {
                  description 'Rewrite packet precedence and transmit the packet'
                              ;
                  container set-prec-transmit {
                    description 'Specify action to rewrite packet precedence an'
                              + 'd transmit it'
                                ;
                    leaf prec-value {
                      description 'Reset the IP-Precedence value in exceed-acti'
                                + 'on, support <0-7>'
                                  ;
                      type uint8 {
                        range 0..7 {
                          description 'The IP-Precedence value, support <0-7>'
                                      ;
                        }
                      }
                      mandatory true ;
                    }
                  }
                }
                case ea-dscp {
                  description 'Rewrite packet DSCP and transmit the packet'
                              ;
                  container set-dscp-transmit {
                    description 'Specify action to rewrite packet DSCP and tran'
                              + 'smit it'
                                ;
                    leaf dscp-value {
                      description 'Reset DSCP in exceed-action, support <0-63>'
                                  ;
                      type uint8 {
                        range 0..63 {
                          description 'The DSCP value, support <0-63>'
                                      ;
                        }
                      }
                      mandatory true ;
                    }
                  }
                }
                case ea-8021p {
                  description 'Rewrite packet 802.1p and transmit the packet'
                              ;
                  container set-8021p-transmit {
                    description 'Specify action to rewrite packet 802.1p and tr'
                              + 'ansmit it'
                                ;
                    leaf value-8021p {
                      description 'Reset 802.1p in exceed-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ea-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ea-service-class {
                  description 'Rewrite packet DSCP and transmit the packet'
                              ;
                  container set-service-class-transmit {
                    description 'Specify action to rewrite packet service class'
                              + ' and transmit it'
                                ;
                    leaf service-class-value {
                      description 'Reset service class in exceed-action'
                                  ;
                      type qos-service-class ;
                      mandatory true ;
                    }
                  }
                  ncd:revise-date 2020-05-18 ;
                }
              }
            }
            container violate-action {
              description 'Action to packets that violate the rate limit'
                          ;
              choice action {
                description 'Specify action to packets that violate the rate li'
                          + 'mit'
                            ;
                mandatory true ;
                case va-drop {
                  description 'Drop packet in violate-action'
                              ;
                  leaf drop {
                    description 'Specify action to drop packet'
                                ;
                    type empty ;
                    mandatory true ;
                  }
                }
                case va-transmit {
                  description 'Transmit packet in violate-action'
                              ;
                  leaf transmit {
                    description 'Specify action to transmit packet'
                                ;
                    type empty ;
                    mandatory true ;
                  }
                }
                case va-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in violate-action, supp'
                                + 'ort <0-7>'
                                  ;
                      type uint8 {
                        range 0..7 {
                          description 'The MPLS-EXP value, support <0-7>'
                                      ;
                        }
                      }
                      mandatory true ;
                    }
                  }
                }
                case va-precedence {
                  description 'Rewrite packet precedence and transmit the packet'
                              ;
                  container set-prec-transmit {
                    description 'Specify action to rewrite packet precedence an'
                              + 'd transmit it'
                                ;
                    leaf prec-value {
                      description 'Reset the IP-Precedence value in violate-act'
                                + 'ion, support <0-7>'
                                  ;
                      type uint8 {
                        range 0..7 ;
                      }
                      mandatory true ;
                    }
                  }
                }
                case va-dscp {
                  description 'Rewrite packet DSCP and transmit the packet'
                              ;
                  container set-dscp-transmit {
                    description 'Specify action to rewrite packet DSCP and tran'
                              + 'smit it'
                                ;
                    leaf dscp-value {
                      description 'Reset DSCP in violate-action, support <0-63>'
                                  ;
                      type uint8 {
                        range 0..63 {
                          description 'The DSCP value, support <0-63>'
                                      ;
                        }
                      }
                      mandatory true ;
                    }
                  }
                }
                case va-8021p {
                  description 'Rewrite packet 802.1p and transmit the packet'
                              ;
                  container set-8021p-transmit {
                    description 'Specify action to rewrite packet 802.1p and tr'
                              + 'ansmit it'
                                ;
                    leaf value-8021p {
                      description 'Reset 802.1p in violate-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case va-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case va-service-class {
                  description 'Rewrite packet service class and transmit the pa'
                            + 'cket'
                              ;
                  container set-service-class-transmit {
                    description 'Specify action to rewrite packet service class'
                              + ' and transmit it'
                                ;
                    leaf service-class-value {
                      description 'Reset service class in violate-action'
                                  ;
                      type qos-service-class ;
                      mandatory true ;
                    }
                  }
                  ncd:revise-date 2020-05-18 ;
                }
              }
            }
          }
          ncd:revise-date 2015-10-28 ;
        }
        container broadcasts {
          description 'Match broadcast, only for VPLS'
                      ;
          list broadcast {
            description 'Configure interface rate limit based on matching broad'
                      + 'cast'
                        ;
            key 'if-name if-direct'
                ;
            leaf if-name {
              description 'Configure the name of the attaching interface'
                          ;
              type ncd:ifname {
                length 1..31 {
                  description 'Name of the attaching interface, support 1-31 ch'
                            + 'aracters'
                              ;
                }
              }
            }
            leaf if-direct {
              description 'Specify the direction of interface, as follows,'+"\n"
                        + '     input  Rate limit on input'+"\n"
                        + '     output Rate limit on output'
                          ;
              type enumeration {
                enum input {
                  value 1 ;
                  description 'Rate limit on input'
                              ;
                }
                enum output {
                  value 2 ;
                  description 'Rate limit on output'
                              ;
                }
              }
            }
            leaf rate-limit-desc {
              description 'Description of rate limit, support 1-79 characters.'
                          ;
              type ncd:string-with-blank {
                length 1..79 {
                  description 'Description of rate limit, support 1-79 characte'
                            + 'rs.'
                              ;
                }
              }
              ncd:revise-date 2020-06-18 ;
            }
            choice unit-style {
              description "Specify unit's style"
                          ;
              mandatory true ;
              case unit-value {
                description 'Configure the value style'
                            ;
                leaf cir {
                  description 'Configure the CIR(Committed Information Rate) va'
                            + 'lue (default: kilobits per second)'
                              ;
                  type uint32 {
                    range 8..4294967295 {
                      description 'The CIR value (default: kilobits per second)'
                                + ',support <8-4294967295>'
                                  ;
                    }
                  }
                  mandatory true ;
                }
                leaf cir-unit {
                  description 'set cir unit, such as kbps, mbps, gbps'
                              ;
                  type qos-rate-unit-type ;
                }
                leaf cbs {
                  description 'Configure the CBS(Committed Burst Size) size in '
                            + 'bytes.'
                              ;
                  type uint32 {
                    range 1..4294967295 {
                      description 'The CBS(Committed Burst Size) size in bytes,'
                                + ' support <1-4294967295>.'
                                  ;
                    }
                  }
                  units byte ;
                }
                leaf pir {
                  description 'Configure the PIR(Peak Information Rate) value ('
                            + 'default: kilobits per second)'
                              ;
                  type uint32 {
                    range 8..4294967295 {
                      description 'The PIR(Peak Information Rate) value (defaul'
                                + 't: kilobits per second), support <8-42949672'
                                + '95>'
                                  ;
                    }
                  }
                  mandatory true ;
                }
                leaf pir-unit {
                  description 'set pir unit, such as kbps, mbps, gbps'
                              ;
                  type qos-rate-unit-type ;
                }
                leaf pbs {
                  description 'Configure the PBS(Peak Burst Size) size in bytes.'
                              ;
                  type uint32 {
                    range 1..4294967295 {
                      description 'The PBS(Peak Burst Size) size in KB, support'
                                + ' <1-4294967295>'
                                  ;
                    }
                  }
                  units byte ;
                }
              }
              case unit-percentage {
                description 'Configure the percentage style'
                            ;
                leaf cir-percentage {
                  description 'Configure the CIR(Committed Information Rate) pe'
                            + 'rcentage (Set the accuracy rate per hundred (1%)'
                            + ')'
                              ;
                  type uint32 {
                    range 1..100 {
                      description 'The CIR percentage, support <1-100>'
                                  ;
                    }
                  }
                  mandatory true ;
                }
                leaf pir-percentage {
                  description 'Configure the PIR(Peak Information Rate) percent'
                            + 'age (Set the accuracy rate per hundred (1%))'
                              ;
                  type uint32 {
                    range 1..100 {
                      description 'The PIR percentage, support <1-100>'
                                  ;
                    }
                  }
                  mandatory true ;
                }
                ncd:revise-date 2020-12-23 ;
              }
            }
            choice buket-value-percent {
              if-feature car-buket-value-percent ;
              description 'Configure CIR, CBS, PIR and PBS.'
                          ;
              mandatory true ;
              case buket-value {
                description 'Configure CIR, CBS, PIR and PBS in numerical form.'
                            ;
                container c-buket {
                  description 'Configure C-buket related parameters.'
                              ;
                  container cir-value {
                    description 'Configure the CIR(Committed Information Rate).'
                                ;
                    leaf cir {
                      description 'Configure the CIR(Committed Information Rate'
                                + ') value (default: kilobits per second)'
                                  ;
                      type uint32 {
                        range 8..4294967295 {
                          description 'The CIR value (default: kilobits per sec'
                                    + 'ond),support <8-4294967295>'
                                      ;
                        }
                      }
                      mandatory true ;
                    }
                    leaf cir-unit {
                      description 'set cir unit, such as kbps, mbps, gbps, pps.'
                                  ;
                      type qos-rate-unit-type-ex ;
                    }
                  }
                  container cbs-value {
                    description 'Configure the CBS(Committed Burst Size).'
                                ;
                    presence cbs ;
                    leaf cbs {
                      description 'Configure the CBS(Committed Burst Size) valu'
                                + 'e in bytes.'
                                  ;
                      type uint32 {
                        range 1..4294967295 {
                          description 'The CBS(Committed Burst Size) size in by'
                                    + 'tes, support <1-4294967295>'
                                      ;
                        }
                      }
                      units byte ;
                      mandatory true ;
                    }
                  }
                }
                container p-buket {
                  description 'Configure P-buket related parameters.'
                              ;
                  presence p-buket ;
                  container pir-value {
                    description 'Configure the PIR(Peak Information Rate).'
                                ;
                    leaf pir {
                      description 'Configure the PIR(Peak Information Rate) val'
                                + 'ue (default: kilobits per second)'
                                  ;
                      type uint32 {
                        range 8..4294967295 {
                          description 'The PIR(Peak Information Rate) value (de'
                                    + 'fault: kilobits per second), support <8-'
                                    + '4294967295>'
                                      ;
                        }
                      }
                      mandatory true ;
                    }
                    leaf pir-unit {
                      description 'set pir unit, such as kbps, mbps, gbps, pps'
                                  ;
                      type qos-rate-unit-type-ex ;
                    }
                  }
                  container pbs-value {
                    description 'Configure the PBS(Peak Burst Size).'
                                ;
                    presence pbs ;
                    leaf pbs {
                      description 'Configure the PBS(Peak Burst Size) value in '
                                + 'bytes.'
                                  ;
                      type uint32 {
                        range 1..4294967295 {
                          description 'The PBS(Peak Burst Size) size in bytes, '
                                    + 'support <1-4294967295>'
                                      ;
                        }
                      }
                      units byte ;
                      mandatory true ;
                    }
                  }
                }
              }
              case buket-percent {
                description 'Configure CIR and PIR in percentage.'
                            ;
                container cir-percent {
                  description 'Configure CIR in percentage.'
                              ;
                  leaf cir-percent {
                    description 'Configure CIR in percentage.'
                                ;
                    type uint32 {
                      range 1..100 ;
                    }
                    mandatory true ;
                  }
                }
                container pir-percent {
                  description 'Configure PIR in percentage.'
                              ;
                  presence pir ;
                  leaf pir-percent {
                    description 'Configure PIR in percentage.'
                                ;
                    type uint32 {
                      range 1..100 ;
                    }
                    mandatory true ;
                  }
                }
              }
              ncd:revise-date 2021-01-25 ;
            }
            leaf statistical-share {
              description 'The flag of statistical-share, as follows,'+"\n"
                        + '    ture  Statistical-share is configured'+"\n"
                        + '    false Statistical-share is not configured'
                          ;
              type boolean ;
              default false ;
            }
            leaf token-bucket-id {
              description 'Set token bucket id'
                          ;
              type uint32 {
                range 1..4294967295 {
                  description 'Token bucket id'
                              ;
                }
              }
              ncd:revise-date 2019-10-28 ;
            }
            container mode {
              if-feature qos-car-mode ;
              description 'Set color mode'
                          ;
              presence 'Configure mode information'
                       ;
              leaf mode-type {
                description 'Color mode type, as follows,'+"\n"
                          + '     blind   Color-Blind mode'+"\n"
                          + '     aware   Color-Aware mode'
                            ;
                type enumeration {
                  enum blind {
                    value 1 ;
                    description 'Color-Blind mode'
                                ;
                  }
                  enum aware {
                    value 2 ;
                    description 'Color-Aware mode'
                                ;
                  }
                }
                mandatory true ;
              }
            }
            container conform-action {
              description 'Action to packets that conform to the rate limit'
                          ;
              choice action {
                description 'Specify action to packets that conform to the rate'
                          + ' limit'
                            ;
                mandatory true ;
                case ca-drop {
                  description 'Drop packet in conform-action'
                              ;
                  leaf drop {
                    description 'Specify action to drop packet'
                                ;
                    type empty ;
                    mandatory true ;
                  }
                }
                case ca-transmit {
                  description 'Transmit packet in conform-action'
                              ;
                  leaf transmit {
                    description 'Specify action to transmit packet'
                                ;
                    type empty ;
                    mandatory true ;
                  }
                }
                case ca-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in conform-action, supp'
                                + 'ort <0-7>'
                                  ;
                      type uint8 {
                        range 0..7 {
                          description 'The MPLS-EXP value, support <0-7>'
                                      ;
                        }
                      }
                      mandatory true ;
                    }
                  }
                }
                case ca-precedence {
                  description 'Rewrite packet precedence and transmit the packet'
                              ;
                  container set-prec-transmit {
                    description 'Specify action to rewrite packet precedence an'
                              + 'd transmit it'
                                ;
                    leaf prec-value {
                      description 'Reset the IP-Precedence value in conform-act'
                                + 'ion, support <0-7>'
                                  ;
                      type uint8 {
                        range 0..7 {
                          description 'The IP-Precedence value, support <0-7>'
                                      ;
                        }
                      }
                      mandatory true ;
                    }
                  }
                }
                case ca-dscp {
                  description 'Rewrite packet DSCP and transmit the packet'
                              ;
                  container set-dscp-transmit {
                    description 'Specify action to rewrite packet DSCP and tran'
                              + 'smit it'
                                ;
                    leaf dscp-value {
                      description 'Reset DSCP in conform-action, support <0-63>'
                                  ;
                      type uint8 {
                        range 0..63 {
                          description 'The DSCP value, support <0-63>'
                                      ;
                        }
                      }
                      mandatory true ;
                    }
                  }
                }
                case ca-8021p {
                  description 'Rewrite packet 802.1p and transmit the packet'
                              ;
                  container set-8021p-transmit {
                    description 'Specify action to rewrite packet 802.1p and tr'
                              + 'ansmit it'
                                ;
                    leaf value-8021p {
                      description 'Reset 802.1p in conform-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ca-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ca-service-class {
                  description 'Rewrite packet service class and transmit the pa'
                            + 'cket'
                              ;
                  container set-service-class-transmit {
                    description 'Specify action to rewrite packet service class'
                              + ' and transmit it'
                                ;
                    leaf service-class-value {
                      description 'Reset service class in conform-action'
                                  ;
                      type qos-service-class ;
                      mandatory true ;
                    }
                  }
                  ncd:revise-date 2020-05-18 ;
                }
              }
            }
            container exceed-action {
              description 'Action to packets that exceed the rate limit'
                          ;
              choice action {
                description 'Specify action to packets that exceed the rate lim'
                          + 'it'
                            ;
                mandatory true ;
                case ea-drop {
                  description 'Drop packet in exceed-action'
                              ;
                  leaf drop {
                    description 'Specify action to drop packet'
                                ;
                    type empty ;
                    mandatory true ;
                  }
                }
                case ea-transmit {
                  description 'Transmit packet in exceed-action'
                              ;
                  leaf transmit {
                    description 'Specify action to transmit packet'
                                ;
                    type empty ;
                    mandatory true ;
                  }
                }
                case ea-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in exceed-action, suppo'
                                + 'rt <0-7>'
                                  ;
                      type uint8 {
                        range 0..7 {
                          description 'The MPLS-EXP value, support <0-7>'
                                      ;
                        }
                      }
                      mandatory true ;
                    }
                  }
                }
                case ea-precedence {
                  description 'Rewrite packet precedence and transmit the packet'
                              ;
                  container set-prec-transmit {
                    description 'Specify action to rewrite packet precedence an'
                              + 'd transmit it'
                                ;
                    leaf prec-value {
                      description 'Reset the IP-Precedence value in exceed-acti'
                                + 'on, support <0-7>'
                                  ;
                      type uint8 {
                        range 0..7 {
                          description 'The IP-Precedence value, support <0-7>'
                                      ;
                        }
                      }
                      mandatory true ;
                    }
                  }
                }
                case ea-dscp {
                  description 'Rewrite packet DSCP and transmit the packet'
                              ;
                  container set-dscp-transmit {
                    description 'Specify action to rewrite packet DSCP and tran'
                              + 'smit it'
                                ;
                    leaf dscp-value {
                      description 'Reset DSCP in exceed-action, support <0-63>'
                                  ;
                      type uint8 {
                        range 0..63 {
                          description 'The DSCP value, support <0-63>'
                                      ;
                        }
                      }
                      mandatory true ;
                    }
                  }
                }
                case ea-8021p {
                  description 'Rewrite packet 802.1p and transmit the packet'
                              ;
                  container set-8021p-transmit {
                    description 'Specify action to rewrite packet 802.1p and tr'
                              + 'ansmit it'
                                ;
                    leaf value-8021p {
                      description 'Reset 802.1p in exceed-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ea-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ea-service-class {
                  description 'Rewrite packet service class and transmit the pa'
                            + 'cket'
                              ;
                  container set-service-class-transmit {
                    description 'Specify action to rewrite packet service class'
                              + ' and transmit it'
                                ;
                    leaf service-class-value {
                      description 'Reset service class in exceed-action'
                                  ;
                      type qos-service-class ;
                      mandatory true ;
                    }
                  }
                  ncd:revise-date 2020-05-18 ;
                }
              }
            }
            container violate-action {
              description 'Action to packets that violate the rate limit'
                          ;
              choice action {
                description 'Specify action to packets that violate the rate li'
                          + 'mit'
                            ;
                mandatory true ;
                case va-drop {
                  description 'Drop packet in violate-action'
                              ;
                  leaf drop {
                    description 'Specify action to drop packet'
                                ;
                    type empty ;
                    mandatory true ;
                  }
                }
                case va-transmit {
                  description 'Transmit packet in violate-action'
                              ;
                  leaf transmit {
                    description 'Specify action to transmit packet'
                                ;
                    type empty ;
                    mandatory true ;
                  }
                }
                case va-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in violate-action, supp'
                                + 'ort <0-7>'
                                  ;
                      type uint8 {
                        range 0..7 {
                          description 'The MPLS-EXP value, support <0-7>'
                                      ;
                        }
                      }
                      mandatory true ;
                    }
                  }
                }
                case va-precedence {
                  description 'Rewrite packet precedence and transmit the packet'
                              ;
                  container set-prec-transmit {
                    description 'Specify action to rewrite packet precedence an'
                              + 'd transmit it'
                                ;
                    leaf prec-value {
                      description 'Reset the IP-Precedence value in violate-act'
                                + 'ion, support <0-7>'
                                  ;
                      type uint8 {
                        range 0..7 ;
                      }
                      mandatory true ;
                    }
                  }
                }
                case va-dscp {
                  description 'Rewrite packet DSCP and transmit the packet'
                              ;
                  container set-dscp-transmit {
                    description 'Specify action to rewrite packet DSCP and tran'
                              + 'smit it'
                                ;
                    leaf dscp-value {
                      description 'Reset DSCP in violate-action, support <0-63>'
                                  ;
                      type uint8 {
                        range 0..63 {
                          description 'The DSCP value, support <0-63>'
                                      ;
                        }
                      }
                      mandatory true ;
                    }
                  }
                }
                case va-8021p {
                  description 'Rewrite packet 802.1p and transmit the packet'
                              ;
                  container set-8021p-transmit {
                    description 'Specify action to rewrite packet 802.1p and tr'
                              + 'ansmit it'
                                ;
                    leaf value-8021p {
                      description 'Reset 802.1p in violate-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case va-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case va-service-class {
                  description 'Rewrite packet service class and transmit the pa'
                            + 'cket'
                              ;
                  container set-service-class-transmit {
                    description 'Specify action to rewrite packet service class'
                              + ' and transmit it'
                                ;
                    leaf service-class-value {
                      description 'Reset service class in violate-action'
                                  ;
                      type qos-service-class ;
                      mandatory true ;
                    }
                  }
                  ncd:revise-date 2020-05-18 ;
                }
              }
            }
          }
        }
        container unknowns {
          description 'Match unknown, only for VPLS'
                      ;
          list unknown {
            description 'Configure interface rate limit based on matching unkno'
                      + 'wn'
                        ;
            key 'if-name if-direct'
                ;
            leaf if-name {
              description 'Configure the name of the attaching interface'
                          ;
              type ncd:ifname {
                length 1..31 {
                  description 'Name of the attaching interface, support 1-31 ch'
                            + 'aracters'
                              ;
                }
              }
            }
            leaf if-direct {
              description 'Specify the direction of interface, as follows,'+"\n"
                        + '     input  Rate limit on input'+"\n"
                        + '     output Rate limit on output'
                          ;
              type enumeration {
                enum input {
                  value 1 ;
                  description 'Rate limit on input'
                              ;
                }
                enum output {
                  value 2 ;
                  description 'Rate limit on output'
                              ;
                }
              }
            }
            leaf rate-limit-desc {
              description 'Description of rate limit, support 1-79 characters.'
                          ;
              type ncd:string-with-blank {
                length 1..79 {
                  description 'Description of rate limit, support 1-79 characte'
                            + 'rs.'
                              ;
                }
              }
              ncd:revise-date 2020-06-18 ;
            }
            choice unit-style {
              description "Specify unit's style"
                          ;
              mandatory true ;
              case unit-value {
                description 'Configure the value style'
                            ;
                leaf cir {
                  description 'Configure the CIR(Committed Information Rate) va'
                            + 'lue (default: kilobits per second)'
                              ;
                  type uint32 {
                    range 8..4294967295 {
                      description 'The CIR value (default: kilobits per second)'
                                + ',support <8-4294967295>'
                                  ;
                    }
                  }
                  mandatory true ;
                }
                leaf cir-unit {
                  description 'set cir unit, such as kbps, mbps, gbps'
                              ;
                  type qos-rate-unit-type ;
                }
                leaf cbs {
                  description 'Configure the CBS(Committed Burst Size) size in '
                            + 'bytes.'
                              ;
                  type uint32 {
                    range 1..4294967295 {
                      description 'The CBS(Committed Burst Size) size in bytes,'
                                + ' support <1-4294967295>.'
                                  ;
                    }
                  }
                  units byte ;
                }
                leaf pir {
                  description 'Configure the PIR(Peak Information Rate) value ('
                            + 'default: kilobits per second)'
                              ;
                  type uint32 {
                    range 8..4294967295 {
                      description 'The PIR(Peak Information Rate) value (defaul'
                                + 't: kilobits per second), support <8-42949672'
                                + '95>'
                                  ;
                    }
                  }
                  mandatory true ;
                }
                leaf pir-unit {
                  description 'set pir unit, such as kbps, mbps, gbps'
                              ;
                  type qos-rate-unit-type ;
                }
                leaf pbs {
                  description 'Configure the PBS(Peak Burst Size) size in bytes.'
                              ;
                  type uint32 {
                    range 1..4294967295 {
                      description 'The PBS(Peak Burst Size) size in KB, support'
                                + ' <1-4294967295>'
                                  ;
                    }
                  }
                  units byte ;
                }
              }
              case unit-percentage {
                description 'Configure the percentage style'
                            ;
                leaf cir-percentage {
                  description 'Configure the CIR(Committed Information Rate) pe'
                            + 'rcentage (Set the accuracy rate per hundred (1%)'
                            + ')'
                              ;
                  type uint32 {
                    range 1..100 {
                      description 'The CIR percentage, support <1-100>'
                                  ;
                    }
                  }
                  mandatory true ;
                }
                leaf pir-percentage {
                  description 'Configure the PIR(Peak Information Rate) percent'
                            + 'age (Set the accuracy rate per hundred (1%))'
                              ;
                  type uint32 {
                    range 1..100 {
                      description 'The PIR percentage, support <1-100>'
                                  ;
                    }
                  }
                  mandatory true ;
                }
                ncd:revise-date 2020-12-23 ;
              }
            }
            leaf statistical-share {
              description 'The flag of statistical-share, as follows,'+"\n"
                        + '    ture  Statistical-share is configured'+"\n"
                        + '    false Statistical-share is not configured'
                          ;
              type boolean ;
              default false ;
            }
            leaf token-bucket-id {
              description 'Set token bucket id'
                          ;
              type uint32 {
                range 1..4294967295 {
                  description 'Token bucket id'
                              ;
                }
              }
              ncd:revise-date 2019-10-28 ;
            }
            container mode {
              if-feature qos-car-mode ;
              description 'Set color mode'
                          ;
              presence 'Configure mode information'
                       ;
              leaf mode-type {
                description 'Color mode type, as follows,'+"\n"
                          + '     blind   Color-Blind mode'+"\n"
                          + '     aware   Color-Aware mode'
                            ;
                type enumeration {
                  enum blind {
                    value 1 ;
                    description 'Color-Blind mode'
                                ;
                  }
                  enum aware {
                    value 2 ;
                    description 'Color-Aware mode'
                                ;
                  }
                }
                mandatory true ;
              }
            }
            container conform-action {
              description 'Action to packets that conform to the rate limit'
                          ;
              choice action {
                description 'Specify action to packets that conform to the rate'
                          + ' limit'
                            ;
                mandatory true ;
                case ca-drop {
                  description 'Drop packet in conform-action'
                              ;
                  leaf drop {
                    description 'Specify action to drop packet'
                                ;
                    type empty ;
                    mandatory true ;
                  }
                }
                case ca-transmit {
                  description 'Transmit packet in conform-action'
                              ;
                  leaf transmit {
                    description 'Specify action to transmit packet'
                                ;
                    type empty ;
                    mandatory true ;
                  }
                }
                case ca-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in conform-action, supp'
                                + 'ort <0-7>'
                                  ;
                      type uint8 {
                        range 0..7 {
                          description 'The MPLS-EXP value, support <0-7>'
                                      ;
                        }
                      }
                      mandatory true ;
                    }
                  }
                }
                case ca-precedence {
                  description 'Rewrite packet precedence and transmit the packet'
                              ;
                  container set-prec-transmit {
                    description 'Specify action to rewrite packet precedence an'
                              + 'd transmit it'
                                ;
                    leaf prec-value {
                      description 'Reset the IP-Precedence value in conform-act'
                                + 'ion, support <0-7>'
                                  ;
                      type uint8 {
                        range 0..7 {
                          description 'The IP-Precedence value, support <0-7>'
                                      ;
                        }
                      }
                      mandatory true ;
                    }
                  }
                }
                case ca-dscp {
                  description 'Rewrite packet DSCP and transmit the packet'
                              ;
                  container set-dscp-transmit {
                    description 'Specify action to rewrite packet DSCP and tran'
                              + 'smit it'
                                ;
                    leaf dscp-value {
                      description 'Reset DSCP in conform-action, support <0-63>'
                                  ;
                      type uint8 {
                        range 0..63 {
                          description 'The DSCP value, support <0-63>'
                                      ;
                        }
                      }
                      mandatory true ;
                    }
                  }
                }
                case ca-8021p {
                  description 'Rewrite packet 802.1p and transmit the packet'
                              ;
                  container set-8021p-transmit {
                    description 'Specify action to rewrite packet 802.1p and tr'
                              + 'ansmit it'
                                ;
                    leaf value-8021p {
                      description 'Reset 802.1p in conform-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ca-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ca-service-class {
                  description 'Rewrite packet service class and transmit the pa'
                            + 'cket'
                              ;
                  container set-service-class-transmit {
                    description 'Specify action to rewrite packet service class'
                              + ' and transmit it'
                                ;
                    leaf service-class-value {
                      description 'Reset service class in conform-action'
                                  ;
                      type qos-service-class ;
                      mandatory true ;
                    }
                  }
                  ncd:revise-date 2020-05-18 ;
                }
              }
            }
            container exceed-action {
              description 'Action to packets that exceed the rate limit'
                          ;
              choice action {
                description 'Specify action to packets that exceed the rate lim'
                          + 'it'
                            ;
                mandatory true ;
                case ea-drop {
                  description 'Drop packet in exceed-action'
                              ;
                  leaf drop {
                    description 'Specify action to drop packet'
                                ;
                    type empty ;
                    mandatory true ;
                  }
                }
                case ea-transmit {
                  description 'Transmit packet in exceed-action'
                              ;
                  leaf transmit {
                    description 'Specify action to transmit packet'
                                ;
                    type empty ;
                    mandatory true ;
                  }
                }
                case ea-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in exceed-action, suppo'
                                + 'rt <0-7>'
                                  ;
                      type uint8 {
                        range 0..7 {
                          description 'The MPLS-EXP value, support <0-7>'
                                      ;
                        }
                      }
                      mandatory true ;
                    }
                  }
                }
                case ea-precedence {
                  description 'Rewrite packet precedence and transmit the packet'
                              ;
                  container set-prec-transmit {
                    description 'Specify action to rewrite packet precedence an'
                              + 'd transmit it'
                                ;
                    leaf prec-value {
                      description 'Reset the IP-Precedence value in exceed-acti'
                                + 'on, support <0-7>'
                                  ;
                      type uint8 {
                        range 0..7 {
                          description 'The IP-Precedence value, support <0-7>'
                                      ;
                        }
                      }
                      mandatory true ;
                    }
                  }
                }
                case ea-dscp {
                  description 'Rewrite packet DSCP and transmit the packet'
                              ;
                  container set-dscp-transmit {
                    description 'Specify action to rewrite packet DSCP and tran'
                              + 'smit it'
                                ;
                    leaf dscp-value {
                      description 'Reset DSCP in exceed-action, support <0-63>'
                                  ;
                      type uint8 {
                        range 0..63 {
                          description 'The DSCP value, support <0-63>'
                                      ;
                        }
                      }
                      mandatory true ;
                    }
                  }
                }
                case ea-8021p {
                  description 'Rewrite packet 802.1p and transmit the packet'
                              ;
                  container set-8021p-transmit {
                    description 'Specify action to rewrite packet 802.1p and tr'
                              + 'ansmit it'
                                ;
                    leaf value-8021p {
                      description 'Reset 802.1p in exceed-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ea-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ea-service-class {
                  description 'Rewrite packet service class and transmit the pa'
                            + 'cket'
                              ;
                  container set-service-class-transmit {
                    description 'Specify action to rewrite packet service class'
                              + ' and transmit it'
                                ;
                    leaf service-class-value {
                      description 'Reset service class in exceed-action'
                                  ;
                      type qos-service-class ;
                      mandatory true ;
                    }
                  }
                  ncd:revise-date 2020-05-18 ;
                }
              }
            }
            container violate-action {
              description 'Action to packets that violate the rate limit'
                          ;
              choice action {
                description 'Specify action to packets that violate the rate li'
                          + 'mit'
                            ;
                mandatory true ;
                case va-drop {
                  description 'Drop packet in violate-action'
                              ;
                  leaf drop {
                    description 'Specify action to drop packet'
                                ;
                    type empty ;
                    mandatory true ;
                  }
                }
                case va-transmit {
                  description 'Transmit packet in violate-action'
                              ;
                  leaf transmit {
                    description 'Specify action to transmit packet'
                                ;
                    type empty ;
                    mandatory true ;
                  }
                }
                case va-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in violate-action, supp'
                                + 'ort <0-7>'
                                  ;
                      type uint8 {
                        range 0..7 {
                          description 'The MPLS-EXP value, support <0-7>'
                                      ;
                        }
                      }
                      mandatory true ;
                    }
                  }
                }
                case va-precedence {
                  description 'Rewrite packet precedence and transmit the packet'
                              ;
                  container set-prec-transmit {
                    description 'Specify action to rewrite packet precedence an'
                              + 'd transmit it'
                                ;
                    leaf prec-value {
                      description 'Reset the IP-Precedence value in violate-act'
                                + 'ion, support <0-7>'
                                  ;
                      type uint8 {
                        range 0..7 ;
                      }
                      mandatory true ;
                    }
                  }
                }
                case va-dscp {
                  description 'Rewrite packet DSCP and transmit the packet'
                              ;
                  container set-dscp-transmit {
                    description 'Specify action to rewrite packet DSCP and tran'
                              + 'smit it'
                                ;
                    leaf dscp-value {
                      description 'Reset DSCP in violate-action, support <0-63>'
                                  ;
                      type uint8 {
                        range 0..63 {
                          description 'The DSCP value, support <0-63>'
                                      ;
                        }
                      }
                      mandatory true ;
                    }
                  }
                }
                case va-8021p {
                  description 'Rewrite packet 802.1p and transmit the packet'
                              ;
                  container set-8021p-transmit {
                    description 'Specify action to rewrite packet 802.1p and tr'
                              + 'ansmit it'
                                ;
                    leaf value-8021p {
                      description 'Reset 802.1p in violate-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case va-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case va-service-class {
                  description 'Rewrite packet service class and transmit the pa'
                            + 'cket'
                              ;
                  container set-service-class-transmit {
                    description 'Specify action to rewrite packet service class'
                              + ' and transmit it'
                                ;
                    leaf service-class-value {
                      description 'Reset service class in violate-action'
                                  ;
                      type qos-service-class ;
                      mandatory true ;
                    }
                  }
                  ncd:revise-date 2020-05-18 ;
                }
              }
            }
          }
        }
        container localports {
          description 'Match local port'
                      ;
          list localport {
            description 'Configure interface rate limit based on matching local'
                      + 'port'
                        ;
            key 'if-name if-direct'
                ;
            leaf if-name {
              description 'Configure the name of the attaching interface'
                          ;
              type ncd:ifname {
                length 1..31 {
                  description 'Name of the attaching interface, support 1-31 ch'
                            + 'aracters'
                              ;
                }
              }
            }
            leaf if-direct {
              description 'Specify the direction of interface, as follows,'+"\n"
                        + '     input  Rate limit on input'+"\n"
                        + '     output Rate limit on output'
                          ;
              type enumeration {
                enum input {
                  value 1 ;
                  description 'Rate limit on input'
                              ;
                }
                enum output {
                  value 2 ;
                  description 'Rate limit on output'
                              ;
                }
              }
            }
            leaf rate-limit-desc {
              description 'Description of rate limit, support 1-79 characters.'
                          ;
              type ncd:string-with-blank {
                length 1..79 {
                  description 'Description of rate limit, support 1-79 characte'
                            + 'rs.'
                              ;
                }
              }
              ncd:revise-date 2020-06-18 ;
            }
            choice unit-style {
              description "Specify unit's style"
                          ;
              mandatory true ;
              case unit-value {
                description 'Configure the value style'
                            ;
                leaf cir {
                  description 'Configure the CIR(Committed Information Rate) va'
                            + 'lue (default: kilobits per second)'
                              ;
                  type uint32 {
                    range 8..4294967295 {
                      description 'The CIR value (default: kilobits per second)'
                                + ',support <8-4294967295>'
                                  ;
                    }
                  }
                  mandatory true ;
                }
                leaf cir-unit {
                  description 'set cir unit, such as kbps, mbps, gbps'
                              ;
                  type qos-rate-unit-type ;
                }
                leaf cbs {
                  description 'Configure the CBS(Committed Burst Size) size in '
                            + 'bytes.'
                              ;
                  type uint32 {
                    range 1..4294967295 {
                      description 'The CBS(Committed Burst Size) size in bytes,'
                                + ' support <1-4294967295>.'
                                  ;
                    }
                  }
                  units byte ;
                }
                leaf pir {
                  description 'Configure the PIR(Peak Information Rate) value ('
                            + 'default: kilobits per second)'
                              ;
                  type uint32 {
                    range 8..4294967295 {
                      description 'The PIR(Peak Information Rate) value (defaul'
                                + 't: kilobits per second), support <8-42949672'
                                + '95>'
                                  ;
                    }
                  }
                  mandatory true ;
                }
                leaf pir-unit {
                  description 'set pir unit, such as kbps, mbps, gbps'
                              ;
                  type qos-rate-unit-type ;
                }
                leaf pbs {
                  description 'Configure the PBS(Peak Burst Size) size in bytes.'
                              ;
                  type uint32 {
                    range 1..4294967295 {
                      description 'The PBS(Peak Burst Size) size in KB, support'
                                + ' <1-4294967295>'
                                  ;
                    }
                  }
                  units byte ;
                }
              }
              case unit-percentage {
                description 'Configure the percentage style'
                            ;
                leaf cir-percentage {
                  description 'Configure the CIR(Committed Information Rate) pe'
                            + 'rcentage (Set the accuracy rate per hundred (1%)'
                            + ')'
                              ;
                  type uint32 {
                    range 1..100 {
                      description 'The CIR percentage, support <1-100>'
                                  ;
                    }
                  }
                  mandatory true ;
                }
                leaf pir-percentage {
                  description 'Configure the PIR(Peak Information Rate) percent'
                            + 'age (Set the accuracy rate per hundred (1%))'
                              ;
                  type uint32 {
                    range 1..100 {
                      description 'The PIR percentage, support <1-100>'
                                  ;
                    }
                  }
                  mandatory true ;
                }
                ncd:revise-date 2020-12-23 ;
              }
            }
            choice buket-value-percent {
              if-feature car-buket-value-percent ;
              description 'Configure CIR, CBS, PIR and PBS.'
                          ;
              mandatory true ;
              case buket-value {
                description 'Configure CIR, CBS, PIR and PBS in numerical form.'
                            ;
                container c-buket {
                  description 'Configure C-buket related parameters.'
                              ;
                  container cir-value {
                    description 'Configure the CIR(Committed Information Rate).'
                                ;
                    leaf cir {
                      description 'Configure the CIR(Committed Information Rate'
                                + ') value (default: kilobits per second)'
                                  ;
                      type uint32 {
                        range 8..4294967295 {
                          description 'The CIR value (default: kilobits per sec'
                                    + 'ond),support <8-4294967295>'
                                      ;
                        }
                      }
                      mandatory true ;
                    }
                    leaf cir-unit {
                      description 'set cir unit, such as kbps, mbps, gbps, pps.'
                                  ;
                      type qos-rate-unit-type-ex ;
                    }
                  }
                  container cbs-value {
                    description 'Configure the CBS(Committed Burst Size).'
                                ;
                    presence cbs ;
                    leaf cbs {
                      description 'Configure the CBS(Committed Burst Size) valu'
                                + 'e in bytes.'
                                  ;
                      type uint32 {
                        range 1..4294967295 {
                          description 'The CBS(Committed Burst Size) size in by'
                                    + 'tes, support <1-4294967295>'
                                      ;
                        }
                      }
                      units byte ;
                      mandatory true ;
                    }
                  }
                }
                container p-buket {
                  description 'Configure P-buket related parameters.'
                              ;
                  presence p-buket ;
                  container pir-value {
                    description 'Configure the PIR(Peak Information Rate).'
                                ;
                    leaf pir {
                      description 'Configure the PIR(Peak Information Rate) val'
                                + 'ue (default: kilobits per second)'
                                  ;
                      type uint32 {
                        range 8..4294967295 {
                          description 'The PIR(Peak Information Rate) value (de'
                                    + 'fault: kilobits per second), support <8-'
                                    + '4294967295>'
                                      ;
                        }
                      }
                      mandatory true ;
                    }
                    leaf pir-unit {
                      description 'set pir unit, such as kbps, mbps, gbps, pps'
                                  ;
                      type qos-rate-unit-type-ex ;
                    }
                  }
                  container pbs-value {
                    description 'Configure the PBS(Peak Burst Size).'
                                ;
                    presence pbs ;
                    leaf pbs {
                      description 'Configure the PBS(Peak Burst Size) value in '
                                + 'bytes.'
                                  ;
                      type uint32 {
                        range 1..4294967295 {
                          description 'The PBS(Peak Burst Size) size in bytes, '
                                    + 'support <1-4294967295>'
                                      ;
                        }
                      }
                      units byte ;
                      mandatory true ;
                    }
                  }
                }
              }
              case buket-percent {
                description 'Configure CIR and PIR in percentage.'
                            ;
                container cir-percent {
                  description 'Configure CIR in percentage.'
                              ;
                  leaf cir-percent {
                    description 'Configure CIR in percentage.'
                                ;
                    type uint32 {
                      range 1..100 ;
                    }
                    mandatory true ;
                  }
                }
                container pir-percent {
                  description 'Configure PIR in percentage.'
                              ;
                  presence pir ;
                  leaf pir-percent {
                    description 'Configure PIR in percentage.'
                                ;
                    type uint32 {
                      range 1..100 ;
                    }
                    mandatory true ;
                  }
                }
              }
              ncd:revise-date 2021-01-25 ;
            }
            leaf statistical-share {
              description 'The flag of statistical-share, as follows,'+"\n"
                        + '    ture  Statistical-share is configured'+"\n"
                        + '    false Statistical-share is not configured'
                          ;
              type boolean ;
              default false ;
            }
            leaf token-bucket-id {
              description 'Set token bucket id'
                          ;
              type uint32 {
                range 1..4294967295 {
                  description 'Token bucket id'
                              ;
                }
              }
              ncd:revise-date 2019-10-28 ;
            }
            container mode {
              if-feature qos-car-mode ;
              description 'Set color mode'
                          ;
              presence 'Configure mode information'
                       ;
              leaf mode-type {
                description 'Color mode type, as follows,'+"\n"
                          + '     blind   Color-Blind mode'+"\n"
                          + '     aware   Color-Aware mode'
                            ;
                type enumeration {
                  enum blind {
                    value 1 ;
                    description 'Color-Blind mode'
                                ;
                  }
                  enum aware {
                    value 2 ;
                    description 'Color-Aware mode'
                                ;
                  }
                }
                mandatory true ;
              }
            }
            container conform-action {
              description 'Action to packets that conform to the rate limit'
                          ;
              choice action {
                description 'Specify action to packets that conform to the rate'
                          + ' limit'
                            ;
                mandatory true ;
                case ca-drop {
                  description 'Drop packet in conform-action'
                              ;
                  leaf drop {
                    description 'Specify action to drop packet'
                                ;
                    type empty ;
                    mandatory true ;
                  }
                }
                case ca-transmit {
                  description 'Transmit packet in conform-action'
                              ;
                  leaf transmit {
                    description 'Specify action to transmit packet'
                                ;
                    type empty ;
                    mandatory true ;
                  }
                }
                case ca-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in conform-action, supp'
                                + 'ort <0-7>'
                                  ;
                      type uint8 {
                        range 0..7 {
                          description 'The MPLS-EXP value, support <0-7>'
                                      ;
                        }
                      }
                      mandatory true ;
                    }
                  }
                }
                case ca-precedence {
                  description 'Rewrite packet precedence and transmit the packet'
                              ;
                  container set-prec-transmit {
                    description 'Specify action to rewrite packet precedence an'
                              + 'd transmit it'
                                ;
                    leaf prec-value {
                      description 'Reset the IP-Precedence value in conform-act'
                                + 'ion, support <0-7>'
                                  ;
                      type uint8 {
                        range 0..7 {
                          description 'The IP-Precedence value, support <0-7>'
                                      ;
                        }
                      }
                      mandatory true ;
                    }
                  }
                }
                case ca-dscp {
                  description 'Rewrite packet DSCP and transmit the packet'
                              ;
                  container set-dscp-transmit {
                    description 'Specify action to rewrite packet DSCP and tran'
                              + 'smit it'
                                ;
                    leaf dscp-value {
                      description 'Reset DSCP in conform-action, support <0-63>'
                                  ;
                      type uint8 {
                        range 0..63 {
                          description 'The DSCP value, support <0-63>'
                                      ;
                        }
                      }
                      mandatory true ;
                    }
                  }
                }
                case ca-8021p {
                  description 'Rewrite packet 802.1p and transmit the packet'
                              ;
                  container set-8021p-transmit {
                    description 'Specify action to rewrite packet 802.1p and tr'
                              + 'ansmit it'
                                ;
                    leaf value-8021p {
                      description 'Reset 802.1p in conform-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ca-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ca-service-class {
                  description 'Rewrite packet service class and transmit the pa'
                            + 'cket'
                              ;
                  container set-service-class-transmit {
                    description 'Specify action to rewrite packet service class'
                              + ' and transmit it'
                                ;
                    leaf service-class-value {
                      description 'Reset service class in conform-action'
                                  ;
                      type qos-service-class ;
                      mandatory true ;
                    }
                  }
                  ncd:revise-date 2020-05-18 ;
                }
              }
            }
            container exceed-action {
              description 'Action to packets that exceed the rate limit'
                          ;
              choice action {
                description 'Specify action to packets that exceed the rate lim'
                          + 'it'
                            ;
                mandatory true ;
                case ea-drop {
                  description 'Drop packet in exceed-action'
                              ;
                  leaf drop {
                    description 'Specify action to drop packet'
                                ;
                    type empty ;
                    mandatory true ;
                  }
                }
                case ea-transmit {
                  description 'Transmit packet in exceed-action'
                              ;
                  leaf transmit {
                    description 'Specify action to transmit packet'
                                ;
                    type empty ;
                    mandatory true ;
                  }
                }
                case ea-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in exceed-action, suppo'
                                + 'rt <0-7>'
                                  ;
                      type uint8 {
                        range 0..7 {
                          description 'The MPLS-EXP value, support <0-7>'
                                      ;
                        }
                      }
                      mandatory true ;
                    }
                  }
                }
                case ea-precedence {
                  description 'Rewrite packet precedence and transmit the packet'
                              ;
                  container set-prec-transmit {
                    description 'Specify action to rewrite packet precedence an'
                              + 'd transmit it'
                                ;
                    leaf prec-value {
                      description 'Reset the IP-Precedence value in exceed-acti'
                                + 'on, support <0-7>'
                                  ;
                      type uint8 {
                        range 0..7 {
                          description 'The IP-Precedence value, support <0-7>'
                                      ;
                        }
                      }
                      mandatory true ;
                    }
                  }
                }
                case ea-dscp {
                  description 'Rewrite packet DSCP and transmit the packet'
                              ;
                  container set-dscp-transmit {
                    description 'Specify action to rewrite packet DSCP and tran'
                              + 'smit it'
                                ;
                    leaf dscp-value {
                      description 'Reset DSCP in exceed-action, support <0-63>'
                                  ;
                      type uint8 {
                        range 0..63 {
                          description 'The DSCP value, support <0-63>'
                                      ;
                        }
                      }
                      mandatory true ;
                    }
                  }
                }
                case ea-8021p {
                  description 'Rewrite packet 802.1p and transmit the packet'
                              ;
                  container set-8021p-transmit {
                    description 'Specify action to rewrite packet 802.1p and tr'
                              + 'ansmit it'
                                ;
                    leaf value-8021p {
                      description 'Reset 802.1p in exceed-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ea-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ea-service-class {
                  description 'Rewrite packet service class and transmit the pa'
                            + 'cket'
                              ;
                  container set-service-class-transmit {
                    description 'Specify action to rewrite packet service class'
                              + ' and transmit it'
                                ;
                    leaf service-class-value {
                      description 'Reset service class in exceed-action'
                                  ;
                      type qos-service-class ;
                      mandatory true ;
                    }
                  }
                  ncd:revise-date 2020-05-18 ;
                }
              }
            }
            container violate-action {
              description 'Action to packets that violate the rate limit'
                          ;
              choice action {
                description 'Specify action to packets that violate the rate li'
                          + 'mit'
                            ;
                mandatory true ;
                case va-drop {
                  description 'Drop packet in violate-action'
                              ;
                  leaf drop {
                    description 'Specify action to drop packet'
                                ;
                    type empty ;
                    mandatory true ;
                  }
                }
                case va-transmit {
                  description 'Transmit packet in violate-action'
                              ;
                  leaf transmit {
                    description 'Specify action to transmit packet'
                                ;
                    type empty ;
                    mandatory true ;
                  }
                }
                case va-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in violate-action, supp'
                                + 'ort <0-7>'
                                  ;
                      type uint8 {
                        range 0..7 {
                          description 'The MPLS-EXP value, support <0-7>'
                                      ;
                        }
                      }
                      mandatory true ;
                    }
                  }
                }
                case va-precedence {
                  description 'Rewrite packet precedence and transmit the packet'
                              ;
                  container set-prec-transmit {
                    description 'Specify action to rewrite packet precedence an'
                              + 'd transmit it'
                                ;
                    leaf prec-value {
                      description 'Reset the IP-Precedence value in violate-act'
                                + 'ion, support <0-7>'
                                  ;
                      type uint8 {
                        range 0..7 ;
                      }
                      mandatory true ;
                    }
                  }
                }
                case va-dscp {
                  description 'Rewrite packet DSCP and transmit the packet'
                              ;
                  container set-dscp-transmit {
                    description 'Specify action to rewrite packet DSCP and tran'
                              + 'smit it'
                                ;
                    leaf dscp-value {
                      description 'Reset DSCP in violate-action, support <0-63>'
                                  ;
                      type uint8 {
                        range 0..63 {
                          description 'The DSCP value, support <0-63>'
                                      ;
                        }
                      }
                      mandatory true ;
                    }
                  }
                }
                case va-8021p {
                  description 'Rewrite packet 802.1p and transmit the packet'
                              ;
                  container set-8021p-transmit {
                    description 'Specify action to rewrite packet 802.1p and tr'
                              + 'ansmit it'
                                ;
                    leaf value-8021p {
                      description 'Reset 802.1p in violate-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case va-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case va-service-class {
                  description 'Rewrite packet service class and transmit the pa'
                            + 'cket'
                              ;
                  container set-service-class-transmit {
                    description 'Specify action to rewrite packet service class'
                              + ' and transmit it'
                                ;
                    leaf service-class-value {
                      description 'Reset service class in violate-action'
                                  ;
                      type qos-service-class ;
                      mandatory true ;
                    }
                  }
                  ncd:revise-date 2020-05-18 ;
                }
              }
            }
          }
        }
        container dscps {
          description 'Match DSCP'
                      ;
          list dscp {
            description 'Configure interface rate limit based on matching dscp'
                        ;
            key 'if-name if-direct ip-protocol dscp-value'
                ;
            leaf if-name {
              description 'Configure the name of the attaching interface'
                          ;
              type ncd:ifname {
                length 1..31 {
                  description 'Name of the attaching interface, support 1-31 ch'
                            + 'aracters'
                              ;
                }
              }
            }
            leaf if-direct {
              description 'Specify the direction of interface, as follows,'+"\n"
                        + '     input  Rate limit on input'+"\n"
                        + '     output Rate limit on output'
                          ;
              type enumeration {
                enum input {
                  value 1 ;
                  description 'Rate limit on input'
                              ;
                }
                enum output {
                  value 2 ;
                  description 'Rate limit on output'
                              ;
                }
              }
            }
            leaf ip-protocol {
              description 'Rate limit based on protocol, as follows,'+"\n"
                        + '    any  Rate limit based on any protocol'+"\n"
                        + '    ipv4 Rate limit based on IPv4 protocol'+"\n"
                        + '    ipv6 Rate limit based on IPv6 protocol'
                          ;
              type enumeration {
                enum any {
                  value 1 ;
                  description 'Rate limit based on any protocol'
                              ;
                }
                enum ipv4 {
                  value 2 ;
                  description 'Rate limit based on IPv4'
                              ;
                }
                enum ipv6 {
                  value 3 ;
                  description 'Rate limit based on IPv6'
                              ;
                }
              }
            }
            leaf dscp-value {
              description 'DSCP value, support <0-63>'
                          ;
              type uint32 {
                range 0..63 {
                  description 'DSCP value, support <0-63>'
                              ;
                }
              }
            }
            leaf rate-limit-desc {
              description 'Description of rate limit, support 1-79 characters.'
                          ;
              type ncd:string-with-blank {
                length 1..79 {
                  description 'Description of rate limit, support 1-79 characte'
                            + 'rs.'
                              ;
                }
              }
              ncd:revise-date 2020-06-18 ;
            }
            choice unit-style {
              description "Specify unit's style"
                          ;
              mandatory true ;
              case unit-value {
                description 'Configure the value style'
                            ;
                leaf cir {
                  description 'Configure the CIR(Committed Information Rate) va'
                            + 'lue (default: kilobits per second)'
                              ;
                  type uint32 {
                    range 8..4294967295 {
                      description 'The CIR value (default: kilobits per second)'
                                + ',support <8-4294967295>'
                                  ;
                    }
                  }
                  mandatory true ;
                }
                leaf cir-unit {
                  description 'set cir unit, such as kbps, mbps, gbps'
                              ;
                  type qos-rate-unit-type ;
                }
                leaf cbs {
                  description 'Configure the CBS(Committed Burst Size) size in '
                            + 'bytes.'
                              ;
                  type uint32 {
                    range 1..4294967295 {
                      description 'The CBS(Committed Burst Size) size in bytes,'
                                + ' support <1-4294967295>.'
                                  ;
                    }
                  }
                  units byte ;
                }
                leaf pir {
                  description 'Configure the PIR(Peak Information Rate) value ('
                            + 'default: kilobits per second)'
                              ;
                  type uint32 {
                    range 8..4294967295 {
                      description 'The PIR(Peak Information Rate) value (defaul'
                                + 't: kilobits per second), support <8-42949672'
                                + '95>'
                                  ;
                    }
                  }
                  mandatory true ;
                }
                leaf pir-unit {
                  description 'set pir unit, such as kbps, mbps, gbps'
                              ;
                  type qos-rate-unit-type ;
                }
                leaf pbs {
                  description 'Configure the PBS(Peak Burst Size) size in bytes.'
                              ;
                  type uint32 {
                    range 1..4294967295 {
                      description 'The PBS(Peak Burst Size) size in KB, support'
                                + ' <1-4294967295>'
                                  ;
                    }
                  }
                  units byte ;
                }
              }
              case unit-percentage {
                description 'Configure the percentage style'
                            ;
                leaf cir-percentage {
                  description 'Configure the CIR(Committed Information Rate) pe'
                            + 'rcentage (Set the accuracy rate per hundred (1%)'
                            + ')'
                              ;
                  type uint32 {
                    range 1..100 {
                      description 'The CIR percentage, support <1-100>'
                                  ;
                    }
                  }
                  mandatory true ;
                }
                leaf pir-percentage {
                  description 'Configure the PIR(Peak Information Rate) percent'
                            + 'age (Set the accuracy rate per hundred (1%))'
                              ;
                  type uint32 {
                    range 1..100 {
                      description 'The PIR percentage, support <1-100>'
                                  ;
                    }
                  }
                  mandatory true ;
                }
                ncd:revise-date 2020-12-23 ;
              }
            }
            leaf statistical-share {
              description 'The flag of statistical-share, as follows,'+"\n"
                        + '    ture  Statistical-share is configured'+"\n"
                        + '    false Statistical-share is not configured'
                          ;
              type boolean ;
              default false ;
            }
            leaf token-bucket-id {
              description 'Set token bucket id'
                          ;
              type uint32 {
                range 1..4294967295 {
                  description 'Token bucket id'
                              ;
                }
              }
              ncd:revise-date 2019-10-28 ;
            }
            container mode {
              if-feature qos-car-mode ;
              description 'Set color mode'
                          ;
              presence 'Configure mode information'
                       ;
              leaf mode-type {
                description 'Color mode type, as follows,'+"\n"
                          + '     blind   Color-Blind mode'+"\n"
                          + '     aware   Color-Aware mode'
                            ;
                type enumeration {
                  enum blind {
                    value 1 ;
                    description 'Color-Blind mode'
                                ;
                  }
                  enum aware {
                    value 2 ;
                    description 'Color-Aware mode'
                                ;
                  }
                }
                mandatory true ;
              }
            }
            container conform-action {
              description 'Action to packets that conform to the rate limit'
                          ;
              choice action {
                description 'Specify action to packets that conform to the rate'
                          + ' limit'
                            ;
                mandatory true ;
                case ca-drop {
                  description 'Drop packet in conform-action'
                              ;
                  leaf drop {
                    description 'Specify action to drop packet'
                                ;
                    type empty ;
                    mandatory true ;
                  }
                }
                case ca-transmit {
                  description 'Transmit packet in conform-action'
                              ;
                  leaf transmit {
                    description 'Specify action to transmit packet'
                                ;
                    type empty ;
                    mandatory true ;
                  }
                }
                case ca-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in conform-action, supp'
                                + 'ort <0-7>'
                                  ;
                      type uint8 {
                        range 0..7 {
                          description 'The MPLS-EXP value, support <0-7>'
                                      ;
                        }
                      }
                      mandatory true ;
                    }
                  }
                }
                case ca-precedence {
                  description 'Rewrite packet precedence and transmit the packet'
                              ;
                  container set-prec-transmit {
                    description 'Specify action to rewrite packet precedence an'
                              + 'd transmit it'
                                ;
                    leaf prec-value {
                      description 'Reset the IP-Precedence value in conform-act'
                                + 'ion, support <0-7>'
                                  ;
                      type uint8 {
                        range 0..7 {
                          description 'The IP-Precedence value, support <0-7>'
                                      ;
                        }
                      }
                      mandatory true ;
                    }
                  }
                }
                case ca-dscp {
                  description 'Rewrite packet DSCP and transmit the packet'
                              ;
                  container set-dscp-transmit {
                    description 'Specify action to rewrite packet DSCP and tran'
                              + 'smit it'
                                ;
                    leaf dscp-value {
                      description 'Reset DSCP in conform-action, support <0-63>'
                                  ;
                      type uint8 {
                        range 0..63 {
                          description 'The DSCP value, support <0-63>'
                                      ;
                        }
                      }
                      mandatory true ;
                    }
                  }
                }
                case ca-8021p {
                  description 'Rewrite packet 802.1p and transmit the packet'
                              ;
                  container set-8021p-transmit {
                    description 'Specify action to rewrite packet 802.1p and tr'
                              + 'ansmit it'
                                ;
                    leaf value-8021p {
                      description 'Reset 802.1p in conform-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ca-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ca-service-class {
                  description 'Rewrite packet service class and transmit the pa'
                            + 'cket'
                              ;
                  container set-service-class-transmit {
                    description 'Specify action to rewrite packet service class'
                              + ' and transmit it'
                                ;
                    leaf service-class-value {
                      description 'Reset service class in conform-action'
                                  ;
                      type qos-service-class ;
                      mandatory true ;
                    }
                  }
                  ncd:revise-date 2020-05-18 ;
                }
              }
            }
            container exceed-action {
              description 'Action to packets that exceed the rate limit'
                          ;
              choice action {
                description 'Specify action to packets that exceed the rate lim'
                          + 'it'
                            ;
                mandatory true ;
                case ea-drop {
                  description 'Drop packet in exceed-action'
                              ;
                  leaf drop {
                    description 'Specify action to drop packet'
                                ;
                    type empty ;
                    mandatory true ;
                  }
                }
                case ea-transmit {
                  description 'Transmit packet in exceed-action'
                              ;
                  leaf transmit {
                    description 'Specify action to transmit packet'
                                ;
                    type empty ;
                    mandatory true ;
                  }
                }
                case ea-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in exceed-action, suppo'
                                + 'rt <0-7>'
                                  ;
                      type uint8 {
                        range 0..7 {
                          description 'The MPLS-EXP value, support <0-7>'
                                      ;
                        }
                      }
                      mandatory true ;
                    }
                  }
                }
                case ea-precedence {
                  description 'Rewrite packet precedence and transmit the packet'
                              ;
                  container set-prec-transmit {
                    description 'Specify action to rewrite packet precedence an'
                              + 'd transmit it'
                                ;
                    leaf prec-value {
                      description 'Reset the IP-Precedence value in exceed-acti'
                                + 'on, support <0-7>'
                                  ;
                      type uint8 {
                        range 0..7 {
                          description 'The IP-Precedence value, support <0-7>'
                                      ;
                        }
                      }
                      mandatory true ;
                    }
                  }
                }
                case ea-dscp {
                  description 'Rewrite packet DSCP and transmit the packet'
                              ;
                  container set-dscp-transmit {
                    description 'Specify action to rewrite packet DSCP and tran'
                              + 'smit it'
                                ;
                    leaf dscp-value {
                      description 'Reset DSCP in exceed-action, support <0-63>'
                                  ;
                      type uint8 {
                        range 0..63 {
                          description 'The DSCP value, support <0-63>'
                                      ;
                        }
                      }
                      mandatory true ;
                    }
                  }
                }
                case ea-8021p {
                  description 'Rewrite packet 802.1p and transmit the packet'
                              ;
                  container set-8021p-transmit {
                    description 'Specify action to rewrite packet 802.1p and tr'
                              + 'ansmit it'
                                ;
                    leaf value-8021p {
                      description 'Reset 802.1p in exceed-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ea-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ea-service-class {
                  description 'Rewrite packet service class and transmit the pa'
                            + 'cket'
                              ;
                  container set-service-class-transmit {
                    description 'Specify action to rewrite packet service class'
                              + ' and transmit it'
                                ;
                    leaf service-class-value {
                      description 'Reset service class in exceed-action'
                                  ;
                      type qos-service-class ;
                      mandatory true ;
                    }
                  }
                  ncd:revise-date 2020-05-18 ;
                }
              }
            }
            container violate-action {
              description 'Action to packets that violate the rate limit'
                          ;
              choice action {
                description 'Specify action to packets that violate the rate li'
                          + 'mit'
                            ;
                mandatory true ;
                case va-drop {
                  description 'Drop packet in violate-action'
                              ;
                  leaf drop {
                    description 'Specify action to drop packet'
                                ;
                    type empty ;
                    mandatory true ;
                  }
                }
                case va-transmit {
                  description 'Transmit packet in violate-action'
                              ;
                  leaf transmit {
                    description 'Specify action to transmit packet'
                                ;
                    type empty ;
                    mandatory true ;
                  }
                }
                case va-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in violate-action, supp'
                                + 'ort <0-7>'
                                  ;
                      type uint8 {
                        range 0..7 {
                          description 'The MPLS-EXP value, support <0-7>'
                                      ;
                        }
                      }
                      mandatory true ;
                    }
                  }
                }
                case va-precedence {
                  description 'Rewrite packet precedence and transmit the packet'
                              ;
                  container set-prec-transmit {
                    description 'Specify action to rewrite packet precedence an'
                              + 'd transmit it'
                                ;
                    leaf prec-value {
                      description 'Reset the IP-Precedence value in violate-act'
                                + 'ion, support <0-7>'
                                  ;
                      type uint8 {
                        range 0..7 ;
                      }
                      mandatory true ;
                    }
                  }
                }
                case va-dscp {
                  description 'Rewrite packet DSCP and transmit the packet'
                              ;
                  container set-dscp-transmit {
                    description 'Specify action to rewrite packet DSCP and tran'
                              + 'smit it'
                                ;
                    leaf dscp-value {
                      description 'Reset DSCP in violate-action, support <0-63>'
                                  ;
                      type uint8 {
                        range 0..63 {
                          description 'The DSCP value, support <0-63>'
                                      ;
                        }
                      }
                      mandatory true ;
                    }
                  }
                }
                case va-8021p {
                  description 'Rewrite packet 802.1p and transmit the packet'
                              ;
                  container set-8021p-transmit {
                    description 'Specify action to rewrite packet 802.1p and tr'
                              + 'ansmit it'
                                ;
                    leaf value-8021p {
                      description 'Reset 802.1p in violate-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case va-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case va-service-class {
                  description 'Rewrite packet service class and transmit the pa'
                            + 'cket'
                              ;
                  container set-service-class-transmit {
                    description 'Specify action to rewrite packet service class'
                              + ' and transmit it'
                                ;
                    leaf service-class-value {
                      description 'Reset service class in violate-action'
                                  ;
                      type qos-service-class ;
                      mandatory true ;
                    }
                  }
                  ncd:revise-date 2020-05-18 ;
                }
              }
            }
          }
        }
        container precedences {
          description 'Match IP precedence'
                      ;
          list precedence {
            description 'Configure interface rate limit based on matching prece'
                      + 'dence'
                        ;
            key 'if-name if-direct ip-protocol prec-value'
                ;
            leaf if-name {
              description 'Configure the name of the attaching interface'
                          ;
              type ncd:ifname {
                length 1..31 {
                  description 'Name of the attaching interface, support 1-31 ch'
                            + 'aracters'
                              ;
                }
              }
            }
            leaf if-direct {
              description 'Specify the direction of interface, as follows,'+"\n"
                        + '     input  Rate limit on input'+"\n"
                        + '     output Rate limit on output'
                          ;
              type enumeration {
                enum input {
                  value 1 ;
                  description 'Rate limit on input'
                              ;
                }
                enum output {
                  value 2 ;
                  description 'Rate limit on output'
                              ;
                }
              }
            }
            leaf ip-protocol {
              description 'Rate limit based on protocol, as follows,'+"\n"
                        + '    any  Rate limit based on any protocol'+"\n"
                        + '    ipv4 Rate limit based on IPv4 protocol'+"\n"
                        + '    ipv6 Rate limit based on IPv6 protocol'
                          ;
              type enumeration {
                enum any {
                  value 1 ;
                  description 'Rate limit based on any protocol'
                              ;
                }
                enum ipv4 {
                  value 2 ;
                  description 'Rate limit based on IPv4'
                              ;
                }
                enum ipv6 {
                  value 3 ;
                  description 'Rate limit based on IPv6'
                              ;
                }
              }
            }
            leaf prec-value {
              description 'IP precedence value, support <0-7>'
                          ;
              type uint32 {
                range 0..7 {
                  description 'IP precedence value, support <0-7>'
                              ;
                }
              }
            }
            leaf rate-limit-desc {
              description 'Description of rate limit, support 1-79 characters.'
                          ;
              type ncd:string-with-blank {
                length 1..79 {
                  description 'Description of rate limit, support 1-79 characte'
                            + 'rs.'
                              ;
                }
              }
              ncd:revise-date 2020-06-18 ;
            }
            choice unit-style {
              description "Specify unit's style"
                          ;
              mandatory true ;
              case unit-value {
                description 'Configure the value style'
                            ;
                leaf cir {
                  description 'Configure the CIR(Committed Information Rate) va'
                            + 'lue (default: kilobits per second)'
                              ;
                  type uint32 {
                    range 8..4294967295 {
                      description 'The CIR value (default: kilobits per second)'
                                + ',support <8-4294967295>'
                                  ;
                    }
                  }
                  mandatory true ;
                }
                leaf cir-unit {
                  description 'set cir unit, such as kbps, mbps, gbps'
                              ;
                  type qos-rate-unit-type ;
                }
                leaf cbs {
                  description 'Configure the CBS(Committed Burst Size) size in '
                            + 'bytes.'
                              ;
                  type uint32 {
                    range 1..4294967295 {
                      description 'The CBS(Committed Burst Size) size in bytes,'
                                + ' support <1-4294967295>.'
                                  ;
                    }
                  }
                  units byte ;
                }
                leaf pir {
                  description 'Configure the PIR(Peak Information Rate) value ('
                            + 'default: kilobits per second)'
                              ;
                  type uint32 {
                    range 8..4294967295 {
                      description 'The PIR(Peak Information Rate) value (defaul'
                                + 't: kilobits per second), support <8-42949672'
                                + '95>'
                                  ;
                    }
                  }
                  mandatory true ;
                }
                leaf pir-unit {
                  description 'set pir unit, such as kbps, mbps, gbps'
                              ;
                  type qos-rate-unit-type ;
                }
                leaf pbs {
                  description 'Configure the PBS(Peak Burst Size) size in bytes.'
                              ;
                  type uint32 {
                    range 1..4294967295 {
                      description 'The PBS(Peak Burst Size) size in KB, support'
                                + ' <1-4294967295>'
                                  ;
                    }
                  }
                  units byte ;
                }
              }
              case unit-percentage {
                description 'Configure the percentage style'
                            ;
                leaf cir-percentage {
                  description 'Configure the CIR(Committed Information Rate) pe'
                            + 'rcentage (Set the accuracy rate per hundred (1%)'
                            + ')'
                              ;
                  type uint32 {
                    range 1..100 {
                      description 'The CIR percentage, support <1-100>'
                                  ;
                    }
                  }
                  mandatory true ;
                }
                leaf pir-percentage {
                  description 'Configure the PIR(Peak Information Rate) percent'
                            + 'age (Set the accuracy rate per hundred (1%))'
                              ;
                  type uint32 {
                    range 1..100 {
                      description 'The PIR percentage, support <1-100>'
                                  ;
                    }
                  }
                  mandatory true ;
                }
                ncd:revise-date 2020-12-23 ;
              }
            }
            leaf statistical-share {
              description 'The flag of statistical-share, as follows,'+"\n"
                        + '    ture  Statistical-share is configured'+"\n"
                        + '    false Statistical-share is not configured'
                          ;
              type boolean ;
              default false ;
            }
            leaf token-bucket-id {
              description 'Set token bucket id'
                          ;
              type uint32 {
                range 1..4294967295 {
                  description 'Token bucket id'
                              ;
                }
              }
              ncd:revise-date 2019-10-28 ;
            }
            container mode {
              if-feature qos-car-mode ;
              description 'Set color mode'
                          ;
              presence 'Configure mode information'
                       ;
              leaf mode-type {
                description 'Color mode type, as follows,'+"\n"
                          + '     blind   Color-Blind mode'+"\n"
                          + '     aware   Color-Aware mode'
                            ;
                type enumeration {
                  enum blind {
                    value 1 ;
                    description 'Color-Blind mode'
                                ;
                  }
                  enum aware {
                    value 2 ;
                    description 'Color-Aware mode'
                                ;
                  }
                }
                mandatory true ;
              }
            }
            container conform-action {
              description 'Action to packets that conform to the rate limit'
                          ;
              choice action {
                description 'Specify action to packets that conform to the rate'
                          + ' limit'
                            ;
                mandatory true ;
                case ca-drop {
                  description 'Drop packet in conform-action'
                              ;
                  leaf drop {
                    description 'Specify action to drop packet'
                                ;
                    type empty ;
                    mandatory true ;
                  }
                }
                case ca-transmit {
                  description 'Transmit packet in conform-action'
                              ;
                  leaf transmit {
                    description 'Specify action to transmit packet'
                                ;
                    type empty ;
                    mandatory true ;
                  }
                }
                case ca-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in conform-action, supp'
                                + 'ort <0-7>'
                                  ;
                      type uint8 {
                        range 0..7 {
                          description 'The MPLS-EXP value, support <0-7>'
                                      ;
                        }
                      }
                      mandatory true ;
                    }
                  }
                }
                case ca-precedence {
                  description 'Rewrite packet precedence and transmit the packet'
                              ;
                  container set-prec-transmit {
                    description 'Specify action to rewrite packet precedence an'
                              + 'd transmit it'
                                ;
                    leaf prec-value {
                      description 'Reset the IP-Precedence value in conform-act'
                                + 'ion, support <0-7>'
                                  ;
                      type uint8 {
                        range 0..7 {
                          description 'The IP-Precedence value, support <0-7>'
                                      ;
                        }
                      }
                      mandatory true ;
                    }
                  }
                }
                case ca-dscp {
                  description 'Rewrite packet DSCP and transmit the packet'
                              ;
                  container set-dscp-transmit {
                    description 'Specify action to rewrite packet DSCP and tran'
                              + 'smit it'
                                ;
                    leaf dscp-value {
                      description 'Reset DSCP in conform-action, support <0-63>'
                                  ;
                      type uint8 {
                        range 0..63 {
                          description 'The DSCP value, support <0-63>'
                                      ;
                        }
                      }
                      mandatory true ;
                    }
                  }
                }
                case ca-8021p {
                  description 'Rewrite packet 802.1p and transmit the packet'
                              ;
                  container set-8021p-transmit {
                    description 'Specify action to rewrite packet 802.1p and tr'
                              + 'ansmit it'
                                ;
                    leaf value-8021p {
                      description 'Reset 802.1p in conform-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ca-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ca-service-class {
                  description 'Rewrite packet service class and transmit the pa'
                            + 'cket'
                              ;
                  container set-service-class-transmit {
                    description 'Specify action to rewrite packet service class'
                              + ' and transmit it'
                                ;
                    leaf service-class-value {
                      description 'Reset service class in conform-action'
                                  ;
                      type qos-service-class ;
                      mandatory true ;
                    }
                  }
                  ncd:revise-date 2020-05-18 ;
                }
              }
            }
            container exceed-action {
              description 'Action to packets that exceed the rate limit'
                          ;
              choice action {
                description 'Specify action to packets that exceed the rate lim'
                          + 'it'
                            ;
                mandatory true ;
                case ea-drop {
                  description 'Drop packet in exceed-action'
                              ;
                  leaf drop {
                    description 'Specify action to drop packet'
                                ;
                    type empty ;
                    mandatory true ;
                  }
                }
                case ea-transmit {
                  description 'Transmit packet in exceed-action'
                              ;
                  leaf transmit {
                    description 'Specify action to transmit packet'
                                ;
                    type empty ;
                    mandatory true ;
                  }
                }
                case ea-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in exceed-action, suppo'
                                + 'rt <0-7>'
                                  ;
                      type uint8 {
                        range 0..7 {
                          description 'The MPLS-EXP value, support <0-7>'
                                      ;
                        }
                      }
                      mandatory true ;
                    }
                  }
                }
                case ea-precedence {
                  description 'Rewrite packet precedence and transmit the packet'
                              ;
                  container set-prec-transmit {
                    description 'Specify action to rewrite packet precedence an'
                              + 'd transmit it'
                                ;
                    leaf prec-value {
                      description 'Reset the IP-Precedence value in exceed-acti'
                                + 'on, support <0-7>'
                                  ;
                      type uint8 {
                        range 0..7 {
                          description 'The IP-Precedence value, support <0-7>'
                                      ;
                        }
                      }
                      mandatory true ;
                    }
                  }
                }
                case ea-dscp {
                  description 'Rewrite packet DSCP and transmit the packet'
                              ;
                  container set-dscp-transmit {
                    description 'Specify action to rewrite packet DSCP and tran'
                              + 'smit it'
                                ;
                    leaf dscp-value {
                      description 'Reset DSCP in exceed-action, support <0-63>'
                                  ;
                      type uint8 {
                        range 0..63 {
                          description 'The DSCP value, support <0-63>'
                                      ;
                        }
                      }
                      mandatory true ;
                    }
                  }
                }
                case ea-8021p {
                  description 'Rewrite packet 802.1p and transmit the packet'
                              ;
                  container set-8021p-transmit {
                    description 'Specify action to rewrite packet 802.1p and tr'
                              + 'ansmit it'
                                ;
                    leaf value-8021p {
                      description 'Reset 802.1p in exceed-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ea-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ea-service-class {
                  description 'Rewrite packet service class and transmit the pa'
                            + 'cket'
                              ;
                  container set-service-class-transmit {
                    description 'Specify action to rewrite packet service class'
                              + ' and transmit it'
                                ;
                    leaf service-class-value {
                      description 'Reset service class in exceed-action'
                                  ;
                      type qos-service-class ;
                      mandatory true ;
                    }
                  }
                  ncd:revise-date 2020-05-18 ;
                }
              }
            }
            container violate-action {
              description 'Action to packets that violate the rate limit'
                          ;
              choice action {
                description 'Specify action to packets that violate the rate li'
                          + 'mit'
                            ;
                mandatory true ;
                case va-drop {
                  description 'Drop packet in violate-action'
                              ;
                  leaf drop {
                    description 'Specify action to drop packet'
                                ;
                    type empty ;
                    mandatory true ;
                  }
                }
                case va-transmit {
                  description 'Transmit packet in violate-action'
                              ;
                  leaf transmit {
                    description 'Specify action to transmit packet'
                                ;
                    type empty ;
                    mandatory true ;
                  }
                }
                case va-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in violate-action, supp'
                                + 'ort <0-7>'
                                  ;
                      type uint8 {
                        range 0..7 {
                          description 'The MPLS-EXP value, support <0-7>'
                                      ;
                        }
                      }
                      mandatory true ;
                    }
                  }
                }
                case va-precedence {
                  description 'Rewrite packet precedence and transmit the packet'
                              ;
                  container set-prec-transmit {
                    description 'Specify action to rewrite packet precedence an'
                              + 'd transmit it'
                                ;
                    leaf prec-value {
                      description 'Reset the IP-Precedence value in violate-act'
                                + 'ion, support <0-7>'
                                  ;
                      type uint8 {
                        range 0..7 ;
                      }
                      mandatory true ;
                    }
                  }
                }
                case va-dscp {
                  description 'Rewrite packet DSCP and transmit the packet'
                              ;
                  container set-dscp-transmit {
                    description 'Specify action to rewrite packet DSCP and tran'
                              + 'smit it'
                                ;
                    leaf dscp-value {
                      description 'Reset DSCP in violate-action, support <0-63>'
                                  ;
                      type uint8 {
                        range 0..63 {
                          description 'The DSCP value, support <0-63>'
                                      ;
                        }
                      }
                      mandatory true ;
                    }
                  }
                }
                case va-8021p {
                  description 'Rewrite packet 802.1p and transmit the packet'
                              ;
                  container set-8021p-transmit {
                    description 'Specify action to rewrite packet 802.1p and tr'
                              + 'ansmit it'
                                ;
                    leaf value-8021p {
                      description 'Reset 802.1p in violate-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case va-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case va-service-class {
                  description 'Rewrite packet service class and transmit the pa'
                            + 'cket'
                              ;
                  container set-service-class-transmit {
                    description 'Specify action to rewrite packet service class'
                              + ' and transmit it'
                                ;
                    leaf service-class-value {
                      description 'Reset service class in violate-action'
                                  ;
                      type qos-service-class ;
                      mandatory true ;
                    }
                  }
                  ncd:revise-date 2020-05-18 ;
                }
              }
            }
          }
        }
        container mpls-exps {
          description 'Match MPLS-EXP'
                      ;
          list mpls-exp {
            description 'Configure interface rate limit based on matching mpls-'
                      + 'exp'
                        ;
            key 'if-name if-direct mpls-exp-value'
                ;
            leaf if-name {
              description 'Configure the name of the attaching interface'
                          ;
              type ncd:ifname {
                length 1..31 {
                  description 'Name of the attaching interface, support 1-31 ch'
                            + 'aracters'
                              ;
                }
              }
            }
            leaf if-direct {
              description 'Specify the direction of interface, as follows,'+"\n"
                        + '     input  Rate limit on input'+"\n"
                        + '     output Rate limit on output'
                          ;
              type enumeration {
                enum input {
                  value 1 ;
                  description 'Rate limit on input'
                              ;
                }
                enum output {
                  value 2 ;
                  description 'Rate limit on output'
                              ;
                }
              }
            }
            leaf mpls-exp-value {
              description 'MPLS-EXP value, support <0-7>'
                          ;
              type uint32 {
                range 0..7 {
                  description 'MPLS-EXP value, support <0-7>'
                              ;
                }
              }
            }
            leaf rate-limit-desc {
              description 'Description of rate limit, support 1-79 characters.'
                          ;
              type ncd:string-with-blank {
                length 1..79 {
                  description 'Description of rate limit, support 1-79 characte'
                            + 'rs.'
                              ;
                }
              }
              ncd:revise-date 2020-06-18 ;
            }
            choice unit-style {
              description "Specify unit's style"
                          ;
              mandatory true ;
              case unit-value {
                description 'Configure the value style'
                            ;
                leaf cir {
                  description 'Configure the CIR(Committed Information Rate) va'
                            + 'lue (default: kilobits per second)'
                              ;
                  type uint32 {
                    range 8..4294967295 {
                      description 'The CIR value (default: kilobits per second)'
                                + ',support <8-4294967295>'
                                  ;
                    }
                  }
                  mandatory true ;
                }
                leaf cir-unit {
                  description 'set cir unit, such as kbps, mbps, gbps'
                              ;
                  type qos-rate-unit-type ;
                }
                leaf cbs {
                  description 'Configure the CBS(Committed Burst Size) size in '
                            + 'bytes.'
                              ;
                  type uint32 {
                    range 1..4294967295 {
                      description 'The CBS(Committed Burst Size) size in bytes,'
                                + ' support <1-4294967295>.'
                                  ;
                    }
                  }
                  units byte ;
                }
                leaf pir {
                  description 'Configure the PIR(Peak Information Rate) value ('
                            + 'default: kilobits per second)'
                              ;
                  type uint32 {
                    range 8..4294967295 {
                      description 'The PIR(Peak Information Rate) value (defaul'
                                + 't: kilobits per second), support <8-42949672'
                                + '95>'
                                  ;
                    }
                  }
                  mandatory true ;
                }
                leaf pir-unit {
                  description 'set pir unit, such as kbps, mbps, gbps'
                              ;
                  type qos-rate-unit-type ;
                }
                leaf pbs {
                  description 'Configure the PBS(Peak Burst Size) size in bytes.'
                              ;
                  type uint32 {
                    range 1..4294967295 {
                      description 'The PBS(Peak Burst Size) size in KB, support'
                                + ' <1-4294967295>'
                                  ;
                    }
                  }
                  units byte ;
                }
              }
              case unit-percentage {
                description 'Configure the percentage style'
                            ;
                leaf cir-percentage {
                  description 'Configure the CIR(Committed Information Rate) pe'
                            + 'rcentage (Set the accuracy rate per hundred (1%)'
                            + ')'
                              ;
                  type uint32 {
                    range 1..100 {
                      description 'The CIR percentage, support <1-100>'
                                  ;
                    }
                  }
                  mandatory true ;
                }
                leaf pir-percentage {
                  description 'Configure the PIR(Peak Information Rate) percent'
                            + 'age (Set the accuracy rate per hundred (1%))'
                              ;
                  type uint32 {
                    range 1..100 {
                      description 'The PIR percentage, support <1-100>'
                                  ;
                    }
                  }
                  mandatory true ;
                }
                ncd:revise-date 2020-12-23 ;
              }
            }
            leaf statistical-share {
              description 'The flag of statistical-share, as follows,'+"\n"
                        + '    ture  Statistical-share is configured'+"\n"
                        + '    false Statistical-share is not configured'
                          ;
              type boolean ;
              default false ;
            }
            leaf token-bucket-id {
              description 'Set token bucket id'
                          ;
              type uint32 {
                range 1..4294967295 {
                  description 'Token bucket id'
                              ;
                }
              }
              ncd:revise-date 2019-10-28 ;
            }
            container mode {
              if-feature qos-car-mode ;
              description 'Set color mode'
                          ;
              presence 'Configure mode information'
                       ;
              leaf mode-type {
                description 'Color mode type, as follows,'+"\n"
                          + '     blind   Color-Blind mode'+"\n"
                          + '     aware   Color-Aware mode'
                            ;
                type enumeration {
                  enum blind {
                    value 1 ;
                    description 'Color-Blind mode'
                                ;
                  }
                  enum aware {
                    value 2 ;
                    description 'Color-Aware mode'
                                ;
                  }
                }
                mandatory true ;
              }
            }
            container conform-action {
              description 'Action to packets that conform to the rate limit'
                          ;
              choice action {
                description 'Specify action to packets that conform to the rate'
                          + ' limit'
                            ;
                mandatory true ;
                case ca-drop {
                  description 'Drop packet in conform-action'
                              ;
                  leaf drop {
                    description 'Specify action to drop packet'
                                ;
                    type empty ;
                    mandatory true ;
                  }
                }
                case ca-transmit {
                  description 'Transmit packet in conform-action'
                              ;
                  leaf transmit {
                    description 'Specify action to transmit packet'
                                ;
                    type empty ;
                    mandatory true ;
                  }
                }
                case ca-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in conform-action, supp'
                                + 'ort <0-7>'
                                  ;
                      type uint8 {
                        range 0..7 {
                          description 'The MPLS-EXP value, support <0-7>'
                                      ;
                        }
                      }
                      mandatory true ;
                    }
                  }
                }
                case ca-precedence {
                  description 'Rewrite packet precedence and transmit the packet'
                              ;
                  container set-prec-transmit {
                    description 'Specify action to rewrite packet precedence an'
                              + 'd transmit it'
                                ;
                    leaf prec-value {
                      description 'Reset the IP-Precedence value in conform-act'
                                + 'ion, support <0-7>'
                                  ;
                      type uint8 {
                        range 0..7 {
                          description 'The IP-Precedence value, support <0-7>'
                                      ;
                        }
                      }
                      mandatory true ;
                    }
                  }
                }
                case ca-dscp {
                  description 'Rewrite packet DSCP and transmit the packet'
                              ;
                  container set-dscp-transmit {
                    description 'Specify action to rewrite packet DSCP and tran'
                              + 'smit it'
                                ;
                    leaf dscp-value {
                      description 'Reset DSCP in conform-action, support <0-63>'
                                  ;
                      type uint8 {
                        range 0..63 {
                          description 'The DSCP value, support <0-63>'
                                      ;
                        }
                      }
                      mandatory true ;
                    }
                  }
                }
                case ca-8021p {
                  description 'Rewrite packet 802.1p and transmit the packet'
                              ;
                  container set-8021p-transmit {
                    description 'Specify action to rewrite packet 802.1p and tr'
                              + 'ansmit it'
                                ;
                    leaf value-8021p {
                      description 'Reset 802.1p in conform-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ca-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ca-service-class {
                  description 'Rewrite packet service class and transmit the pa'
                            + 'cket'
                              ;
                  container set-service-class-transmit {
                    description 'Specify action to rewrite packet service class'
                              + ' and transmit it'
                                ;
                    leaf service-class-value {
                      description 'Reset service class in conform-action'
                                  ;
                      type qos-service-class ;
                      mandatory true ;
                    }
                  }
                  ncd:revise-date 2020-05-18 ;
                }
              }
            }
            container exceed-action {
              description 'Action to packets that exceed the rate limit'
                          ;
              choice action {
                description 'Specify action to packets that exceed the rate lim'
                          + 'it'
                            ;
                mandatory true ;
                case ea-drop {
                  description 'Drop packet in exceed-action'
                              ;
                  leaf drop {
                    description 'Specify action to drop packet'
                                ;
                    type empty ;
                    mandatory true ;
                  }
                }
                case ea-transmit {
                  description 'Transmit packet in exceed-action'
                              ;
                  leaf transmit {
                    description 'Specify action to transmit packet'
                                ;
                    type empty ;
                    mandatory true ;
                  }
                }
                case ea-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in exceed-action, suppo'
                                + 'rt <0-7>'
                                  ;
                      type uint8 {
                        range 0..7 {
                          description 'The MPLS-EXP value, support <0-7>'
                                      ;
                        }
                      }
                      mandatory true ;
                    }
                  }
                }
                case ea-precedence {
                  description 'Rewrite packet precedence and transmit the packet'
                              ;
                  container set-prec-transmit {
                    description 'Specify action to rewrite packet precedence an'
                              + 'd transmit it'
                                ;
                    leaf prec-value {
                      description 'Reset the IP-Precedence value in exceed-acti'
                                + 'on, support <0-7>'
                                  ;
                      type uint8 {
                        range 0..7 {
                          description 'The IP-Precedence value, support <0-7>'
                                      ;
                        }
                      }
                      mandatory true ;
                    }
                  }
                }
                case ea-dscp {
                  description 'Rewrite packet DSCP and transmit the packet'
                              ;
                  container set-dscp-transmit {
                    description 'Specify action to rewrite packet DSCP and tran'
                              + 'smit it'
                                ;
                    leaf dscp-value {
                      description 'Reset DSCP in exceed-action, support <0-63>'
                                  ;
                      type uint8 {
                        range 0..63 {
                          description 'The DSCP value, support <0-63>'
                                      ;
                        }
                      }
                      mandatory true ;
                    }
                  }
                }
                case ea-8021p {
                  description 'Rewrite packet 802.1p and transmit the packet'
                              ;
                  container set-8021p-transmit {
                    description 'Specify action to rewrite packet 802.1p and tr'
                              + 'ansmit it'
                                ;
                    leaf value-8021p {
                      description 'Reset 802.1p in exceed-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ea-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ea-service-class {
                  description 'Rewrite packet service class and transmit the pa'
                            + 'cket'
                              ;
                  container set-service-class-transmit {
                    description 'Specify action to rewrite packet service class'
                              + ' and transmit it'
                                ;
                    leaf service-class-value {
                      description 'Reset service class in exceed-action'
                                  ;
                      type qos-service-class ;
                      mandatory true ;
                    }
                  }
                  ncd:revise-date 2020-05-18 ;
                }
              }
            }
            container violate-action {
              description 'Action to packets that violate the rate limit'
                          ;
              choice action {
                description 'Specify action to packets that violate the rate li'
                          + 'mit'
                            ;
                mandatory true ;
                case va-drop {
                  description 'Drop packet in violate-action'
                              ;
                  leaf drop {
                    description 'Specify action to drop packet'
                                ;
                    type empty ;
                    mandatory true ;
                  }
                }
                case va-transmit {
                  description 'Transmit packet in violate-action'
                              ;
                  leaf transmit {
                    description 'Specify action to transmit packet'
                                ;
                    type empty ;
                    mandatory true ;
                  }
                }
                case va-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in violate-action, supp'
                                + 'ort <0-7>'
                                  ;
                      type uint8 {
                        range 0..7 {
                          description 'The MPLS-EXP value, support <0-7>'
                                      ;
                        }
                      }
                      mandatory true ;
                    }
                  }
                }
                case va-precedence {
                  description 'Rewrite packet precedence and transmit the packet'
                              ;
                  container set-prec-transmit {
                    description 'Specify action to rewrite packet precedence an'
                              + 'd transmit it'
                                ;
                    leaf prec-value {
                      description 'Reset the IP-Precedence value in violate-act'
                                + 'ion, support <0-7>'
                                  ;
                      type uint8 {
                        range 0..7 ;
                      }
                      mandatory true ;
                    }
                  }
                }
                case va-dscp {
                  description 'Rewrite packet DSCP and transmit the packet'
                              ;
                  container set-dscp-transmit {
                    description 'Specify action to rewrite packet DSCP and tran'
                              + 'smit it'
                                ;
                    leaf dscp-value {
                      description 'Reset DSCP in violate-action, support <0-63>'
                                  ;
                      type uint8 {
                        range 0..63 {
                          description 'The DSCP value, support <0-63>'
                                      ;
                        }
                      }
                      mandatory true ;
                    }
                  }
                }
                case va-8021p {
                  description 'Rewrite packet 802.1p and transmit the packet'
                              ;
                  container set-8021p-transmit {
                    description 'Specify action to rewrite packet 802.1p and tr'
                              + 'ansmit it'
                                ;
                    leaf value-8021p {
                      description 'Reset 802.1p in violate-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case va-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case va-service-class {
                  description 'Rewrite packet service class and transmit the pa'
                            + 'cket'
                              ;
                  container set-service-class-transmit {
                    description 'Specify action to rewrite packet service class'
                              + ' and transmit it'
                                ;
                    leaf service-class-value {
                      description 'Reset service class in violate-action'
                                  ;
                      type qos-service-class ;
                      mandatory true ;
                    }
                  }
                  ncd:revise-date 2020-05-18 ;
                }
              }
            }
          }
        }
        container inner-vlans {
          description 'Match inner VLAN ID'
                      ;
          list inner-vlan {
            description 'Configure interface rate limit based on matching inner'
                      + '-vlan'
                        ;
            key 'if-name if-direct inner-vlan'
                ;
            leaf if-name {
              description 'Configure the name of the attaching interface'
                          ;
              type ncd:ifname {
                length 1..31 {
                  description 'Name of the attaching interface, support 1-31 ch'
                            + 'aracters'
                              ;
                }
              }
            }
            leaf if-direct {
              description 'Specify the direction of interface, as follows,'+"\n"
                        + '     input  Rate limit on input'+"\n"
                        + '     output Rate limit on output'
                          ;
              type enumeration {
                enum input {
                  value 1 ;
                  description 'Rate limit on input'
                              ;
                }
                enum output {
                  value 2 ;
                  description 'Rate limit on output'
                              ;
                }
              }
            }
            leaf inner-vlan {
              description 'Configure inner-VLAN value in range mode, support si'
                        + 'ngle inner-VLAN value or range(max num:4;spacing mar'
                        + 'k:,) in <1-4094>. For example,"1,300-400,1000,2000-4'
                        + '000",etc.'
                          ;
              type qos-vlan-range ;
            }
            leaf rate-limit-desc {
              description 'Description of rate limit, support 1-79 characters.'
                          ;
              type ncd:string-with-blank {
                length 1..79 {
                  description 'Description of rate limit, support 1-79 characte'
                            + 'rs.'
                              ;
                }
              }
              ncd:revise-date 2020-06-18 ;
            }
            choice unit-style {
              description "Specify unit's style"
                          ;
              mandatory true ;
              case unit-value {
                description 'Configure the value style'
                            ;
                leaf cir {
                  description 'Configure the CIR(Committed Information Rate) va'
                            + 'lue (default: kilobits per second)'
                              ;
                  type uint32 {
                    range 8..4294967295 {
                      description 'The CIR value (default: kilobits per second)'
                                + ',support <8-4294967295>'
                                  ;
                    }
                  }
                  mandatory true ;
                }
                leaf cir-unit {
                  description 'set cir unit, such as kbps, mbps, gbps'
                              ;
                  type qos-rate-unit-type ;
                }
                leaf cbs {
                  description 'Configure the CBS(Committed Burst Size) size in '
                            + 'bytes.'
                              ;
                  type uint32 {
                    range 1..4294967295 {
                      description 'The CBS(Committed Burst Size) size in bytes,'
                                + ' support <1-4294967295>.'
                                  ;
                    }
                  }
                  units byte ;
                }
                leaf pir {
                  description 'Configure the PIR(Peak Information Rate) value ('
                            + 'default: kilobits per second)'
                              ;
                  type uint32 {
                    range 8..4294967295 {
                      description 'The PIR(Peak Information Rate) value (defaul'
                                + 't: kilobits per second), support <8-42949672'
                                + '95>'
                                  ;
                    }
                  }
                  mandatory true ;
                }
                leaf pir-unit {
                  description 'set pir unit, such as kbps, mbps, gbps'
                              ;
                  type qos-rate-unit-type ;
                }
                leaf pbs {
                  description 'Configure the PBS(Peak Burst Size) size in bytes.'
                              ;
                  type uint32 {
                    range 1..4294967295 {
                      description 'The PBS(Peak Burst Size) size in KB, support'
                                + ' <1-4294967295>'
                                  ;
                    }
                  }
                  units byte ;
                }
              }
              case unit-percentage {
                description 'Configure the percentage style'
                            ;
                leaf cir-percentage {
                  description 'Configure the CIR(Committed Information Rate) pe'
                            + 'rcentage (Set the accuracy rate per hundred (1%)'
                            + ')'
                              ;
                  type uint32 {
                    range 1..100 {
                      description 'The CIR percentage, support <1-100>'
                                  ;
                    }
                  }
                  mandatory true ;
                }
                leaf pir-percentage {
                  description 'Configure the PIR(Peak Information Rate) percent'
                            + 'age (Set the accuracy rate per hundred (1%))'
                              ;
                  type uint32 {
                    range 1..100 {
                      description 'The PIR percentage, support <1-100>'
                                  ;
                    }
                  }
                  mandatory true ;
                }
                ncd:revise-date 2020-12-23 ;
              }
            }
            leaf statistical-share {
              description 'The flag of statistical-share, as follows,'+"\n"
                        + '    ture  Statistical-share is configured'+"\n"
                        + '    false Statistical-share is not configured'
                          ;
              type boolean ;
              default false ;
            }
            leaf token-bucket-id {
              description 'Set token bucket id'
                          ;
              type uint32 {
                range 1..4294967295 {
                  description 'Token bucket id'
                              ;
                }
              }
              ncd:revise-date 2019-10-28 ;
            }
            container mode {
              if-feature qos-car-mode ;
              description 'Set color mode'
                          ;
              presence 'Configure mode information'
                       ;
              leaf mode-type {
                description 'Color mode type, as follows,'+"\n"
                          + '     blind   Color-Blind mode'+"\n"
                          + '     aware   Color-Aware mode'
                            ;
                type enumeration {
                  enum blind {
                    value 1 ;
                    description 'Color-Blind mode'
                                ;
                  }
                  enum aware {
                    value 2 ;
                    description 'Color-Aware mode'
                                ;
                  }
                }
                mandatory true ;
              }
            }
            container conform-action {
              description 'Action to packets that conform to the rate limit'
                          ;
              choice action {
                description 'Specify action to packets that conform to the rate'
                          + ' limit'
                            ;
                mandatory true ;
                case ca-drop {
                  description 'Drop packet in conform-action'
                              ;
                  leaf drop {
                    description 'Specify action to drop packet'
                                ;
                    type empty ;
                    mandatory true ;
                  }
                }
                case ca-transmit {
                  description 'Transmit packet in conform-action'
                              ;
                  leaf transmit {
                    description 'Specify action to transmit packet'
                                ;
                    type empty ;
                    mandatory true ;
                  }
                }
                case ca-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in conform-action, supp'
                                + 'ort <0-7>'
                                  ;
                      type uint8 {
                        range 0..7 {
                          description 'The MPLS-EXP value, support <0-7>'
                                      ;
                        }
                      }
                      mandatory true ;
                    }
                  }
                }
                case ca-precedence {
                  description 'Rewrite packet precedence and transmit the packet'
                              ;
                  container set-prec-transmit {
                    description 'Specify action to rewrite packet precedence an'
                              + 'd transmit it'
                                ;
                    leaf prec-value {
                      description 'Reset the IP-Precedence value in conform-act'
                                + 'ion, support <0-7>'
                                  ;
                      type uint8 {
                        range 0..7 {
                          description 'The IP-Precedence value, support <0-7>'
                                      ;
                        }
                      }
                      mandatory true ;
                    }
                  }
                }
                case ca-dscp {
                  description 'Rewrite packet DSCP and transmit the packet'
                              ;
                  container set-dscp-transmit {
                    description 'Specify action to rewrite packet DSCP and tran'
                              + 'smit it'
                                ;
                    leaf dscp-value {
                      description 'Reset DSCP in conform-action, support <0-63>'
                                  ;
                      type uint8 {
                        range 0..63 {
                          description 'The DSCP value, support <0-63>'
                                      ;
                        }
                      }
                      mandatory true ;
                    }
                  }
                }
                case ca-8021p {
                  description 'Rewrite packet 802.1p and transmit the packet'
                              ;
                  container set-8021p-transmit {
                    description 'Specify action to rewrite packet 802.1p and tr'
                              + 'ansmit it'
                                ;
                    leaf value-8021p {
                      description 'Reset 802.1p in conform-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ca-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ca-service-class {
                  description 'Rewrite packet service class and transmit the pa'
                            + 'cket'
                              ;
                  container set-service-class-transmit {
                    description 'Specify action to rewrite packet service class'
                              + ' and transmit it'
                                ;
                    leaf service-class-value {
                      description 'Reset service class in conform-action'
                                  ;
                      type qos-service-class ;
                      mandatory true ;
                    }
                  }
                  ncd:revise-date 2020-05-18 ;
                }
              }
            }
            container exceed-action {
              description 'Action to packets that exceed the rate limit'
                          ;
              choice action {
                description 'Specify action to packets that exceed the rate lim'
                          + 'it'
                            ;
                mandatory true ;
                case ea-drop {
                  description 'Drop packet in exceed-action'
                              ;
                  leaf drop {
                    description 'Specify action to drop packet'
                                ;
                    type empty ;
                    mandatory true ;
                  }
                }
                case ea-transmit {
                  description 'Transmit packet in exceed-action'
                              ;
                  leaf transmit {
                    description 'Specify action to transmit packet'
                                ;
                    type empty ;
                    mandatory true ;
                  }
                }
                case ea-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in exceed-action, suppo'
                                + 'rt <0-7>'
                                  ;
                      type uint8 {
                        range 0..7 {
                          description 'The MPLS-EXP value, support <0-7>'
                                      ;
                        }
                      }
                      mandatory true ;
                    }
                  }
                }
                case ea-precedence {
                  description 'Rewrite packet precedence and transmit the packet'
                              ;
                  container set-prec-transmit {
                    description 'Specify action to rewrite packet precedence an'
                              + 'd transmit it'
                                ;
                    leaf prec-value {
                      description 'Reset the IP-Precedence value in exceed-acti'
                                + 'on, support <0-7>'
                                  ;
                      type uint8 {
                        range 0..7 {
                          description 'The IP-Precedence value, support <0-7>'
                                      ;
                        }
                      }
                      mandatory true ;
                    }
                  }
                }
                case ea-dscp {
                  description 'Rewrite packet DSCP and transmit the packet'
                              ;
                  container set-dscp-transmit {
                    description 'Specify action to rewrite packet DSCP and tran'
                              + 'smit it'
                                ;
                    leaf dscp-value {
                      description 'Reset DSCP in exceed-action, support <0-63>'
                                  ;
                      type uint8 {
                        range 0..63 {
                          description 'The DSCP value, support <0-63>'
                                      ;
                        }
                      }
                      mandatory true ;
                    }
                  }
                }
                case ea-8021p {
                  description 'Rewrite packet 802.1p and transmit the packet'
                              ;
                  container set-8021p-transmit {
                    description 'Specify action to rewrite packet 802.1p and tr'
                              + 'ansmit it'
                                ;
                    leaf value-8021p {
                      description 'Reset 802.1p in exceed-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ea-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ea-service-class {
                  description 'Rewrite packet service class and transmit the pa'
                            + 'cket'
                              ;
                  container set-service-class-transmit {
                    description 'Specify action to rewrite packet service class'
                              + ' and transmit it'
                                ;
                    leaf service-class-value {
                      description 'Reset service class in exceed-action'
                                  ;
                      type qos-service-class ;
                      mandatory true ;
                    }
                  }
                  ncd:revise-date 2020-05-18 ;
                }
              }
            }
            container violate-action {
              description 'Action to packets that violate the rate limit'
                          ;
              choice action {
                description 'Specify action to packets that violate the rate li'
                          + 'mit'
                            ;
                mandatory true ;
                case va-drop {
                  description 'Drop packet in violate-action'
                              ;
                  leaf drop {
                    description 'Specify action to drop packet'
                                ;
                    type empty ;
                    mandatory true ;
                  }
                }
                case va-transmit {
                  description 'Transmit packet in violate-action'
                              ;
                  leaf transmit {
                    description 'Specify action to transmit packet'
                                ;
                    type empty ;
                    mandatory true ;
                  }
                }
                case va-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in violate-action, supp'
                                + 'ort <0-7>'
                                  ;
                      type uint8 {
                        range 0..7 {
                          description 'The MPLS-EXP value, support <0-7>'
                                      ;
                        }
                      }
                      mandatory true ;
                    }
                  }
                }
                case va-precedence {
                  description 'Rewrite packet precedence and transmit the packet'
                              ;
                  container set-prec-transmit {
                    description 'Specify action to rewrite packet precedence an'
                              + 'd transmit it'
                                ;
                    leaf prec-value {
                      description 'Reset the IP-Precedence value in violate-act'
                                + 'ion, support <0-7>'
                                  ;
                      type uint8 {
                        range 0..7 ;
                      }
                      mandatory true ;
                    }
                  }
                }
                case va-dscp {
                  description 'Rewrite packet DSCP and transmit the packet'
                              ;
                  container set-dscp-transmit {
                    description 'Specify action to rewrite packet DSCP and tran'
                              + 'smit it'
                                ;
                    leaf dscp-value {
                      description 'Reset DSCP in violate-action, support <0-63>'
                                  ;
                      type uint8 {
                        range 0..63 {
                          description 'The DSCP value, support <0-63>'
                                      ;
                        }
                      }
                      mandatory true ;
                    }
                  }
                }
                case va-8021p {
                  description 'Rewrite packet 802.1p and transmit the packet'
                              ;
                  container set-8021p-transmit {
                    description 'Specify action to rewrite packet 802.1p and tr'
                              + 'ansmit it'
                                ;
                    leaf value-8021p {
                      description 'Reset 802.1p in violate-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case va-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case va-service-class {
                  description 'Rewrite packet service class and transmit the pa'
                            + 'cket'
                              ;
                  container set-service-class-transmit {
                    description 'Specify action to rewrite packet service class'
                              + ' and transmit it'
                                ;
                    leaf service-class-value {
                      description 'Reset service class in violate-action'
                                  ;
                      type qos-service-class ;
                      mandatory true ;
                    }
                  }
                  ncd:revise-date 2020-05-18 ;
                }
              }
            }
          }
        }
        container outer-vlans {
          description 'Match outer VLAN ID'
                      ;
          list outer-vlan {
            description 'Configure interface rate limit based on matching outer'
                      + '-vlan'
                        ;
            key 'if-name if-direct outer-vlan'
                ;
            leaf if-name {
              description 'Configure the name of the attaching interface'
                          ;
              type ncd:ifname {
                length 1..31 {
                  description 'Name of the attaching interface, support 1-31 ch'
                            + 'aracters'
                              ;
                }
              }
            }
            leaf if-direct {
              description 'Specify the direction of interface, as follows,'+"\n"
                        + '     input  Rate limit on input'+"\n"
                        + '     output Rate limit on output'
                          ;
              type enumeration {
                enum input {
                  value 1 ;
                  description 'Rate limit on input'
                              ;
                }
                enum output {
                  value 2 ;
                  description 'Rate limit on output'
                              ;
                }
              }
            }
            leaf outer-vlan {
              description 'Configure outer-VLAN value in range mode, support si'
                        + 'ngle outer-VLAN value or range(max num:4;spacing mar'
                        + 'k:,) in <1-4094>. For example,"1,300-400,1000,2000-4'
                        + '000",etc.'
                          ;
              type qos-vlan-range ;
            }
            leaf rate-limit-desc {
              description 'Description of rate limit, support 1-79 characters.'
                          ;
              type ncd:string-with-blank {
                length 1..79 {
                  description 'Description of rate limit, support 1-79 characte'
                            + 'rs.'
                              ;
                }
              }
              ncd:revise-date 2020-06-18 ;
            }
            choice unit-style {
              description "Specify unit's style"
                          ;
              mandatory true ;
              case unit-value {
                description 'Configure the value style'
                            ;
                leaf cir {
                  description 'Configure the CIR(Committed Information Rate) va'
                            + 'lue (default: kilobits per second)'
                              ;
                  type uint32 {
                    range 8..4294967295 {
                      description 'The CIR value (default: kilobits per second)'
                                + ',support <8-4294967295>'
                                  ;
                    }
                  }
                  mandatory true ;
                }
                leaf cir-unit {
                  description 'set cir unit, such as kbps, mbps, gbps'
                              ;
                  type qos-rate-unit-type ;
                }
                leaf cbs {
                  description 'Configure the CBS(Committed Burst Size) size in '
                            + 'bytes.'
                              ;
                  type uint32 {
                    range 1..4294967295 {
                      description 'The CBS(Committed Burst Size) size in bytes,'
                                + ' support <1-4294967295>.'
                                  ;
                    }
                  }
                  units byte ;
                }
                leaf pir {
                  description 'Configure the PIR(Peak Information Rate) value ('
                            + 'default: kilobits per second)'
                              ;
                  type uint32 {
                    range 8..4294967295 {
                      description 'The PIR(Peak Information Rate) value (defaul'
                                + 't: kilobits per second), support <8-42949672'
                                + '95>'
                                  ;
                    }
                  }
                  mandatory true ;
                }
                leaf pir-unit {
                  description 'set pir unit, such as kbps, mbps, gbps'
                              ;
                  type qos-rate-unit-type ;
                }
                leaf pbs {
                  description 'Configure the PBS(Peak Burst Size) size in bytes.'
                              ;
                  type uint32 {
                    range 1..4294967295 {
                      description 'The PBS(Peak Burst Size) size in KB, support'
                                + ' <1-4294967295>'
                                  ;
                    }
                  }
                  units byte ;
                }
              }
              case unit-percentage {
                description 'Configure the percentage style'
                            ;
                leaf cir-percentage {
                  description 'Configure the CIR(Committed Information Rate) pe'
                            + 'rcentage (Set the accuracy rate per hundred (1%)'
                            + ')'
                              ;
                  type uint32 {
                    range 1..100 {
                      description 'The CIR percentage, support <1-100>'
                                  ;
                    }
                  }
                  mandatory true ;
                }
                leaf pir-percentage {
                  description 'Configure the PIR(Peak Information Rate) percent'
                            + 'age (Set the accuracy rate per hundred (1%))'
                              ;
                  type uint32 {
                    range 1..100 {
                      description 'The PIR percentage, support <1-100>'
                                  ;
                    }
                  }
                  mandatory true ;
                }
                ncd:revise-date 2020-12-23 ;
              }
            }
            leaf statistical-share {
              description 'The flag of statistical-share, as follows,'+"\n"
                        + '    ture  Statistical-share is configured'+"\n"
                        + '    false Statistical-share is not configured'
                          ;
              type boolean ;
              default false ;
            }
            leaf token-bucket-id {
              description 'Set token bucket id'
                          ;
              type uint32 {
                range 1..4294967295 {
                  description 'Token bucket id'
                              ;
                }
              }
              ncd:revise-date 2019-10-28 ;
            }
            container mode {
              if-feature qos-car-mode ;
              description 'Set color mode'
                          ;
              presence 'Configure mode information'
                       ;
              leaf mode-type {
                description 'Color mode type, as follows,'+"\n"
                          + '     blind   Color-Blind mode'+"\n"
                          + '     aware   Color-Aware mode'
                            ;
                type enumeration {
                  enum blind {
                    value 1 ;
                    description 'Color-Blind mode'
                                ;
                  }
                  enum aware {
                    value 2 ;
                    description 'Color-Aware mode'
                                ;
                  }
                }
                mandatory true ;
              }
            }
            container conform-action {
              description 'Action to packets that conform to the rate limit'
                          ;
              choice action {
                description 'Specify action to packets that conform to the rate'
                          + ' limit'
                            ;
                mandatory true ;
                case ca-drop {
                  description 'Drop packet in conform-action'
                              ;
                  leaf drop {
                    description 'Specify action to drop packet'
                                ;
                    type empty ;
                    mandatory true ;
                  }
                }
                case ca-transmit {
                  description 'Transmit packet in conform-action'
                              ;
                  leaf transmit {
                    description 'Specify action to transmit packet'
                                ;
                    type empty ;
                    mandatory true ;
                  }
                }
                case ca-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in conform-action, supp'
                                + 'ort <0-7>'
                                  ;
                      type uint8 {
                        range 0..7 {
                          description 'The MPLS-EXP value, support <0-7>'
                                      ;
                        }
                      }
                      mandatory true ;
                    }
                  }
                }
                case ca-precedence {
                  description 'Rewrite packet precedence and transmit the packet'
                              ;
                  container set-prec-transmit {
                    description 'Specify action to rewrite packet precedence an'
                              + 'd transmit it'
                                ;
                    leaf prec-value {
                      description 'Reset the IP-Precedence value in conform-act'
                                + 'ion, support <0-7>'
                                  ;
                      type uint8 {
                        range 0..7 {
                          description 'The IP-Precedence value, support <0-7>'
                                      ;
                        }
                      }
                      mandatory true ;
                    }
                  }
                }
                case ca-dscp {
                  description 'Rewrite packet DSCP and transmit the packet'
                              ;
                  container set-dscp-transmit {
                    description 'Specify action to rewrite packet DSCP and tran'
                              + 'smit it'
                                ;
                    leaf dscp-value {
                      description 'Reset DSCP in conform-action, support <0-63>'
                                  ;
                      type uint8 {
                        range 0..63 {
                          description 'The DSCP value, support <0-63>'
                                      ;
                        }
                      }
                      mandatory true ;
                    }
                  }
                }
                case ca-8021p {
                  description 'Rewrite packet 802.1p and transmit the packet'
                              ;
                  container set-8021p-transmit {
                    description 'Specify action to rewrite packet 802.1p and tr'
                              + 'ansmit it'
                                ;
                    leaf value-8021p {
                      description 'Reset 802.1p in conform-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ca-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ca-service-class {
                  description 'Rewrite packet service class and transmit the pa'
                            + 'cket'
                              ;
                  container set-service-class-transmit {
                    description 'Specify action to rewrite packet service class'
                              + ' and transmit it'
                                ;
                    leaf service-class-value {
                      description 'Reset service class in conform-action'
                                  ;
                      type qos-service-class ;
                      mandatory true ;
                    }
                  }
                  ncd:revise-date 2020-05-18 ;
                }
              }
            }
            container exceed-action {
              description 'Action to packets that exceed the rate limit'
                          ;
              choice action {
                description 'Specify action to packets that exceed the rate lim'
                          + 'it'
                            ;
                mandatory true ;
                case ea-drop {
                  description 'Drop packet in exceed-action'
                              ;
                  leaf drop {
                    description 'Specify action to drop packet'
                                ;
                    type empty ;
                    mandatory true ;
                  }
                }
                case ea-transmit {
                  description 'Transmit packet in exceed-action'
                              ;
                  leaf transmit {
                    description 'Specify action to transmit packet'
                                ;
                    type empty ;
                    mandatory true ;
                  }
                }
                case ea-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in exceed-action, suppo'
                                + 'rt <0-7>'
                                  ;
                      type uint8 {
                        range 0..7 {
                          description 'The MPLS-EXP value, support <0-7>'
                                      ;
                        }
                      }
                      mandatory true ;
                    }
                  }
                }
                case ea-precedence {
                  description 'Rewrite packet precedence and transmit the packet'
                              ;
                  container set-prec-transmit {
                    description 'Specify action to rewrite packet precedence an'
                              + 'd transmit it'
                                ;
                    leaf prec-value {
                      description 'Reset the IP-Precedence value in exceed-acti'
                                + 'on, support <0-7>'
                                  ;
                      type uint8 {
                        range 0..7 {
                          description 'The IP-Precedence value, support <0-7>'
                                      ;
                        }
                      }
                      mandatory true ;
                    }
                  }
                }
                case ea-dscp {
                  description 'Rewrite packet DSCP and transmit the packet'
                              ;
                  container set-dscp-transmit {
                    description 'Specify action to rewrite packet DSCP and tran'
                              + 'smit it'
                                ;
                    leaf dscp-value {
                      description 'Reset DSCP in exceed-action, support <0-63>'
                                  ;
                      type uint8 {
                        range 0..63 {
                          description 'The DSCP value, support <0-63>'
                                      ;
                        }
                      }
                      mandatory true ;
                    }
                  }
                }
                case ea-8021p {
                  description 'Rewrite packet 802.1p and transmit the packet'
                              ;
                  container set-8021p-transmit {
                    description 'Specify action to rewrite packet 802.1p and tr'
                              + 'ansmit it'
                                ;
                    leaf value-8021p {
                      description 'Reset 802.1p in exceed-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ea-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ea-service-class {
                  description 'Rewrite packet service class and transmit the pa'
                            + 'cket'
                              ;
                  container set-service-class-transmit {
                    description 'Specify action to rewrite packet service class'
                              + ' and transmit it'
                                ;
                    leaf service-class-value {
                      description 'Reset service class in exceed-action'
                                  ;
                      type qos-service-class ;
                      mandatory true ;
                    }
                  }
                  ncd:revise-date 2020-05-18 ;
                }
              }
            }
            container violate-action {
              description 'Action to packets that violate the rate limit'
                          ;
              choice action {
                description 'Specify action to packets that violate the rate li'
                          + 'mit'
                            ;
                mandatory true ;
                case va-drop {
                  description 'Drop packet in violate-action'
                              ;
                  leaf drop {
                    description 'Specify action to drop packet'
                                ;
                    type empty ;
                    mandatory true ;
                  }
                }
                case va-transmit {
                  description 'Transmit packet in violate-action'
                              ;
                  leaf transmit {
                    description 'Specify action to transmit packet'
                                ;
                    type empty ;
                    mandatory true ;
                  }
                }
                case va-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in violate-action, supp'
                                + 'ort <0-7>'
                                  ;
                      type uint8 {
                        range 0..7 {
                          description 'The MPLS-EXP value, support <0-7>'
                                      ;
                        }
                      }
                      mandatory true ;
                    }
                  }
                }
                case va-precedence {
                  description 'Rewrite packet precedence and transmit the packet'
                              ;
                  container set-prec-transmit {
                    description 'Specify action to rewrite packet precedence an'
                              + 'd transmit it'
                                ;
                    leaf prec-value {
                      description 'Reset the IP-Precedence value in violate-act'
                                + 'ion, support <0-7>'
                                  ;
                      type uint8 {
                        range 0..7 ;
                      }
                      mandatory true ;
                    }
                  }
                }
                case va-dscp {
                  description 'Rewrite packet DSCP and transmit the packet'
                              ;
                  container set-dscp-transmit {
                    description 'Specify action to rewrite packet DSCP and tran'
                              + 'smit it'
                                ;
                    leaf dscp-value {
                      description 'Reset DSCP in violate-action, support <0-63>'
                                  ;
                      type uint8 {
                        range 0..63 {
                          description 'The DSCP value, support <0-63>'
                                      ;
                        }
                      }
                      mandatory true ;
                    }
                  }
                }
                case va-8021p {
                  description 'Rewrite packet 802.1p and transmit the packet'
                              ;
                  container set-8021p-transmit {
                    description 'Specify action to rewrite packet 802.1p and tr'
                              + 'ansmit it'
                                ;
                    leaf value-8021p {
                      description 'Reset 802.1p in violate-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case va-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case va-service-class {
                  description 'Rewrite packet service class and transmit the pa'
                            + 'cket'
                              ;
                  container set-service-class-transmit {
                    description 'Specify action to rewrite packet service class'
                              + ' and transmit it'
                                ;
                    leaf service-class-value {
                      description 'Reset service class in violate-action'
                                  ;
                      type qos-service-class ;
                      mandatory true ;
                    }
                  }
                  ncd:revise-date 2020-05-18 ;
                }
              }
            }
          }
        }
        container multi-vlans {
          description 'Match inner and outer VLAN ID'
                      ;
          list multi-vlan {
            description 'Configure interface rate limit based on matching inner'
                      + ' and outer vlan'
                        ;
            key 'if-name if-direct inner-vlan outer-vlan'
                ;
            leaf if-name {
              description 'Configure the name of the attaching interface'
                          ;
              type ncd:ifname {
                length 1..31 {
                  description 'Name of the attaching interface, support 1-31 ch'
                            + 'aracters'
                              ;
                }
              }
            }
            leaf if-direct {
              description 'Specify the direction of interface, as follows,'+"\n"
                        + '     input  Rate limit on input'+"\n"
                        + '     output Rate limit on output'
                          ;
              type enumeration {
                enum input {
                  value 1 ;
                  description 'Rate limit on input'
                              ;
                }
                enum output {
                  value 2 ;
                  description 'Rate limit on output'
                              ;
                }
              }
            }
            leaf inner-vlan {
              description 'Configure inner-VLAN value in range mode, support si'
                        + 'ngle inner-VLAN value or range(max num:4;spacing mar'
                        + 'k:,) in <1-4094>. For example,"1,300-400,1000,2000-4'
                        + '000",etc.'
                          ;
              type qos-vlan-range ;
            }
            leaf outer-vlan {
              description 'Configure outer-VLAN value in range mode, support si'
                        + 'ngle outer-VLAN value or range(max num:4;spacing mar'
                        + 'k:,) in <1-4094>. For example,"1,300-400,1000,2000-4'
                        + '000",etc.'
                          ;
              type qos-vlan-range ;
            }
            leaf rate-limit-desc {
              description 'Description of rate limit, support 1-79 characters.'
                          ;
              type ncd:string-with-blank {
                length 1..79 {
                  description 'Description of rate limit, support 1-79 characte'
                            + 'rs.'
                              ;
                }
              }
              ncd:revise-date 2020-06-18 ;
            }
            choice unit-style {
              description "Specify unit's style"
                          ;
              mandatory true ;
              case unit-value {
                description 'Configure the value style'
                            ;
                leaf cir {
                  description 'Configure the CIR(Committed Information Rate) va'
                            + 'lue (default: kilobits per second)'
                              ;
                  type uint32 {
                    range 8..4294967295 {
                      description 'The CIR value (default: kilobits per second)'
                                + ',support <8-4294967295>'
                                  ;
                    }
                  }
                  mandatory true ;
                }
                leaf cir-unit {
                  description 'set cir unit, such as kbps, mbps, gbps'
                              ;
                  type qos-rate-unit-type ;
                }
                leaf cbs {
                  description 'Configure the CBS(Committed Burst Size) size in '
                            + 'bytes.'
                              ;
                  type uint32 {
                    range 1..4294967295 {
                      description 'The CBS(Committed Burst Size) size in bytes,'
                                + ' support <1-4294967295>.'
                                  ;
                    }
                  }
                  units byte ;
                }
                leaf pir {
                  description 'Configure the PIR(Peak Information Rate) value ('
                            + 'default: kilobits per second)'
                              ;
                  type uint32 {
                    range 8..4294967295 {
                      description 'The PIR(Peak Information Rate) value (defaul'
                                + 't: kilobits per second), support <8-42949672'
                                + '95>'
                                  ;
                    }
                  }
                  mandatory true ;
                }
                leaf pir-unit {
                  description 'set pir unit, such as kbps, mbps, gbps'
                              ;
                  type qos-rate-unit-type ;
                }
                leaf pbs {
                  description 'Configure the PBS(Peak Burst Size) size in bytes.'
                              ;
                  type uint32 {
                    range 1..4294967295 {
                      description 'The PBS(Peak Burst Size) size in KB, support'
                                + ' <1-4294967295>'
                                  ;
                    }
                  }
                  units byte ;
                }
              }
              case unit-percentage {
                description 'Configure the percentage style'
                            ;
                leaf cir-percentage {
                  description 'Configure the CIR(Committed Information Rate) pe'
                            + 'rcentage (Set the accuracy rate per hundred (1%)'
                            + ')'
                              ;
                  type uint32 {
                    range 1..100 {
                      description 'The CIR percentage, support <1-100>'
                                  ;
                    }
                  }
                  mandatory true ;
                }
                leaf pir-percentage {
                  description 'Configure the PIR(Peak Information Rate) percent'
                            + 'age (Set the accuracy rate per hundred (1%))'
                              ;
                  type uint32 {
                    range 1..100 {
                      description 'The PIR percentage, support <1-100>'
                                  ;
                    }
                  }
                  mandatory true ;
                }
                ncd:revise-date 2020-12-23 ;
              }
            }
            leaf statistical-share {
              description 'The flag of statistical-share, as follows,'+"\n"
                        + '    ture  Statistical-share is configured'+"\n"
                        + '    false Statistical-share is not configured'
                          ;
              type boolean ;
              default false ;
            }
            leaf token-bucket-id {
              description 'Set token bucket id'
                          ;
              type uint32 {
                range 1..4294967295 {
                  description 'Token bucket id'
                              ;
                }
              }
              ncd:revise-date 2019-10-28 ;
            }
            container mode {
              if-feature qos-car-mode ;
              description 'Set color mode'
                          ;
              presence 'Configure mode information'
                       ;
              leaf mode-type {
                description 'Color mode type, as follows,'+"\n"
                          + '     blind   Color-Blind mode'+"\n"
                          + '     aware   Color-Aware mode'
                            ;
                type enumeration {
                  enum blind {
                    value 1 ;
                    description 'Color-Blind mode'
                                ;
                  }
                  enum aware {
                    value 2 ;
                    description 'Color-Aware mode'
                                ;
                  }
                }
                mandatory true ;
              }
            }
            container conform-action {
              description 'Action to packets that conform to the rate limit'
                          ;
              choice action {
                description 'Specify action to packets that conform to the rate'
                          + ' limit'
                            ;
                mandatory true ;
                case ca-drop {
                  description 'Drop packet in conform-action'
                              ;
                  leaf drop {
                    description 'Specify action to drop packet'
                                ;
                    type empty ;
                    mandatory true ;
                  }
                }
                case ca-transmit {
                  description 'Transmit packet in conform-action'
                              ;
                  leaf transmit {
                    description 'Specify action to transmit packet'
                                ;
                    type empty ;
                    mandatory true ;
                  }
                }
                case ca-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in conform-action, supp'
                                + 'ort <0-7>'
                                  ;
                      type uint8 {
                        range 0..7 {
                          description 'The MPLS-EXP value, support <0-7>'
                                      ;
                        }
                      }
                      mandatory true ;
                    }
                  }
                }
                case ca-precedence {
                  description 'Rewrite packet precedence and transmit the packet'
                              ;
                  container set-prec-transmit {
                    description 'Specify action to rewrite packet precedence an'
                              + 'd transmit it'
                                ;
                    leaf prec-value {
                      description 'Reset the IP-Precedence value in conform-act'
                                + 'ion, support <0-7>'
                                  ;
                      type uint8 {
                        range 0..7 {
                          description 'The IP-Precedence value, support <0-7>'
                                      ;
                        }
                      }
                      mandatory true ;
                    }
                  }
                }
                case ca-dscp {
                  description 'Rewrite packet DSCP and transmit the packet'
                              ;
                  container set-dscp-transmit {
                    description 'Specify action to rewrite packet DSCP and tran'
                              + 'smit it'
                                ;
                    leaf dscp-value {
                      description 'Reset DSCP in conform-action, support <0-63>'
                                  ;
                      type uint8 {
                        range 0..63 {
                          description 'The DSCP value, support <0-63>'
                                      ;
                        }
                      }
                      mandatory true ;
                    }
                  }
                }
                case ca-8021p {
                  description 'Rewrite packet 802.1p and transmit the packet'
                              ;
                  container set-8021p-transmit {
                    description 'Specify action to rewrite packet 802.1p and tr'
                              + 'ansmit it'
                                ;
                    leaf value-8021p {
                      description 'Reset 802.1p in conform-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ca-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ca-service-class {
                  description 'Rewrite packet service class and transmit the pa'
                            + 'cket'
                              ;
                  container set-service-class-transmit {
                    description 'Specify action to rewrite packet service class'
                              + ' and transmit it'
                                ;
                    leaf service-class-value {
                      description 'Reset service class in conform-action'
                                  ;
                      type qos-service-class ;
                      mandatory true ;
                    }
                  }
                  ncd:revise-date 2020-05-18 ;
                }
              }
            }
            container exceed-action {
              description 'Action to packets that exceed the rate limit'
                          ;
              choice action {
                description 'Specify action to packets that exceed the rate lim'
                          + 'it'
                            ;
                mandatory true ;
                case ea-drop {
                  description 'Drop packet in exceed-action'
                              ;
                  leaf drop {
                    description 'Specify action to drop packet'
                                ;
                    type empty ;
                    mandatory true ;
                  }
                }
                case ea-transmit {
                  description 'Transmit packet in exceed-action'
                              ;
                  leaf transmit {
                    description 'Specify action to transmit packet'
                                ;
                    type empty ;
                    mandatory true ;
                  }
                }
                case ea-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in exceed-action, suppo'
                                + 'rt <0-7>'
                                  ;
                      type uint8 {
                        range 0..7 {
                          description 'The MPLS-EXP value, support <0-7>'
                                      ;
                        }
                      }
                      mandatory true ;
                    }
                  }
                }
                case ea-precedence {
                  description 'Rewrite packet precedence and transmit the packet'
                              ;
                  container set-prec-transmit {
                    description 'Specify action to rewrite packet precedence an'
                              + 'd transmit it'
                                ;
                    leaf prec-value {
                      description 'Reset the IP-Precedence value in exceed-acti'
                                + 'on, support <0-7>'
                                  ;
                      type uint8 {
                        range 0..7 {
                          description 'The IP-Precedence value, support <0-7>'
                                      ;
                        }
                      }
                      mandatory true ;
                    }
                  }
                }
                case ea-dscp {
                  description 'Rewrite packet DSCP and transmit the packet'
                              ;
                  container set-dscp-transmit {
                    description 'Specify action to rewrite packet DSCP and tran'
                              + 'smit it'
                                ;
                    leaf dscp-value {
                      description 'Reset DSCP in exceed-action, support <0-63>'
                                  ;
                      type uint8 {
                        range 0..63 {
                          description 'The DSCP value, support <0-63>'
                                      ;
                        }
                      }
                      mandatory true ;
                    }
                  }
                }
                case ea-8021p {
                  description 'Rewrite packet 802.1p and transmit the packet'
                              ;
                  container set-8021p-transmit {
                    description 'Specify action to rewrite packet 802.1p and tr'
                              + 'ansmit it'
                                ;
                    leaf value-8021p {
                      description 'Reset 802.1p in exceed-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ea-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ea-service-class {
                  description 'Rewrite packet DSCP and transmit the packet'
                              ;
                  container set-service-class-transmit {
                    description 'Specify action to rewrite packet service class'
                              + ' and transmit it'
                                ;
                    leaf service-class-value {
                      description 'Reset service class in exceed-action'
                                  ;
                      type qos-service-class ;
                      mandatory true ;
                    }
                  }
                  ncd:revise-date 2020-05-18 ;
                }
              }
            }
            container violate-action {
              description 'Action to packets that violate the rate limit'
                          ;
              choice action {
                description 'Specify action to packets that violate the rate li'
                          + 'mit'
                            ;
                mandatory true ;
                case va-drop {
                  description 'Drop packet in violate-action'
                              ;
                  leaf drop {
                    description 'Specify action to drop packet'
                                ;
                    type empty ;
                    mandatory true ;
                  }
                }
                case va-transmit {
                  description 'Transmit packet in violate-action'
                              ;
                  leaf transmit {
                    description 'Specify action to transmit packet'
                                ;
                    type empty ;
                    mandatory true ;
                  }
                }
                case va-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in violate-action, supp'
                                + 'ort <0-7>'
                                  ;
                      type uint8 {
                        range 0..7 {
                          description 'The MPLS-EXP value, support <0-7>'
                                      ;
                        }
                      }
                      mandatory true ;
                    }
                  }
                }
                case va-precedence {
                  description 'Rewrite packet precedence and transmit the packet'
                              ;
                  container set-prec-transmit {
                    description 'Specify action to rewrite packet precedence an'
                              + 'd transmit it'
                                ;
                    leaf prec-value {
                      description 'Reset the IP-Precedence value in violate-act'
                                + 'ion, support <0-7>'
                                  ;
                      type uint8 {
                        range 0..7 ;
                      }
                      mandatory true ;
                    }
                  }
                }
                case va-dscp {
                  description 'Rewrite packet DSCP and transmit the packet'
                              ;
                  container set-dscp-transmit {
                    description 'Specify action to rewrite packet DSCP and tran'
                              + 'smit it'
                                ;
                    leaf dscp-value {
                      description 'Reset DSCP in violate-action, support <0-63>'
                                  ;
                      type uint8 {
                        range 0..63 {
                          description 'The DSCP value, support <0-63>'
                                      ;
                        }
                      }
                      mandatory true ;
                    }
                  }
                }
                case va-8021p {
                  description 'Rewrite packet 802.1p and transmit the packet'
                              ;
                  container set-8021p-transmit {
                    description 'Specify action to rewrite packet 802.1p and tr'
                              + 'ansmit it'
                                ;
                    leaf value-8021p {
                      description 'Reset 802.1p in violate-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case va-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case va-service-class {
                  description 'Rewrite packet service class and transmit the pa'
                            + 'cket'
                              ;
                  container set-service-class-transmit {
                    description 'Specify action to rewrite packet service class'
                              + ' and transmit it'
                                ;
                    leaf service-class-value {
                      description 'Reset service class in violate-action'
                                  ;
                      type qos-service-class ;
                      mandatory true ;
                    }
                  }
                  ncd:revise-date 2020-05-18 ;
                }
              }
            }
          }
        }
        container inner-8021ps {
          description 'Match inner 802.1p value'
                      ;
          list inner-8021p {
            description 'Configure interface rate limit based on matching inner'
                      + ' 802.1p'
                        ;
            key 'if-name if-direct in-8021p-value'
                ;
            leaf if-name {
              description 'Configure the name of the attaching interface'
                          ;
              type ncd:ifname {
                length 1..31 {
                  description 'Name of the attaching interface, support 1-31 ch'
                            + 'aracters'
                              ;
                }
              }
            }
            leaf if-direct {
              description 'Specify the direction of interface, as follows,'+"\n"
                        + '     input  Rate limit on input'+"\n"
                        + '     output Rate limit on output'
                          ;
              type enumeration {
                enum input {
                  value 1 ;
                  description 'Rate limit on input'
                              ;
                }
                enum output {
                  value 2 ;
                  description 'Rate limit on output'
                              ;
                }
              }
            }
            leaf in-8021p-value {
              description 'Inner 802.1p value, support <0-7>'
                          ;
              type uint32 {
                range 0..7 {
                  description '802.1p value, support <0-7>'
                              ;
                }
              }
            }
            leaf rate-limit-desc {
              description 'Description of rate limit, support 1-79 characters.'
                          ;
              type ncd:string-with-blank {
                length 1..79 {
                  description 'Description of rate limit, support 1-79 characte'
                            + 'rs.'
                              ;
                }
              }
              ncd:revise-date 2020-06-18 ;
            }
            choice unit-style {
              description "Specify unit's style"
                          ;
              mandatory true ;
              case unit-value {
                description 'Configure the value style'
                            ;
                leaf cir {
                  description 'Configure the CIR(Committed Information Rate) va'
                            + 'lue (default: kilobits per second)'
                              ;
                  type uint32 {
                    range 8..4294967295 {
                      description 'The CIR value (default: kilobits per second)'
                                + ',support <8-4294967295>'
                                  ;
                    }
                  }
                  mandatory true ;
                }
                leaf cir-unit {
                  description 'set cir unit, such as kbps, mbps, gbps'
                              ;
                  type qos-rate-unit-type ;
                }
                leaf cbs {
                  description 'Configure the CBS(Committed Burst Size) size in '
                            + 'bytes.'
                              ;
                  type uint32 {
                    range 1..4294967295 {
                      description 'The CBS(Committed Burst Size) size in bytes,'
                                + ' support <1-4294967295>.'
                                  ;
                    }
                  }
                  units byte ;
                }
                leaf pir {
                  description 'Configure the PIR(Peak Information Rate) value ('
                            + 'default: kilobits per second)'
                              ;
                  type uint32 {
                    range 8..4294967295 {
                      description 'The PIR(Peak Information Rate) value (defaul'
                                + 't: kilobits per second), support <8-42949672'
                                + '95>'
                                  ;
                    }
                  }
                  mandatory true ;
                }
                leaf pir-unit {
                  description 'set pir unit, such as kbps, mbps, gbps'
                              ;
                  type qos-rate-unit-type ;
                }
                leaf pbs {
                  description 'Configure the PBS(Peak Burst Size) size in bytes.'
                              ;
                  type uint32 {
                    range 1..4294967295 {
                      description 'The PBS(Peak Burst Size) size in KB, support'
                                + ' <1-4294967295>'
                                  ;
                    }
                  }
                  units byte ;
                }
              }
              case unit-percentage {
                description 'Configure the percentage style'
                            ;
                leaf cir-percentage {
                  description 'Configure the CIR(Committed Information Rate) pe'
                            + 'rcentage (Set the accuracy rate per hundred (1%)'
                            + ')'
                              ;
                  type uint32 {
                    range 1..100 {
                      description 'The CIR percentage, support <1-100>'
                                  ;
                    }
                  }
                  mandatory true ;
                }
                leaf pir-percentage {
                  description 'Configure the PIR(Peak Information Rate) percent'
                            + 'age (Set the accuracy rate per hundred (1%))'
                              ;
                  type uint32 {
                    range 1..100 {
                      description 'The PIR percentage, support <1-100>'
                                  ;
                    }
                  }
                  mandatory true ;
                }
                ncd:revise-date 2020-12-23 ;
              }
            }
            leaf statistical-share {
              description 'The flag of statistical-share, as follows,'+"\n"
                        + '    ture  Statistical-share is configured'+"\n"
                        + '    false Statistical-share is not configured'
                          ;
              type boolean ;
              default false ;
            }
            leaf token-bucket-id {
              description 'Set token bucket id'
                          ;
              type uint32 {
                range 1..4294967295 {
                  description 'Token bucket id'
                              ;
                }
              }
              ncd:revise-date 2019-10-28 ;
            }
            container mode {
              if-feature qos-car-mode ;
              description 'Set color mode'
                          ;
              presence 'Configure mode information'
                       ;
              leaf mode-type {
                description 'Color mode type, as follows,'+"\n"
                          + '     blind   Color-Blind mode'+"\n"
                          + '     aware   Color-Aware mode'
                            ;
                type enumeration {
                  enum blind {
                    value 1 ;
                    description 'Color-Blind mode'
                                ;
                  }
                  enum aware {
                    value 2 ;
                    description 'Color-Aware mode'
                                ;
                  }
                }
                mandatory true ;
              }
            }
            container conform-action {
              description 'Action to packets that conform to the rate limit'
                          ;
              choice action {
                description 'Specify action to packets that conform to the rate'
                          + ' limit'
                            ;
                mandatory true ;
                case ca-drop {
                  description 'Drop packet in conform-action'
                              ;
                  leaf drop {
                    description 'Specify action to drop packet'
                                ;
                    type empty ;
                    mandatory true ;
                  }
                }
                case ca-transmit {
                  description 'Transmit packet in conform-action'
                              ;
                  leaf transmit {
                    description 'Specify action to transmit packet'
                                ;
                    type empty ;
                    mandatory true ;
                  }
                }
                case ca-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in conform-action, supp'
                                + 'ort <0-7>'
                                  ;
                      type uint8 {
                        range 0..7 {
                          description 'The MPLS-EXP value, support <0-7>'
                                      ;
                        }
                      }
                      mandatory true ;
                    }
                  }
                }
                case ca-precedence {
                  description 'Rewrite packet precedence and transmit the packet'
                              ;
                  container set-prec-transmit {
                    description 'Specify action to rewrite packet precedence an'
                              + 'd transmit it'
                                ;
                    leaf prec-value {
                      description 'Reset the IP-Precedence value in conform-act'
                                + 'ion, support <0-7>'
                                  ;
                      type uint8 {
                        range 0..7 {
                          description 'The IP-Precedence value, support <0-7>'
                                      ;
                        }
                      }
                      mandatory true ;
                    }
                  }
                }
                case ca-dscp {
                  description 'Rewrite packet DSCP and transmit the packet'
                              ;
                  container set-dscp-transmit {
                    description 'Specify action to rewrite packet DSCP and tran'
                              + 'smit it'
                                ;
                    leaf dscp-value {
                      description 'Reset DSCP in conform-action, support <0-63>'
                                  ;
                      type uint8 {
                        range 0..63 {
                          description 'The DSCP value, support <0-63>'
                                      ;
                        }
                      }
                      mandatory true ;
                    }
                  }
                }
                case ca-8021p {
                  description 'Rewrite packet 802.1p and transmit the packet'
                              ;
                  container set-8021p-transmit {
                    description 'Specify action to rewrite packet 802.1p and tr'
                              + 'ansmit it'
                                ;
                    leaf value-8021p {
                      description 'Reset 802.1p in conform-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ca-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ca-service-class {
                  description 'Rewrite packet service class and transmit the pa'
                            + 'cket'
                              ;
                  container set-service-class-transmit {
                    description 'Specify action to rewrite packet service class'
                              + ' and transmit it'
                                ;
                    leaf service-class-value {
                      description 'Reset service class in conform-action'
                                  ;
                      type qos-service-class ;
                      mandatory true ;
                    }
                  }
                  ncd:revise-date 2020-05-18 ;
                }
              }
            }
            container exceed-action {
              description 'Action to packets that exceed the rate limit'
                          ;
              choice action {
                description 'Specify action to packets that exceed the rate lim'
                          + 'it'
                            ;
                mandatory true ;
                case ea-drop {
                  description 'Drop packet in exceed-action'
                              ;
                  leaf drop {
                    description 'Specify action to drop packet'
                                ;
                    type empty ;
                    mandatory true ;
                  }
                }
                case ea-transmit {
                  description 'Transmit packet in exceed-action'
                              ;
                  leaf transmit {
                    description 'Specify action to transmit packet'
                                ;
                    type empty ;
                    mandatory true ;
                  }
                }
                case ea-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in exceed-action, suppo'
                                + 'rt <0-7>'
                                  ;
                      type uint8 {
                        range 0..7 {
                          description 'The MPLS-EXP value, support <0-7>'
                                      ;
                        }
                      }
                      mandatory true ;
                    }
                  }
                }
                case ea-precedence {
                  description 'Rewrite packet precedence and transmit the packet'
                              ;
                  container set-prec-transmit {
                    description 'Specify action to rewrite packet precedence an'
                              + 'd transmit it'
                                ;
                    leaf prec-value {
                      description 'Reset the IP-Precedence value in exceed-acti'
                                + 'on, support <0-7>'
                                  ;
                      type uint8 {
                        range 0..7 {
                          description 'The IP-Precedence value, support <0-7>'
                                      ;
                        }
                      }
                      mandatory true ;
                    }
                  }
                }
                case ea-dscp {
                  description 'Rewrite packet DSCP and transmit the packet'
                              ;
                  container set-dscp-transmit {
                    description 'Specify action to rewrite packet DSCP and tran'
                              + 'smit it'
                                ;
                    leaf dscp-value {
                      description 'Reset DSCP in exceed-action, support <0-63>'
                                  ;
                      type uint8 {
                        range 0..63 {
                          description 'The DSCP value, support <0-63>'
                                      ;
                        }
                      }
                      mandatory true ;
                    }
                  }
                }
                case ea-8021p {
                  description 'Rewrite packet 802.1p and transmit the packet'
                              ;
                  container set-8021p-transmit {
                    description 'Specify action to rewrite packet 802.1p and tr'
                              + 'ansmit it'
                                ;
                    leaf value-8021p {
                      description 'Reset 802.1p in exceed-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ea-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ea-service-class {
                  description 'Rewrite packet service class and transmit the pa'
                            + 'cket'
                              ;
                  container set-service-class-transmit {
                    description 'Specify action to rewrite packet service class'
                              + ' and transmit it'
                                ;
                    leaf service-class-value {
                      description 'Reset service class in exceed-action'
                                  ;
                      type qos-service-class ;
                      mandatory true ;
                    }
                  }
                  ncd:revise-date 2020-05-18 ;
                }
              }
            }
            container violate-action {
              description 'Action to packets that violate the rate limit'
                          ;
              choice action {
                description 'Specify action to packets that violate the rate li'
                          + 'mit'
                            ;
                mandatory true ;
                case va-drop {
                  description 'Drop packet in violate-action'
                              ;
                  leaf drop {
                    description 'Specify action to drop packet'
                                ;
                    type empty ;
                    mandatory true ;
                  }
                }
                case va-transmit {
                  description 'Transmit packet in violate-action'
                              ;
                  leaf transmit {
                    description 'Specify action to transmit packet'
                                ;
                    type empty ;
                    mandatory true ;
                  }
                }
                case va-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in violate-action, supp'
                                + 'ort <0-7>'
                                  ;
                      type uint8 {
                        range 0..7 {
                          description 'The MPLS-EXP value, support <0-7>'
                                      ;
                        }
                      }
                      mandatory true ;
                    }
                  }
                }
                case va-precedence {
                  description 'Rewrite packet precedence and transmit the packet'
                              ;
                  container set-prec-transmit {
                    description 'Specify action to rewrite packet precedence an'
                              + 'd transmit it'
                                ;
                    leaf prec-value {
                      description 'Reset the IP-Precedence value in violate-act'
                                + 'ion, support <0-7>'
                                  ;
                      type uint8 {
                        range 0..7 ;
                      }
                      mandatory true ;
                    }
                  }
                }
                case va-dscp {
                  description 'Rewrite packet DSCP and transmit the packet'
                              ;
                  container set-dscp-transmit {
                    description 'Specify action to rewrite packet DSCP and tran'
                              + 'smit it'
                                ;
                    leaf dscp-value {
                      description 'Reset DSCP in violate-action, support <0-63>'
                                  ;
                      type uint8 {
                        range 0..63 {
                          description 'The DSCP value, support <0-63>'
                                      ;
                        }
                      }
                      mandatory true ;
                    }
                  }
                }
                case va-8021p {
                  description 'Rewrite packet 802.1p and transmit the packet'
                              ;
                  container set-8021p-transmit {
                    description 'Specify action to rewrite packet 802.1p and tr'
                              + 'ansmit it'
                                ;
                    leaf value-8021p {
                      description 'Reset 802.1p in violate-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case va-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case va-service-class {
                  description 'Rewrite packet service class and transmit the pa'
                            + 'cket'
                              ;
                  container set-service-class-transmit {
                    description 'Specify action to rewrite packet service class'
                              + ' and transmit it'
                                ;
                    leaf service-class-value {
                      description 'Reset service class in violate-action'
                                  ;
                      type qos-service-class ;
                      mandatory true ;
                    }
                  }
                  ncd:revise-date 2020-05-18 ;
                }
              }
            }
          }
        }
        container outer-8021ps {
          description 'Match outer 802.1p value'
                      ;
          list outer-8021p {
            description 'Configure interface rate limit based on matching outer'
                      + ' 802.1p'
                        ;
            key 'if-name if-direct out-8021p-value'
                ;
            leaf if-name {
              description 'Configure the name of the attaching interface'
                          ;
              type ncd:ifname {
                length 1..31 {
                  description 'Name of the attaching interface, support 1-31 ch'
                            + 'aracters'
                              ;
                }
              }
            }
            leaf if-direct {
              description 'Specify the direction of interface, as follows,'+"\n"
                        + '     input  Rate limit on input'+"\n"
                        + '     output Rate limit on output'
                          ;
              type enumeration {
                enum input {
                  value 1 ;
                  description 'Rate limit on input'
                              ;
                }
                enum output {
                  value 2 ;
                  description 'Rate limit on output'
                              ;
                }
              }
            }
            leaf out-8021p-value {
              description 'Outer 802.1p value, support <0-7>'
                          ;
              type uint32 {
                range 0..7 {
                  description '802.1p value, support <0-7>'
                              ;
                }
              }
            }
            leaf rate-limit-desc {
              description 'Description of rate limit, support 1-79 characters.'
                          ;
              type ncd:string-with-blank {
                length 1..79 {
                  description 'Description of rate limit, support 1-79 characte'
                            + 'rs.'
                              ;
                }
              }
              ncd:revise-date 2020-06-18 ;
            }
            choice unit-style {
              description "Specify unit's style"
                          ;
              mandatory true ;
              case unit-value {
                description 'Configure the value style'
                            ;
                leaf cir {
                  description 'Configure the CIR(Committed Information Rate) va'
                            + 'lue (default: kilobits per second)'
                              ;
                  type uint32 {
                    range 8..4294967295 {
                      description 'The CIR value (default: kilobits per second)'
                                + ',support <8-4294967295>'
                                  ;
                    }
                  }
                  mandatory true ;
                }
                leaf cir-unit {
                  description 'set cir unit, such as kbps, mbps, gbps'
                              ;
                  type qos-rate-unit-type ;
                }
                leaf cbs {
                  description 'Configure the CBS(Committed Burst Size) size in '
                            + 'bytes.'
                              ;
                  type uint32 {
                    range 1..4294967295 {
                      description 'The CBS(Committed Burst Size) size in bytes,'
                                + ' support <1-4294967295>.'
                                  ;
                    }
                  }
                  units byte ;
                }
                leaf pir {
                  description 'Configure the PIR(Peak Information Rate) value ('
                            + 'default: kilobits per second)'
                              ;
                  type uint32 {
                    range 8..4294967295 {
                      description 'The PIR(Peak Information Rate) value (defaul'
                                + 't: kilobits per second), support <8-42949672'
                                + '95>'
                                  ;
                    }
                  }
                  mandatory true ;
                }
                leaf pir-unit {
                  description 'set pir unit, such as kbps, mbps, gbps'
                              ;
                  type qos-rate-unit-type ;
                }
                leaf pbs {
                  description 'Configure the PBS(Peak Burst Size) size in bytes.'
                              ;
                  type uint32 {
                    range 1..4294967295 {
                      description 'The PBS(Peak Burst Size) size in KB, support'
                                + ' <1-4294967295>'
                                  ;
                    }
                  }
                  units byte ;
                }
              }
              case unit-percentage {
                description 'Configure the percentage style'
                            ;
                leaf cir-percentage {
                  description 'Configure the CIR(Committed Information Rate) pe'
                            + 'rcentage (Set the accuracy rate per hundred (1%)'
                            + ')'
                              ;
                  type uint32 {
                    range 1..100 {
                      description 'The CIR percentage, support <1-100>'
                                  ;
                    }
                  }
                  mandatory true ;
                }
                leaf pir-percentage {
                  description 'Configure the PIR(Peak Information Rate) percent'
                            + 'age (Set the accuracy rate per hundred (1%))'
                              ;
                  type uint32 {
                    range 1..100 {
                      description 'The PIR percentage, support <1-100>'
                                  ;
                    }
                  }
                  mandatory true ;
                }
                ncd:revise-date 2020-12-23 ;
              }
            }
            leaf statistical-share {
              description 'The flag of statistical-share, as follows,'+"\n"
                        + '    ture  Statistical-share is configured'+"\n"
                        + '    false Statistical-share is not configured'
                          ;
              type boolean ;
              default false ;
            }
            leaf token-bucket-id {
              description 'Set token bucket id'
                          ;
              type uint32 {
                range 1..4294967295 {
                  description 'Token bucket id'
                              ;
                }
              }
              ncd:revise-date 2019-10-28 ;
            }
            container mode {
              if-feature qos-car-mode ;
              description 'Set color mode'
                          ;
              presence 'Configure mode information'
                       ;
              leaf mode-type {
                description 'Color mode type, as follows,'+"\n"
                          + '     blind   Color-Blind mode'+"\n"
                          + '     aware   Color-Aware mode'
                            ;
                type enumeration {
                  enum blind {
                    value 1 ;
                    description 'Color-Blind mode'
                                ;
                  }
                  enum aware {
                    value 2 ;
                    description 'Color-Aware mode'
                                ;
                  }
                }
                mandatory true ;
              }
            }
            container conform-action {
              description 'Action to packets that conform to the rate limit'
                          ;
              choice action {
                description 'Specify action to packets that conform to the rate'
                          + ' limit'
                            ;
                mandatory true ;
                case ca-drop {
                  description 'Drop packet in conform-action'
                              ;
                  leaf drop {
                    description 'Specify action to drop packet'
                                ;
                    type empty ;
                    mandatory true ;
                  }
                }
                case ca-transmit {
                  description 'Transmit packet in conform-action'
                              ;
                  leaf transmit {
                    description 'Specify action to transmit packet'
                                ;
                    type empty ;
                    mandatory true ;
                  }
                }
                case ca-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in conform-action, supp'
                                + 'ort <0-7>'
                                  ;
                      type uint8 {
                        range 0..7 {
                          description 'The MPLS-EXP value, support <0-7>'
                                      ;
                        }
                      }
                      mandatory true ;
                    }
                  }
                }
                case ca-precedence {
                  description 'Rewrite packet precedence and transmit the packet'
                              ;
                  container set-prec-transmit {
                    description 'Specify action to rewrite packet precedence an'
                              + 'd transmit it'
                                ;
                    leaf prec-value {
                      description 'Reset the IP-Precedence value in conform-act'
                                + 'ion, support <0-7>'
                                  ;
                      type uint8 {
                        range 0..7 {
                          description 'The IP-Precedence value, support <0-7>'
                                      ;
                        }
                      }
                      mandatory true ;
                    }
                  }
                }
                case ca-dscp {
                  description 'Rewrite packet DSCP and transmit the packet'
                              ;
                  container set-dscp-transmit {
                    description 'Specify action to rewrite packet DSCP and tran'
                              + 'smit it'
                                ;
                    leaf dscp-value {
                      description 'Reset DSCP in conform-action, support <0-63>'
                                  ;
                      type uint8 {
                        range 0..63 {
                          description 'The DSCP value, support <0-63>'
                                      ;
                        }
                      }
                      mandatory true ;
                    }
                  }
                }
                case ca-8021p {
                  description 'Rewrite packet 802.1p and transmit the packet'
                              ;
                  container set-8021p-transmit {
                    description 'Specify action to rewrite packet 802.1p and tr'
                              + 'ansmit it'
                                ;
                    leaf value-8021p {
                      description 'Reset 802.1p in conform-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ca-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ca-service-class {
                  description 'Rewrite packet service class and transmit the pa'
                            + 'cket'
                              ;
                  container set-service-class-transmit {
                    description 'Specify action to rewrite packet service class'
                              + ' and transmit it'
                                ;
                    leaf service-class-value {
                      description 'Reset service class in conform-action'
                                  ;
                      type qos-service-class ;
                      mandatory true ;
                    }
                  }
                  ncd:revise-date 2020-05-18 ;
                }
              }
            }
            container exceed-action {
              description 'Action to packets that exceed the rate limit'
                          ;
              choice action {
                description 'Specify action to packets that exceed the rate lim'
                          + 'it'
                            ;
                mandatory true ;
                case ea-drop {
                  description 'Drop packet in exceed-action'
                              ;
                  leaf drop {
                    description 'Specify action to drop packet'
                                ;
                    type empty ;
                    mandatory true ;
                  }
                }
                case ea-transmit {
                  description 'Transmit packet in exceed-action'
                              ;
                  leaf transmit {
                    description 'Specify action to transmit packet'
                                ;
                    type empty ;
                    mandatory true ;
                  }
                }
                case ea-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in exceed-action, suppo'
                                + 'rt <0-7>'
                                  ;
                      type uint8 {
                        range 0..7 {
                          description 'The MPLS-EXP value, support <0-7>'
                                      ;
                        }
                      }
                      mandatory true ;
                    }
                  }
                }
                case ea-precedence {
                  description 'Rewrite packet precedence and transmit the packet'
                              ;
                  container set-prec-transmit {
                    description 'Specify action to rewrite packet precedence an'
                              + 'd transmit it'
                                ;
                    leaf prec-value {
                      description 'Reset the IP-Precedence value in exceed-acti'
                                + 'on, support <0-7>'
                                  ;
                      type uint8 {
                        range 0..7 {
                          description 'The IP-Precedence value, support <0-7>'
                                      ;
                        }
                      }
                      mandatory true ;
                    }
                  }
                }
                case ea-dscp {
                  description 'Rewrite packet DSCP and transmit the packet'
                              ;
                  container set-dscp-transmit {
                    description 'Specify action to rewrite packet DSCP and tran'
                              + 'smit it'
                                ;
                    leaf dscp-value {
                      description 'Reset DSCP in exceed-action, support <0-63>'
                                  ;
                      type uint8 {
                        range 0..63 {
                          description 'The DSCP value, support <0-63>'
                                      ;
                        }
                      }
                      mandatory true ;
                    }
                  }
                }
                case ea-8021p {
                  description 'Rewrite packet 802.1p and transmit the packet'
                              ;
                  container set-8021p-transmit {
                    description 'Specify action to rewrite packet 802.1p and tr'
                              + 'ansmit it'
                                ;
                    leaf value-8021p {
                      description 'Reset 802.1p in exceed-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ea-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ea-service-class {
                  description 'Rewrite packet service class and transmit the pa'
                            + 'cket'
                              ;
                  container set-service-class-transmit {
                    description 'Specify action to rewrite packet service class'
                              + ' and transmit it'
                                ;
                    leaf service-class-value {
                      description 'Reset service class in exceed-action'
                                  ;
                      type qos-service-class ;
                      mandatory true ;
                    }
                  }
                  ncd:revise-date 2020-05-18 ;
                }
              }
            }
            container violate-action {
              description 'Action to packets that violate the rate limit'
                          ;
              choice action {
                description 'Specify action to packets that violate the rate li'
                          + 'mit'
                            ;
                mandatory true ;
                case va-drop {
                  description 'Drop packet in violate-action'
                              ;
                  leaf drop {
                    description 'Specify action to drop packet'
                                ;
                    type empty ;
                    mandatory true ;
                  }
                }
                case va-transmit {
                  description 'Transmit packet in violate-action'
                              ;
                  leaf transmit {
                    description 'Specify action to transmit packet'
                                ;
                    type empty ;
                    mandatory true ;
                  }
                }
                case va-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in violate-action, supp'
                                + 'ort <0-7>'
                                  ;
                      type uint8 {
                        range 0..7 {
                          description 'The MPLS-EXP value, support <0-7>'
                                      ;
                        }
                      }
                      mandatory true ;
                    }
                  }
                }
                case va-precedence {
                  description 'Rewrite packet precedence and transmit the packet'
                              ;
                  container set-prec-transmit {
                    description 'Specify action to rewrite packet precedence an'
                              + 'd transmit it'
                                ;
                    leaf prec-value {
                      description 'Reset the IP-Precedence value in violate-act'
                                + 'ion, support <0-7>'
                                  ;
                      type uint8 {
                        range 0..7 ;
                      }
                      mandatory true ;
                    }
                  }
                }
                case va-dscp {
                  description 'Rewrite packet DSCP and transmit the packet'
                              ;
                  container set-dscp-transmit {
                    description 'Specify action to rewrite packet DSCP and tran'
                              + 'smit it'
                                ;
                    leaf dscp-value {
                      description 'Reset DSCP in violate-action, support <0-63>'
                                  ;
                      type uint8 {
                        range 0..63 {
                          description 'The DSCP value, support <0-63>'
                                      ;
                        }
                      }
                      mandatory true ;
                    }
                  }
                }
                case va-8021p {
                  description 'Rewrite packet 802.1p and transmit the packet'
                              ;
                  container set-8021p-transmit {
                    description 'Specify action to rewrite packet 802.1p and tr'
                              + 'ansmit it'
                                ;
                    leaf value-8021p {
                      description 'Reset 802.1p in violate-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case va-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case va-service-class {
                  description 'Rewrite packet service class and transmit the pa'
                            + 'cket'
                              ;
                  container set-service-class-transmit {
                    description 'Specify action to rewrite packet service class'
                              + ' and transmit it'
                                ;
                    leaf service-class-value {
                      description 'Reset service class in violate-action'
                                  ;
                      type qos-service-class ;
                      mandatory true ;
                    }
                  }
                  ncd:revise-date 2020-05-18 ;
                }
              }
            }
          }
        }
        container multi-8021ps {
          description 'Match inner and outer 802.1p value'
                      ;
          list multi-8021p {
            description 'Configure interface rate limit based on matching inner'
                      + ' and outer 802.1p'
                        ;
            key 'if-name if-direct in-8021p-value out-8021p-value'
                ;
            leaf if-name {
              description 'Configure the name of the attaching interface'
                          ;
              type ncd:ifname {
                length 1..31 {
                  description 'Name of the attaching interface, support 1-31 ch'
                            + 'aracters'
                              ;
                }
              }
            }
            leaf if-direct {
              description 'Specify the direction of interface, as follows,'+"\n"
                        + '     input  Rate limit on input'+"\n"
                        + '     output Rate limit on output'
                          ;
              type enumeration {
                enum input {
                  value 1 ;
                  description 'Rate limit on input'
                              ;
                }
                enum output {
                  value 2 ;
                  description 'Rate limit on output'
                              ;
                }
              }
            }
            leaf in-8021p-value {
              description 'Inner 802.1p value, support <0-7>'
                          ;
              type uint32 {
                range 0..7 {
                  description '802.1p value, support <0-7>'
                              ;
                }
              }
            }
            leaf out-8021p-value {
              description 'Outer 802.1p value, support <0-7>'
                          ;
              type uint32 {
                range 0..7 {
                  description '802.1p value, support <0-7>'
                              ;
                }
              }
            }
            leaf rate-limit-desc {
              description 'Description of rate limit, support 1-79 characters.'
                          ;
              type ncd:string-with-blank {
                length 1..79 {
                  description 'Description of rate limit, support 1-79 characte'
                            + 'rs.'
                              ;
                }
              }
              ncd:revise-date 2020-06-18 ;
            }
            choice unit-style {
              description "Specify unit's style"
                          ;
              mandatory true ;
              case unit-value {
                description 'Configure the value style'
                            ;
                leaf cir {
                  description 'Configure the CIR(Committed Information Rate) va'
                            + 'lue (default: kilobits per second)'
                              ;
                  type uint32 {
                    range 8..4294967295 {
                      description 'The CIR value (default: kilobits per second)'
                                + ',support <8-4294967295>'
                                  ;
                    }
                  }
                  mandatory true ;
                }
                leaf cir-unit {
                  description 'set cir unit, such as kbps, mbps, gbps'
                              ;
                  type qos-rate-unit-type ;
                }
                leaf cbs {
                  description 'Configure the CBS(Committed Burst Size) size in '
                            + 'bytes.'
                              ;
                  type uint32 {
                    range 1..4294967295 {
                      description 'The CBS(Committed Burst Size) size in bytes,'
                                + ' support <1-4294967295>.'
                                  ;
                    }
                  }
                  units byte ;
                }
                leaf pir {
                  description 'Configure the PIR(Peak Information Rate) value ('
                            + 'default: kilobits per second)'
                              ;
                  type uint32 {
                    range 8..4294967295 {
                      description 'The PIR(Peak Information Rate) value (defaul'
                                + 't: kilobits per second), support <8-42949672'
                                + '95>'
                                  ;
                    }
                  }
                  mandatory true ;
                }
                leaf pir-unit {
                  description 'set pir unit, such as kbps, mbps, gbps'
                              ;
                  type qos-rate-unit-type ;
                }
                leaf pbs {
                  description 'Configure the PBS(Peak Burst Size) size in bytes.'
                              ;
                  type uint32 {
                    range 1..4294967295 {
                      description 'The PBS(Peak Burst Size) size in KB, support'
                                + ' <1-4294967295>'
                                  ;
                    }
                  }
                  units byte ;
                }
              }
              case unit-percentage {
                description 'Configure the percentage style'
                            ;
                leaf cir-percentage {
                  description 'Configure the CIR(Committed Information Rate) pe'
                            + 'rcentage (Set the accuracy rate per hundred (1%)'
                            + ')'
                              ;
                  type uint32 {
                    range 1..100 {
                      description 'The CIR percentage, support <1-100>'
                                  ;
                    }
                  }
                  mandatory true ;
                }
                leaf pir-percentage {
                  description 'Configure the PIR(Peak Information Rate) percent'
                            + 'age (Set the accuracy rate per hundred (1%))'
                              ;
                  type uint32 {
                    range 1..100 {
                      description 'The PIR percentage, support <1-100>'
                                  ;
                    }
                  }
                  mandatory true ;
                }
                ncd:revise-date 2020-12-23 ;
              }
            }
            leaf statistical-share {
              description 'The flag of statistical-share, as follows,'+"\n"
                        + '    ture  Statistical-share is configured'+"\n"
                        + '    false Statistical-share is not configured'
                          ;
              type boolean ;
              default false ;
            }
            leaf token-bucket-id {
              description 'Set token bucket id'
                          ;
              type uint32 {
                range 1..4294967295 {
                  description 'Token bucket id'
                              ;
                }
              }
              ncd:revise-date 2019-10-28 ;
            }
            container mode {
              if-feature qos-car-mode ;
              description 'Set color mode'
                          ;
              presence 'Configure mode information'
                       ;
              leaf mode-type {
                description 'Color mode type, as follows,'+"\n"
                          + '     blind   Color-Blind mode'+"\n"
                          + '     aware   Color-Aware mode'
                            ;
                type enumeration {
                  enum blind {
                    value 1 ;
                    description 'Color-Blind mode'
                                ;
                  }
                  enum aware {
                    value 2 ;
                    description 'Color-Aware mode'
                                ;
                  }
                }
                mandatory true ;
              }
            }
            container conform-action {
              description 'Action to packets that conform to the rate limit'
                          ;
              choice action {
                description 'Specify action to packets that conform to the rate'
                          + ' limit'
                            ;
                mandatory true ;
                case ca-drop {
                  description 'Drop packet in conform-action'
                              ;
                  leaf drop {
                    description 'Specify action to drop packet'
                                ;
                    type empty ;
                    mandatory true ;
                  }
                }
                case ca-transmit {
                  description 'Transmit packet in conform-action'
                              ;
                  leaf transmit {
                    description 'Specify action to transmit packet'
                                ;
                    type empty ;
                    mandatory true ;
                  }
                }
                case ca-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in conform-action, supp'
                                + 'ort <0-7>'
                                  ;
                      type uint8 {
                        range 0..7 {
                          description 'The MPLS-EXP value, support <0-7>'
                                      ;
                        }
                      }
                      mandatory true ;
                    }
                  }
                }
                case ca-precedence {
                  description 'Rewrite packet precedence and transmit the packet'
                              ;
                  container set-prec-transmit {
                    description 'Specify action to rewrite packet precedence an'
                              + 'd transmit it'
                                ;
                    leaf prec-value {
                      description 'Reset the IP-Precedence value in conform-act'
                                + 'ion, support <0-7>'
                                  ;
                      type uint8 {
                        range 0..7 {
                          description 'The IP-Precedence value, support <0-7>'
                                      ;
                        }
                      }
                      mandatory true ;
                    }
                  }
                }
                case ca-dscp {
                  description 'Rewrite packet DSCP and transmit the packet'
                              ;
                  container set-dscp-transmit {
                    description 'Specify action to rewrite packet DSCP and tran'
                              + 'smit it'
                                ;
                    leaf dscp-value {
                      description 'Reset DSCP in conform-action, support <0-63>'
                                  ;
                      type uint8 {
                        range 0..63 {
                          description 'The DSCP value, support <0-63>'
                                      ;
                        }
                      }
                      mandatory true ;
                    }
                  }
                }
                case ca-8021p {
                  description 'Rewrite packet 802.1p and transmit the packet'
                              ;
                  container set-8021p-transmit {
                    description 'Specify action to rewrite packet 802.1p and tr'
                              + 'ansmit it'
                                ;
                    leaf value-8021p {
                      description 'Reset 802.1p in conform-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ca-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ca-service-class {
                  description 'Rewrite packet service class and transmit the pa'
                            + 'cket'
                              ;
                  container set-service-class-transmit {
                    description 'Specify action to rewrite packet service class'
                              + ' and transmit it'
                                ;
                    leaf service-class-value {
                      description 'Reset service class in conform-action'
                                  ;
                      type qos-service-class ;
                      mandatory true ;
                    }
                  }
                  ncd:revise-date 2020-05-18 ;
                }
              }
            }
            container exceed-action {
              description 'Action to packets that exceed the rate limit'
                          ;
              choice action {
                description 'Specify action to packets that exceed the rate lim'
                          + 'it'
                            ;
                mandatory true ;
                case ea-drop {
                  description 'Drop packet in exceed-action'
                              ;
                  leaf drop {
                    description 'Specify action to drop packet'
                                ;
                    type empty ;
                    mandatory true ;
                  }
                }
                case ea-transmit {
                  description 'Transmit packet in exceed-action'
                              ;
                  leaf transmit {
                    description 'Specify action to transmit packet'
                                ;
                    type empty ;
                    mandatory true ;
                  }
                }
                case ea-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in exceed-action, suppo'
                                + 'rt <0-7>'
                                  ;
                      type uint8 {
                        range 0..7 {
                          description 'The MPLS-EXP value, support <0-7>'
                                      ;
                        }
                      }
                      mandatory true ;
                    }
                  }
                }
                case ea-precedence {
                  description 'Rewrite packet precedence and transmit the packet'
                              ;
                  container set-prec-transmit {
                    description 'Specify action to rewrite packet precedence an'
                              + 'd transmit it'
                                ;
                    leaf prec-value {
                      description 'Reset the IP-Precedence value in exceed-acti'
                                + 'on, support <0-7>'
                                  ;
                      type uint8 {
                        range 0..7 {
                          description 'The IP-Precedence value, support <0-7>'
                                      ;
                        }
                      }
                      mandatory true ;
                    }
                  }
                }
                case ea-dscp {
                  description 'Rewrite packet DSCP and transmit the packet'
                              ;
                  container set-dscp-transmit {
                    description 'Specify action to rewrite packet DSCP and tran'
                              + 'smit it'
                                ;
                    leaf dscp-value {
                      description 'Reset DSCP in exceed-action, support <0-63>'
                                  ;
                      type uint8 {
                        range 0..63 {
                          description 'The DSCP value, support <0-63>'
                                      ;
                        }
                      }
                      mandatory true ;
                    }
                  }
                }
                case ea-8021p {
                  description 'Rewrite packet 802.1p and transmit the packet'
                              ;
                  container set-8021p-transmit {
                    description 'Specify action to rewrite packet 802.1p and tr'
                              + 'ansmit it'
                                ;
                    leaf value-8021p {
                      description 'Reset 802.1p in exceed-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ea-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ea-service-class {
                  description 'Rewrite packet service class and transmit the pa'
                            + 'cket'
                              ;
                  container set-service-class-transmit {
                    description 'Specify action to rewrite packet service class'
                              + ' and transmit it'
                                ;
                    leaf service-class-value {
                      description 'Reset service class in exceed-action'
                                  ;
                      type qos-service-class ;
                      mandatory true ;
                    }
                  }
                  ncd:revise-date 2020-05-18 ;
                }
              }
            }
            container violate-action {
              description 'Action to packets that violate the rate limit'
                          ;
              choice action {
                description 'Specify action to packets that violate the rate li'
                          + 'mit'
                            ;
                mandatory true ;
                case va-drop {
                  description 'Drop packet in violate-action'
                              ;
                  leaf drop {
                    description 'Specify action to drop packet'
                                ;
                    type empty ;
                    mandatory true ;
                  }
                }
                case va-transmit {
                  description 'Transmit packet in violate-action'
                              ;
                  leaf transmit {
                    description 'Specify action to transmit packet'
                                ;
                    type empty ;
                    mandatory true ;
                  }
                }
                case va-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in violate-action, supp'
                                + 'ort <0-7>'
                                  ;
                      type uint8 {
                        range 0..7 {
                          description 'The MPLS-EXP value, support <0-7>'
                                      ;
                        }
                      }
                      mandatory true ;
                    }
                  }
                }
                case va-precedence {
                  description 'Rewrite packet precedence and transmit the packet'
                              ;
                  container set-prec-transmit {
                    description 'Specify action to rewrite packet precedence an'
                              + 'd transmit it'
                                ;
                    leaf prec-value {
                      description 'Reset the IP-Precedence value in violate-act'
                                + 'ion, support <0-7>'
                                  ;
                      type uint8 {
                        range 0..7 ;
                      }
                      mandatory true ;
                    }
                  }
                }
                case va-dscp {
                  description 'Rewrite packet DSCP and transmit the packet'
                              ;
                  container set-dscp-transmit {
                    description 'Specify action to rewrite packet DSCP and tran'
                              + 'smit it'
                                ;
                    leaf dscp-value {
                      description 'Reset DSCP in violate-action, support <0-63>'
                                  ;
                      type uint8 {
                        range 0..63 {
                          description 'The DSCP value, support <0-63>'
                                      ;
                        }
                      }
                      mandatory true ;
                    }
                  }
                }
                case va-8021p {
                  description 'Rewrite packet 802.1p and transmit the packet'
                              ;
                  container set-8021p-transmit {
                    description 'Specify action to rewrite packet 802.1p and tr'
                              + 'ansmit it'
                                ;
                    leaf value-8021p {
                      description 'Reset 802.1p in violate-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case va-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case va-service-class {
                  description 'Rewrite packet service class and transmit the pa'
                            + 'cket'
                              ;
                  container set-service-class-transmit {
                    description 'Specify action to rewrite packet service class'
                              + ' and transmit it'
                                ;
                    leaf service-class-value {
                      description 'Reset service-class in violate-action'
                                  ;
                      type qos-service-class ;
                      mandatory true ;
                    }
                  }
                  ncd:revise-date 2020-05-18 ;
                }
              }
            }
          }
        }
        container qos-groups {
          description 'Match qos-group number'
                      ;
          list qos-group {
            description 'Configure interface rate limit based on matching qos g'
                      + 'roup'
                        ;
            key 'if-name if-direct qos-id'
                ;
            leaf if-name {
              description 'Configure the name of the attaching interface'
                          ;
              type ncd:ifname {
                length 1..31 {
                  description 'Name of the attaching interface, support 1-31 ch'
                            + 'aracters'
                              ;
                }
              }
            }
            leaf if-direct {
              description 'Specify the direction of interface, as follows,'+"\n"
                        + '     input  Rate limit on input'+"\n"
                        + '     output Rate limit on output'
                          ;
              type enumeration {
                enum input {
                  value 1 ;
                  description 'Rate limit on input'
                              ;
                }
                enum output {
                  value 2 ;
                  description 'Rate limit on output'
                              ;
                }
              }
            }
            leaf qos-id {
              description 'Qos group number,support <1-16000>'
                          ;
              type uint32 {
                range 1..16000 {
                  description 'Qos group number,support <1-16000>'
                              ;
                }
              }
            }
            leaf rate-limit-desc {
              description 'Description of rate limit, support 1-79 characters.'
                          ;
              type ncd:string-with-blank {
                length 1..79 {
                  description 'Description of rate limit, support 1-79 characte'
                            + 'rs.'
                              ;
                }
              }
              ncd:revise-date 2020-06-18 ;
            }
            choice unit-style {
              description "Specify unit's style"
                          ;
              mandatory true ;
              case unit-value {
                description 'Configure the value style'
                            ;
                leaf cir {
                  description 'Configure the CIR(Committed Information Rate) va'
                            + 'lue (default: kilobits per second)'
                              ;
                  type uint32 {
                    range 8..4294967295 {
                      description 'The CIR value (default: kilobits per second)'
                                + ',support <8-4294967295>'
                                  ;
                    }
                  }
                  mandatory true ;
                }
                leaf cir-unit {
                  description 'set cir unit, such as kbps, mbps, gbps'
                              ;
                  type qos-rate-unit-type ;
                }
                leaf cbs {
                  description 'Configure the CBS(Committed Burst Size) size in '
                            + 'bytes.'
                              ;
                  type uint32 {
                    range 1..4294967295 {
                      description 'The CBS(Committed Burst Size) size in bytes,'
                                + ' support <1-4294967295>.'
                                  ;
                    }
                  }
                  units byte ;
                }
                leaf pir {
                  description 'Configure the PIR(Peak Information Rate) value ('
                            + 'default: kilobits per second)'
                              ;
                  type uint32 {
                    range 8..4294967295 {
                      description 'The PIR(Peak Information Rate) value (defaul'
                                + 't: kilobits per second), support <8-42949672'
                                + '95>'
                                  ;
                    }
                  }
                  mandatory true ;
                }
                leaf pir-unit {
                  description 'set pir unit, such as kbps, mbps, gbps'
                              ;
                  type qos-rate-unit-type ;
                }
                leaf pbs {
                  description 'Configure the PBS(Peak Burst Size) size in bytes.'
                              ;
                  type uint32 {
                    range 1..4294967295 {
                      description 'The PBS(Peak Burst Size) size in KB, support'
                                + ' <1-4294967295>'
                                  ;
                    }
                  }
                  units byte ;
                }
              }
              case unit-percentage {
                description 'Configure the percentage style'
                            ;
                leaf cir-percentage {
                  description 'Configure the CIR(Committed Information Rate) pe'
                            + 'rcentage (Set the accuracy rate per hundred (1%)'
                            + ')'
                              ;
                  type uint32 {
                    range 1..100 {
                      description 'The CIR percentage, support <1-100>'
                                  ;
                    }
                  }
                  mandatory true ;
                }
                leaf pir-percentage {
                  description 'Configure the PIR(Peak Information Rate) percent'
                            + 'age (Set the accuracy rate per hundred (1%))'
                              ;
                  type uint32 {
                    range 1..100 {
                      description 'The PIR percentage, support <1-100>'
                                  ;
                    }
                  }
                  mandatory true ;
                }
                ncd:revise-date 2020-12-23 ;
              }
            }
            leaf statistical-share {
              description 'The flag of statistical-share, as follows,'+"\n"
                        + '    ture  Statistical-share is configured'+"\n"
                        + '    false Statistical-share is not configured'
                          ;
              type boolean ;
              default false ;
            }
            leaf token-bucket-id {
              description 'Set token bucket id'
                          ;
              type uint32 {
                range 1..4294967295 {
                  description 'Token bucket id'
                              ;
                }
              }
              ncd:revise-date 2019-10-28 ;
            }
            container mode {
              if-feature qos-car-mode ;
              description 'Set color mode'
                          ;
              presence 'Configure mode information'
                       ;
              leaf mode-type {
                description 'Color mode type, as follows,'+"\n"
                          + '     blind   Color-Blind mode'+"\n"
                          + '     aware   Color-Aware mode'
                            ;
                type enumeration {
                  enum blind {
                    value 1 ;
                    description 'Color-Blind mode'
                                ;
                  }
                  enum aware {
                    value 2 ;
                    description 'Color-Aware mode'
                                ;
                  }
                }
                mandatory true ;
              }
            }
            container conform-action {
              description 'Action to packets that conform to the rate limit'
                          ;
              choice action {
                description 'Specify action to packets that conform to the rate'
                          + ' limit'
                            ;
                mandatory true ;
                case ca-drop {
                  description 'Drop packet in conform-action'
                              ;
                  leaf drop {
                    description 'Specify action to drop packet'
                                ;
                    type empty ;
                    mandatory true ;
                  }
                }
                case ca-transmit {
                  description 'Transmit packet in conform-action'
                              ;
                  leaf transmit {
                    description 'Specify action to transmit packet'
                                ;
                    type empty ;
                    mandatory true ;
                  }
                }
                case ca-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in conform-action, supp'
                                + 'ort <0-7>'
                                  ;
                      type uint8 {
                        range 0..7 {
                          description 'The MPLS-EXP value, support <0-7>'
                                      ;
                        }
                      }
                      mandatory true ;
                    }
                  }
                }
                case ca-precedence {
                  description 'Rewrite packet precedence and transmit the packet'
                              ;
                  container set-prec-transmit {
                    description 'Specify action to rewrite packet precedence an'
                              + 'd transmit it'
                                ;
                    leaf prec-value {
                      description 'Reset the IP-Precedence value in conform-act'
                                + 'ion, support <0-7>'
                                  ;
                      type uint8 {
                        range 0..7 {
                          description 'The IP-Precedence value, support <0-7>'
                                      ;
                        }
                      }
                      mandatory true ;
                    }
                  }
                }
                case ca-dscp {
                  description 'Rewrite packet DSCP and transmit the packet'
                              ;
                  container set-dscp-transmit {
                    description 'Specify action to rewrite packet DSCP and tran'
                              + 'smit it'
                                ;
                    leaf dscp-value {
                      description 'Reset DSCP in conform-action, support <0-63>'
                                  ;
                      type uint8 {
                        range 0..63 {
                          description 'The DSCP value, support <0-63>'
                                      ;
                        }
                      }
                      mandatory true ;
                    }
                  }
                }
                case ca-8021p {
                  description 'Rewrite packet 802.1p and transmit the packet'
                              ;
                  container set-8021p-transmit {
                    description 'Specify action to rewrite packet 802.1p and tr'
                              + 'ansmit it'
                                ;
                    leaf value-8021p {
                      description 'Reset 802.1p in conform-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ca-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ca-service-class {
                  description 'Rewrite packet service class and transmit the pa'
                            + 'cket'
                              ;
                  container set-service-class-transmit {
                    description 'Specify action to rewrite packet service class'
                              + ' and transmit it'
                                ;
                    leaf service-class-value {
                      description 'Reset service class in conform-action'
                                  ;
                      type qos-service-class ;
                      mandatory true ;
                    }
                  }
                  ncd:revise-date 2020-05-18 ;
                }
              }
            }
            container exceed-action {
              description 'Action to packets that exceed the rate limit'
                          ;
              choice action {
                description 'Specify action to packets that exceed the rate lim'
                          + 'it'
                            ;
                mandatory true ;
                case ea-drop {
                  description 'Drop packet in exceed-action'
                              ;
                  leaf drop {
                    description 'Specify action to drop packet'
                                ;
                    type empty ;
                    mandatory true ;
                  }
                }
                case ea-transmit {
                  description 'Transmit packet in exceed-action'
                              ;
                  leaf transmit {
                    description 'Specify action to transmit packet'
                                ;
                    type empty ;
                    mandatory true ;
                  }
                }
                case ea-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in exceed-action, suppo'
                                + 'rt <0-7>'
                                  ;
                      type uint8 {
                        range 0..7 {
                          description 'The MPLS-EXP value, support <0-7>'
                                      ;
                        }
                      }
                      mandatory true ;
                    }
                  }
                }
                case ea-precedence {
                  description 'Rewrite packet precedence and transmit the packet'
                              ;
                  container set-prec-transmit {
                    description 'Specify action to rewrite packet precedence an'
                              + 'd transmit it'
                                ;
                    leaf prec-value {
                      description 'Reset the IP-Precedence value in exceed-acti'
                                + 'on, support <0-7>'
                                  ;
                      type uint8 {
                        range 0..7 {
                          description 'The IP-Precedence value, support <0-7>'
                                      ;
                        }
                      }
                      mandatory true ;
                    }
                  }
                }
                case ea-dscp {
                  description 'Rewrite packet DSCP and transmit the packet'
                              ;
                  container set-dscp-transmit {
                    description 'Specify action to rewrite packet DSCP and tran'
                              + 'smit it'
                                ;
                    leaf dscp-value {
                      description 'Reset DSCP in exceed-action, support <0-63>'
                                  ;
                      type uint8 {
                        range 0..63 {
                          description 'The DSCP value, support <0-63>'
                                      ;
                        }
                      }
                      mandatory true ;
                    }
                  }
                }
                case ea-8021p {
                  description 'Rewrite packet 802.1p and transmit the packet'
                              ;
                  container set-8021p-transmit {
                    description 'Specify action to rewrite packet 802.1p and tr'
                              + 'ansmit it'
                                ;
                    leaf value-8021p {
                      description 'Reset 802.1p in exceed-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ea-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ea-service-class {
                  description 'Rewrite packet service class and transmit the pa'
                            + 'cket'
                              ;
                  container set-service-class-transmit {
                    description 'Specify action to rewrite packet service class'
                              + ' and transmit it'
                                ;
                    leaf service-class-value {
                      description 'Reset service class in exceed-action'
                                  ;
                      type qos-service-class ;
                      mandatory true ;
                    }
                  }
                  ncd:revise-date 2020-05-18 ;
                }
              }
            }
            container violate-action {
              description 'Action to packets that violate the rate limit'
                          ;
              choice action {
                description 'Specify action to packets that violate the rate li'
                          + 'mit'
                            ;
                mandatory true ;
                case va-drop {
                  description 'Drop packet in violate-action'
                              ;
                  leaf drop {
                    description 'Specify action to drop packet'
                                ;
                    type empty ;
                    mandatory true ;
                  }
                }
                case va-transmit {
                  description 'Transmit packet in violate-action'
                              ;
                  leaf transmit {
                    description 'Specify action to transmit packet'
                                ;
                    type empty ;
                    mandatory true ;
                  }
                }
                case va-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in violate-action, supp'
                                + 'ort <0-7>'
                                  ;
                      type uint8 {
                        range 0..7 {
                          description 'The MPLS-EXP value, support <0-7>'
                                      ;
                        }
                      }
                      mandatory true ;
                    }
                  }
                }
                case va-precedence {
                  description 'Rewrite packet precedence and transmit the packet'
                              ;
                  container set-prec-transmit {
                    description 'Specify action to rewrite packet precedence an'
                              + 'd transmit it'
                                ;
                    leaf prec-value {
                      description 'Reset the IP-Precedence value in violate-act'
                                + 'ion, support <0-7>'
                                  ;
                      type uint8 {
                        range 0..7 ;
                      }
                      mandatory true ;
                    }
                  }
                }
                case va-dscp {
                  description 'Rewrite packet DSCP and transmit the packet'
                              ;
                  container set-dscp-transmit {
                    description 'Specify action to rewrite packet DSCP and tran'
                              + 'smit it'
                                ;
                    leaf dscp-value {
                      description 'Reset DSCP in violate-action, support <0-63>'
                                  ;
                      type uint8 {
                        range 0..63 {
                          description 'The DSCP value, support <0-63>'
                                      ;
                        }
                      }
                      mandatory true ;
                    }
                  }
                }
                case va-8021p {
                  description 'Rewrite packet 802.1p and transmit the packet'
                              ;
                  container set-8021p-transmit {
                    description 'Specify action to rewrite packet 802.1p and tr'
                              + 'ansmit it'
                                ;
                    leaf value-8021p {
                      description 'Reset 802.1p in violate-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case va-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case va-service-class {
                  description 'Rewrite packet service class and transmit the pa'
                            + 'cket'
                              ;
                  container set-service-class-transmit {
                    description 'Specify action to rewrite packet service class'
                              + ' and transmit it'
                                ;
                    leaf service-class-value {
                      description 'Reset service class in violate-action'
                                  ;
                      type qos-service-class ;
                      mandatory true ;
                    }
                  }
                  ncd:revise-date 2020-05-18 ;
                }
              }
            }
          }
        }
        container access-lists {
          description 'Match access list'
                      ;
          list access-list {
            description 'Configure interface rate limit based on matching ACL'
                        ;
            key 'if-name if-direct acl-type acl-name'
                ;
            leaf if-name {
              description 'Configure the name of the attaching interface'
                          ;
              type ncd:ifname {
                length 1..31 {
                  description 'Name of the attaching interface, support 1-31 ch'
                            + 'aracters'
                              ;
                }
              }
            }
            leaf if-direct {
              description 'Specify the direction of interface, as follows,'+"\n"
                        + '     input  Rate limit on input'+"\n"
                        + '     output Rate limit on output'
                          ;
              type enumeration {
                enum input {
                  value 1 ;
                  description 'Rate limit on input'
                              ;
                }
                enum output {
                  value 2 ;
                  description 'Rate limit on output'
                              ;
                }
              }
            }
            leaf acl-type {
              description 'Specify the type of access list, such as ipv4-acl, i'
                        + 'pv6-acl, link-acl'
                          ;
              type enumeration {
                enum ipv4-acl {
                  value 5 ;
                  description 'Match IPv4 access list'
                              ;
                }
                enum ipv6-acl {
                  value 6 ;
                  description 'Match IPv6 access list'
                              ;
                }
                enum link-acl {
                  value 15 ;
                  description 'Match link access list'
                              ;
                }
                enum ipv4-mixed-acl {
                  value 19 ;
                  description 'Match ipv4 mixed access list'
                              ;
                }
                enum ipv6-mixed-acl {
                  value 20 ;
                  description 'Match ipv6 mixed access list'
                              ;
                }
              }
            }
            leaf acl-name {
              description 'Name of access list, support 1-31 characters'
                          ;
              type string {
                length 1..31 {
                  description 'Name of IPv4 access list, support 1-31 characters'
                              ;
                }
              }
            }
            leaf rate-limit-desc {
              description 'Description of rate limit, support 1-79 characters.'
                          ;
              type ncd:string-with-blank {
                length 1..79 {
                  description 'Description of rate limit, support 1-79 characte'
                            + 'rs.'
                              ;
                }
              }
              ncd:revise-date 2020-06-18 ;
            }
            choice unit-style {
              description "Specify unit's style"
                          ;
              mandatory true ;
              case unit-value {
                description 'Configure the value style'
                            ;
                leaf cir {
                  description 'Configure the CIR(Committed Information Rate) va'
                            + 'lue (default: kilobits per second)'
                              ;
                  type uint32 {
                    range 8..4294967295 {
                      description 'The CIR value (default: kilobits per second)'
                                + ',support <8-4294967295>'
                                  ;
                    }
                  }
                  mandatory true ;
                }
                leaf cir-unit {
                  description 'set cir unit, such as kbps, mbps, gbps'
                              ;
                  type qos-rate-unit-type ;
                }
                leaf cbs {
                  description 'Configure the CBS(Committed Burst Size) size in '
                            + 'bytes.'
                              ;
                  type uint32 {
                    range 1..4294967295 {
                      description 'The CBS(Committed Burst Size) size in bytes,'
                                + ' support <1-4294967295>.'
                                  ;
                    }
                  }
                  units byte ;
                }
                leaf pir {
                  description 'Configure the PIR(Peak Information Rate) value ('
                            + 'default: kilobits per second)'
                              ;
                  type uint32 {
                    range 8..4294967295 {
                      description 'The PIR(Peak Information Rate) value (defaul'
                                + 't: kilobits per second), support <8-42949672'
                                + '95>'
                                  ;
                    }
                  }
                  mandatory true ;
                }
                leaf pir-unit {
                  description 'set pir unit, such as kbps, mbps, gbps'
                              ;
                  type qos-rate-unit-type ;
                }
                leaf pbs {
                  description 'Configure the PBS(Peak Burst Size) size in bytes.'
                              ;
                  type uint32 {
                    range 1..4294967295 {
                      description 'The PBS(Peak Burst Size) size in KB, support'
                                + ' <1-4294967295>'
                                  ;
                    }
                  }
                  units byte ;
                }
              }
              case unit-percentage {
                description 'Configure the percentage style'
                            ;
                leaf cir-percentage {
                  description 'Configure the CIR(Committed Information Rate) pe'
                            + 'rcentage (Set the accuracy rate per hundred (1%)'
                            + ')'
                              ;
                  type uint32 {
                    range 1..100 {
                      description 'The CIR percentage, support <1-100>'
                                  ;
                    }
                  }
                  mandatory true ;
                }
                leaf pir-percentage {
                  description 'Configure the PIR(Peak Information Rate) percent'
                            + 'age (Set the accuracy rate per hundred (1%))'
                              ;
                  type uint32 {
                    range 1..100 {
                      description 'The PIR percentage, support <1-100>'
                                  ;
                    }
                  }
                  mandatory true ;
                }
                ncd:revise-date 2020-12-23 ;
              }
            }
            leaf statistical-share {
              description 'The flag of statistical-share, as follows,'+"\n"
                        + '    ture  Statistical-share is configured'+"\n"
                        + '    false Statistical-share is not configured'
                          ;
              type boolean ;
              default false ;
            }
            leaf token-bucket-id {
              description 'Set token bucket id'
                          ;
              type uint32 {
                range 1..4294967295 {
                  description 'Token bucket id'
                              ;
                }
              }
              ncd:revise-date 2019-10-28 ;
            }
            container mode {
              if-feature qos-car-mode ;
              description 'Set color mode'
                          ;
              presence 'Configure mode information'
                       ;
              leaf mode-type {
                description 'Color mode type, as follows,'+"\n"
                          + '     blind   Color-Blind mode'+"\n"
                          + '     aware   Color-Aware mode'
                            ;
                type enumeration {
                  enum blind {
                    value 1 ;
                    description 'Color-Blind mode'
                                ;
                  }
                  enum aware {
                    value 2 ;
                    description 'Color-Aware mode'
                                ;
                  }
                }
                mandatory true ;
              }
            }
            container conform-action {
              description 'Action to packets that conform to the rate limit'
                          ;
              choice action {
                description 'Specify action to packets that conform to the rate'
                          + ' limit'
                            ;
                mandatory true ;
                case ca-drop {
                  description 'Drop packet in conform-action'
                              ;
                  leaf drop {
                    description 'Specify action to drop packet'
                                ;
                    type empty ;
                    mandatory true ;
                  }
                }
                case ca-transmit {
                  description 'Transmit packet in conform-action'
                              ;
                  leaf transmit {
                    description 'Specify action to transmit packet'
                                ;
                    type empty ;
                    mandatory true ;
                  }
                }
                case ca-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in conform-action, supp'
                                + 'ort <0-7>'
                                  ;
                      type uint8 {
                        range 0..7 {
                          description 'The MPLS-EXP value, support <0-7>'
                                      ;
                        }
                      }
                      mandatory true ;
                    }
                  }
                }
                case ca-precedence {
                  description 'Rewrite packet precedence and transmit the packet'
                              ;
                  container set-prec-transmit {
                    description 'Specify action to rewrite packet precedence an'
                              + 'd transmit it'
                                ;
                    leaf prec-value {
                      description 'Reset the IP-Precedence value in conform-act'
                                + 'ion, support <0-7>'
                                  ;
                      type uint8 {
                        range 0..7 {
                          description 'The IP-Precedence value, support <0-7>'
                                      ;
                        }
                      }
                      mandatory true ;
                    }
                  }
                }
                case ca-dscp {
                  description 'Rewrite packet DSCP and transmit the packet'
                              ;
                  container set-dscp-transmit {
                    description 'Specify action to rewrite packet DSCP and tran'
                              + 'smit it'
                                ;
                    leaf dscp-value {
                      description 'Reset DSCP in conform-action, support <0-63>'
                                  ;
                      type uint8 {
                        range 0..63 {
                          description 'The DSCP value, support <0-63>'
                                      ;
                        }
                      }
                      mandatory true ;
                    }
                  }
                }
                case ca-8021p {
                  description 'Rewrite packet 802.1p and transmit the packet'
                              ;
                  container set-8021p-transmit {
                    description 'Specify action to rewrite packet 802.1p and tr'
                              + 'ansmit it'
                                ;
                    leaf value-8021p {
                      description 'Reset 802.1p in conform-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ca-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ca-service-class {
                  description 'Rewrite packet service class and transmit the pa'
                            + 'cket'
                              ;
                  container set-service-class-transmit {
                    description 'Specify action to rewrite packet service class'
                              + ' and transmit it'
                                ;
                    leaf service-class-value {
                      description 'Reset service class in conform-action'
                                  ;
                      type qos-service-class ;
                      mandatory true ;
                    }
                  }
                  ncd:revise-date 2020-05-18 ;
                }
              }
            }
            container exceed-action {
              description 'Action to packets that exceed the rate limit'
                          ;
              choice action {
                description 'Specify action to packets that exceed the rate lim'
                          + 'it'
                            ;
                mandatory true ;
                case ea-drop {
                  description 'Drop packet in exceed-action'
                              ;
                  leaf drop {
                    description 'Specify action to drop packet'
                                ;
                    type empty ;
                    mandatory true ;
                  }
                }
                case ea-transmit {
                  description 'Transmit packet in exceed-action'
                              ;
                  leaf transmit {
                    description 'Specify action to transmit packet'
                                ;
                    type empty ;
                    mandatory true ;
                  }
                }
                case ea-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in exceed-action, suppo'
                                + 'rt <0-7>'
                                  ;
                      type uint8 {
                        range 0..7 {
                          description 'The MPLS-EXP value, support <0-7>'
                                      ;
                        }
                      }
                      mandatory true ;
                    }
                  }
                }
                case ea-precedence {
                  description 'Rewrite packet precedence and transmit the packet'
                              ;
                  container set-prec-transmit {
                    description 'Specify action to rewrite packet precedence an'
                              + 'd transmit it'
                                ;
                    leaf prec-value {
                      description 'Reset the IP-Precedence value in exceed-acti'
                                + 'on, support <0-7>'
                                  ;
                      type uint8 {
                        range 0..7 {
                          description 'The IP-Precedence value, support <0-7>'
                                      ;
                        }
                      }
                      mandatory true ;
                    }
                  }
                }
                case ea-dscp {
                  description 'Rewrite packet DSCP and transmit the packet'
                              ;
                  container set-dscp-transmit {
                    description 'Specify action to rewrite packet DSCP and tran'
                              + 'smit it'
                                ;
                    leaf dscp-value {
                      description 'Reset DSCP in exceed-action, support <0-63>'
                                  ;
                      type uint8 {
                        range 0..63 {
                          description 'The DSCP value, support <0-63>'
                                      ;
                        }
                      }
                      mandatory true ;
                    }
                  }
                }
                case ea-8021p {
                  description 'Rewrite packet 802.1p and transmit the packet'
                              ;
                  container set-8021p-transmit {
                    description 'Specify action to rewrite packet 802.1p and tr'
                              + 'ansmit it'
                                ;
                    leaf value-8021p {
                      description 'Reset 802.1p in exceed-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case ea-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case ea-service-class {
                  description 'Rewrite packet service class and transmit the pa'
                            + 'cket'
                              ;
                  container set-service-class-transmit {
                    description 'Specify action to rewrite packet service class'
                              + ' and transmit it'
                                ;
                    leaf service-class-value {
                      description 'Reset service class in exceed-action'
                                  ;
                      type qos-service-class ;
                      mandatory true ;
                    }
                  }
                  ncd:revise-date 2020-05-18 ;
                }
              }
            }
            container violate-action {
              description 'Action to packets that violate the rate limit'
                          ;
              choice action {
                description 'Specify action to packets that violate the rate li'
                          + 'mit'
                            ;
                mandatory true ;
                case va-drop {
                  description 'Drop packet in violate-action'
                              ;
                  leaf drop {
                    description 'Specify action to drop packet'
                                ;
                    type empty ;
                    mandatory true ;
                  }
                }
                case va-transmit {
                  description 'Transmit packet in violate-action'
                              ;
                  leaf transmit {
                    description 'Specify action to transmit packet'
                                ;
                    type empty ;
                    mandatory true ;
                  }
                }
                case va-mpls-exp {
                  description 'Rewrite packet MPLS-EXP and transmit the packet'
                              ;
                  container set-exp-transmit {
                    description 'Specify action to rewrite packet MPLS-EXP and '
                              + 'transmit it'
                                ;
                    container mpls-label-type {
                      description 'Set MPLS-EXP label type'
                                  ;
                      presence 'Set MPLS-EXP label type'
                               ;
                      leaf label-type {
                        description 'Set MPLS-EXP label position, such as '+"\n"
                                  + '    topmost    Set the MPLS-EXP value on t'
                                  + 'opmost label'+"\n"
                                  + '    imposition Set the MPLS-EXP value on i'
                                  + 'mposition label'+"\n"
                                  + '    inner      Set the MPLS-EXP value on i'
                                  + 'nner label'
                                    ;
                        type enumeration {
                          enum topmost {
                            value 1 ;
                            description 'Set the MPLS-EXP value on topmost label'
                                        ;
                          }
                          enum imposition {
                            value 2 ;
                            description 'Set the MPLS-EXP value on imposition label'
                                        ;
                          }
                          enum inner {
                            value 3 ;
                            description 'Set the MPLS-EXP value on inner label'
                                        ;
                          }
                        }
                        mandatory true ;
                      }
                    }
                    leaf mpls-exp-value {
                      description 'Reset MPLS-EXP value in violate-action, supp'
                                + 'ort <0-7>'
                                  ;
                      type uint8 {
                        range 0..7 {
                          description 'The MPLS-EXP value, support <0-7>'
                                      ;
                        }
                      }
                      mandatory true ;
                    }
                  }
                }
                case va-precedence {
                  description 'Rewrite packet precedence and transmit the packet'
                              ;
                  container set-prec-transmit {
                    description 'Specify action to rewrite packet precedence an'
                              + 'd transmit it'
                                ;
                    leaf prec-value {
                      description 'Reset the IP-Precedence value in violate-act'
                                + 'ion, support <0-7>'
                                  ;
                      type uint8 {
                        range 0..7 ;
                      }
                      mandatory true ;
                    }
                  }
                }
                case va-dscp {
                  description 'Rewrite packet DSCP and transmit the packet'
                              ;
                  container set-dscp-transmit {
                    description 'Specify action to rewrite packet DSCP and tran'
                              + 'smit it'
                                ;
                    leaf dscp-value {
                      description 'Reset DSCP in violate-action, support <0-63>'
                                  ;
                      type uint8 {
                        range 0..63 {
                          description 'The DSCP value, support <0-63>'
                                      ;
                        }
                      }
                      mandatory true ;
                    }
                  }
                }
                case va-8021p {
                  description 'Rewrite packet 802.1p and transmit the packet'
                              ;
                  container set-8021p-transmit {
                    description 'Specify action to rewrite packet 802.1p and tr'
                              + 'ansmit it'
                                ;
                    leaf value-8021p {
                      description 'Reset 802.1p in violate-action, support <0-7>'
                                  ;
                      type uint8 {
                        range 0..7 {
                          description 'The 802.1p value, support <0-7>'
                                      ;
                        }
                      }
                      mandatory true ;
                    }
                    leaf inner-outer {
                      description 'Set 8021p inner or outer flag.If vlaue is 0,'
                                + ' it means outer flag. If value is 1,it means'
                                + ' inner and outer flag.'
                                  ;
                      type uint8 {
                        range 0..1 {
                          description 'Inner or outer flag. 0 is outer. 1 is in'
                                    + 'ner and outer'
                                      ;
                        }
                      }
                      default 0 ;
                      ncd:revise-date 2017-01-10 ;
                    }
                  }
                }
                case va-multi-exp {
                  description 'Rewrite packet multi-MPLS-EXP and transmit it'
                              ;
                  container set-multi-exp-transmit {
                    description 'Specify action to rewrite packet multi-MPLS-EX'
                              + 'P and transmit it'
                                ;
                    leaf inner-value {
                      description 'Inner multi-MPLS-EXP value, support <0-7>'
                                  ;
                      type uint8 {
                        range 0..7 {
                          description 'Inner multi-MPLS-EXP value, support <0-7>'
                                      ;
                        }
                      }
                      mandatory true ;
                    }
                    leaf outer-value {
                      description 'Outer multi-MPLS-EXP value, support <0-7>'
                                  ;
                      type uint8 {
                        range 0..7 {
                          description 'Outer multi-MPLS-EXP value, support <0-7>'
                                      ;
                        }
                      }
                      mandatory true ;
                    }
                  }
                }
                case va-service-class {
                  description 'Rewrite packet service class and transmit the pa'
                            + 'cket'
                              ;
                  container set-service-class-transmit {
                    description 'Specify action to rewrite packet service class'
                              + ' and transmit it'
                                ;
                    leaf service-class-value {
                      description 'Reset service class in violate-action'
                                  ;
                      type qos-service-class ;
                      mandatory true ;
                    }
                  }
                  ncd:revise-date 2020-05-18 ;
                }
              }
            }
          }
        }
      }
      container diffserv {
        if-feature diffserv ;
        description 'Differentiated Services'
                    ;
        container ds-domains {
          description 'Configure the template of diffserv domain'
                      ;
          list ds-domain {
            description 'Configure the template of diffserv domain, the max num'
                      + 'ber of template is 8'
                        ;
            key domain-name ;
            leaf domain-name {
              description 'Name of the diffserv domain, support 1-31 characters'
                          ;
              type string {
                length 1..31 {
                  description 'Name of the diffserv domain, support 1-31 charac'
                            + 'ters'
                              ;
                }
              }
            }
            container map {
              description 'Configure the mapping between some protocol and PHB'
                          ;
              container pri-8021ps {
                status obsolete {
                  ncd:revise-date 2016-12-20 ;
                }
                description 'Configure the mapping based on 802.1p'
                            ;
                list pri-8021p {
                  status obsolete {
                    ncd:revise-date 2016-12-20 ;
                  }
                  description 'Map 802.1p to PHB, PHB include server class and '
                            + 'color.'
                              ;
                  key value-8021p ;
                  leaf value-8021p {
                    status obsolete {
                      ncd:revise-date 2016-12-20 ;
                    }
                    description '802.1p value, support <0-7>'
                                ;
                    type uint32 {
                      range 0..7 {
                        description '802.1p value, support <0-7>'
                                    ;
                      }
                    }
                  }
                  leaf server-class {
                    status obsolete {
                      ncd:revise-date 2016-12-20 ;
                    }
                    description 'Specify server class of PHB info, support <af1'
                              + ',af2,af3,af4,be,cs6,cs7,ef>'
                                ;
                    type qos-service-class ;
                    mandatory true ;
                  }
                  leaf color-type {
                    status obsolete {
                      ncd:revise-date 2016-12-20 ;
                    }
                    description 'Specify packets color, support <green,yellow,r'
                              + 'ed>'
                                ;
                    type qos-color-type ;
                    mandatory true ;
                  }
                }
              }
              container pri-8021p-singles {
                description 'Configure the mapping based on 802.1p.'
                            ;
                list pri-8021p-single {
                  description 'Map 802.1p to PHB, PHB include server class and '
                            + 'color.'
                              ;
                  key value-8021p ;
                  leaf value-8021p {
                    description '802.1p value, support <0-7>.'
                                ;
                    type uint32 {
                      range 0..7 {
                        description '802.1p value, support <0-7>'
                                    ;
                      }
                    }
                  }
                  leaf server-class {
                    description 'Specify server class of PHB info, support <af1'
                              + ',af2,af3,af4,be,cs6,cs7,ef>.'
                                ;
                    type qos-service-class ;
                    mandatory true ;
                  }
                  leaf color-type {
                    description 'Specify packets color, support <green,yellow,r'
                              + 'ed>.'
                                ;
                    type qos-color-type ;
                    mandatory true ;
                  }
                }
                ncd:revise-date 2016-12-20 ;
              }
              container pri-8021p-ranges {
                description 'Configure the mapping based on 802.1p.'
                            ;
                list pri-8021p-range {
                  description 'Map 802.1p to PHB, PHB include server class and '
                            + 'color.'
                              ;
                  key value-8021p ;
                  leaf value-8021p {
                    description '802.1p value, support single 802.1p value or r'
                              + 'ange(max num:4;spacing mark:,) in <0-7>. For e'
                              + 'xample,"0,3-5,7",etc.'
                                ;
                    type qos-8021p-bitmap ;
                  }
                  leaf server-class {
                    description 'Specify server class of PHB info, support <af1'
                              + ',af2,af3,af4,be,cs6,cs7,ef>.'
                                ;
                    type qos-service-class ;
                    mandatory true ;
                  }
                  leaf color-type {
                    description 'Specify packets color, support <green,yellow,r'
                              + 'ed>.'
                                ;
                    type qos-color-type ;
                    mandatory true ;
                  }
                }
                ncd:revise-date 2016-12-20 ;
              }
              container mpls-exps {
                status obsolete {
                  ncd:revise-date 2016-12-20 ;
                }
                description 'Configure the mapping based on MPLS-EXP'
                            ;
                list mpls-exp {
                  status obsolete {
                    ncd:revise-date 2016-12-20 ;
                  }
                  description 'Map MPLS-EXP to PHB, PHB include server class an'
                            + 'd color.'
                              ;
                  key mpls-exp-value ;
                  leaf mpls-exp-value {
                    status obsolete {
                      ncd:revise-date 2016-12-20 ;
                    }
                    description 'MPLS-EXP value, support <0-7>'
                                ;
                    type uint32 {
                      range 0..7 {
                        description 'MPLS-EXP value, support <0-7>'
                                    ;
                      }
                    }
                  }
                  leaf server-class {
                    status obsolete {
                      ncd:revise-date 2016-12-20 ;
                    }
                    description 'Specify server class of PHB info, support <af1'
                              + ',af2,af3,af4,be,cs6,cs7,ef>'
                                ;
                    type qos-service-class ;
                    mandatory true ;
                  }
                  leaf color-type {
                    status obsolete {
                      ncd:revise-date 2016-12-20 ;
                    }
                    description 'Specify packets color, support <green,yellow,r'
                              + 'ed>'
                                ;
                    type qos-color-type ;
                    mandatory true ;
                  }
                }
              }
              container mpls-exp-singles {
                description 'Configure the mapping based on MPLS-EXP.'
                            ;
                list mpls-exp-single {
                  description 'Map MPLS-EXP to PHB, PHB include server class an'
                            + 'd color.'
                              ;
                  key mpls-exp-value ;
                  leaf mpls-exp-value {
                    description 'MPLS-EXP value, support <0-7>.'
                                ;
                    type uint32 {
                      range 0..7 {
                        description 'MPLS-EXP value, support <0-7>'
                                    ;
                      }
                    }
                  }
                  leaf server-class {
                    description 'Specify server class of PHB info, support <af1'
                              + ',af2,af3,af4,be,cs6,cs7,ef>.'
                                ;
                    type qos-service-class ;
                    mandatory true ;
                  }
                  leaf color-type {
                    description 'Specify packets color, support <green,yellow,r'
                              + 'ed>.'
                                ;
                    type qos-color-type ;
                    mandatory true ;
                  }
                }
                ncd:revise-date 2016-12-20 ;
              }
              container mpls-exp-ranges {
                description 'Configure the mapping based on MPLS-EXP.'
                            ;
                list mpls-exp-range {
                  description 'Map MPLS-EXP to PHB, PHB include server class an'
                            + 'd color.'
                              ;
                  key mpls-exp-value ;
                  leaf mpls-exp-value {
                    description 'MPLS-EXP value, support single MPLS-EXP value '
                              + 'or range(max num:4;spacing mark:,) in <0-7>. F'
                              + 'or example,"0,3-5,7",etc.'
                                ;
                    type qos-mpls-bitmap ;
                  }
                  leaf server-class {
                    description 'Specify server class of PHB info, support <af1'
                              + ',af2,af3,af4,be,cs6,cs7,ef>.'
                                ;
                    type qos-service-class ;
                    mandatory true ;
                  }
                  leaf color-type {
                    description 'Specify packets color, support <green,yellow,r'
                              + 'ed>.'
                                ;
                    type qos-color-type ;
                    mandatory true ;
                  }
                }
                ncd:revise-date 2016-12-20 ;
              }
              container phbs {
                description 'Configure PHB (Per Hop Behavior)'
                            ;
                container pri-8021ps {
                  description 'PHB be mapped to 802.1p'
                              ;
                  list pri-8021p {
                    description 'PHB be mapped to 802.1p'
                                ;
                    key 'server-class color-type'
                        ;
                    leaf server-class {
                      description 'Specify server class of PHB info, support <a'
                                + 'f1,af2,af3,af4,be,cs6,cs7,ef>'
                                  ;
                      type qos-service-class ;
                    }
                    leaf color-type {
                      description 'Specify packets color, support <green,yellow'
                                + ',red>'
                                  ;
                      type qos-color-type ;
                    }
                    leaf value-8021p {
                      description '802.1p value, support <0-7>'
                                  ;
                      type uint32 {
                        range 0..7 {
                          description '802.1p value, support <0-7>'
                                      ;
                        }
                      }
                      mandatory true ;
                    }
                  }
                }
                container mpls-exps {
                  description 'PHB be mapped to MPLS-EXP'
                              ;
                  list mpls-exp {
                    description 'PHB be mapped to MPLS-EXP'
                                ;
                    key 'server-class color-type'
                        ;
                    leaf server-class {
                      description 'Specify server class of PHB info, support <a'
                                + 'f1,af2,af3,af4,be,cs6,cs7,ef>'
                                  ;
                      type qos-service-class ;
                    }
                    leaf color-type {
                      description 'Specify packets color, support <green,yellow'
                                + ',red>'
                                  ;
                      type qos-color-type ;
                    }
                    leaf mpls-exp-value {
                      description 'MPLS-EXP value, support <0-7>'
                                  ;
                      type uint32 {
                        range 0..7 {
                          description 'MPLS-EXP value, support <0-7>'
                                      ;
                        }
                      }
                      mandatory true ;
                    }
                  }
                }
                container ipv4-dscps {
                  description 'PHB be mapped to IPv4 DSCP'
                              ;
                  list ipv4-dscp {
                    description 'PHB be mapped to IPv4 DSCP'
                                ;
                    key 'server-class color-type'
                        ;
                    leaf server-class {
                      description 'Specify server class of PHB info, support <a'
                                + 'f1,af2,af3,af4,be,cs6,cs7,ef>'
                                  ;
                      type qos-service-class ;
                    }
                    leaf color-type {
                      description 'Specify packets color, support <green,yellow'
                                + ',red>'
                                  ;
                      type qos-color-type ;
                    }
                    leaf dscp-value {
                      description 'IPv4 DSCP value, support <0-63>'
                                  ;
                      type uint32 {
                        range 0..63 {
                          description 'IPv4 DSCP value, support <0-63>'
                                      ;
                        }
                      }
                      mandatory true ;
                    }
                  }
                }
                container ipv6-dscps {
                  description 'PHB be mapped to IPv6 DSCP'
                              ;
                  list ipv6-dscp {
                    description 'PHB be mapped to IPv6 DSCP'
                                ;
                    key 'server-class color-type'
                        ;
                    leaf server-class {
                      description 'Specify server class of PHB info, support <a'
                                + 'f1,af2,af3,af4,be,cs6,cs7,ef>'
                                  ;
                      type qos-service-class ;
                    }
                    leaf color-type {
                      description 'Specify packets color, support <green,yellow'
                                + ',red>'
                                  ;
                      type qos-color-type ;
                    }
                    leaf dscp-value {
                      description 'IPv6 DSCP value, support <0-63>'
                                  ;
                      type uint32 {
                        range 0..63 {
                          description 'IPv6 DSCP value, support <0-63>'
                                      ;
                        }
                      }
                      mandatory true ;
                    }
                  }
                }
              }
              container link-acls {
                description 'Configure the mapping based on link access list'
                            ;
                list link-acl {
                  description 'Map link access list to PHB, PHB include server '
                            + 'class and color.'
                              ;
                  key acl-name ;
                  leaf acl-name {
                    description 'Set link-access-list name, support 1-31 charac'
                              + 'ters'
                                ;
                    type string {
                      length 1..31 {
                        description 'Name of ACL, support 1-31 characters'
                                    ;
                      }
                    }
                  }
                  leaf server-class {
                    description 'Specify server class of PHB info, support <af1'
                              + ',af2,af3,af4,be,cs6,cs7,ef>'
                                ;
                    type qos-service-class ;
                    mandatory true ;
                  }
                  leaf color-type {
                    description 'Specify packets color, support <green,yellow,r'
                              + 'ed>'
                                ;
                    type qos-color-type ;
                    mandatory true ;
                  }
                }
              }
              container ipv4-dscps {
                status obsolete {
                  ncd:revise-date 2016-12-20 ;
                }
                description 'Configure the mapping based on IPv4 DSCP'
                            ;
                list ipv4-dscp {
                  status obsolete {
                    ncd:revise-date 2016-12-20 ;
                  }
                  description 'Map IPv4 DSCP to PHB, PHB include server class a'
                            + 'nd color.'
                              ;
                  key dscp-value ;
                  leaf dscp-value {
                    status obsolete {
                      ncd:revise-date 2016-12-20 ;
                    }
                    description 'IPv4 DSCP value, support <0-63>'
                                ;
                    type uint32 {
                      range 0..63 {
                        description 'IPv4 DSCP value, support <0-63>'
                                    ;
                      }
                    }
                  }
                  leaf server-class {
                    status obsolete {
                      ncd:revise-date 2016-12-20 ;
                    }
                    description 'Specify server class of PHB info, support <af1'
                              + ',af2,af3,af4,be,cs6,cs7,ef>'
                                ;
                    type qos-service-class ;
                    mandatory true ;
                  }
                  leaf color-type {
                    status obsolete {
                      ncd:revise-date 2016-12-20 ;
                    }
                    description 'Specify packets color, support <green,yellow,r'
                              + 'ed>'
                                ;
                    type qos-color-type ;
                    mandatory true ;
                  }
                }
              }
              container ipv4-dscp-singles {
                description 'Configure the mapping based on IPv4 DSCP.'
                            ;
                list ipv4-dscp-single {
                  description 'Map IPv4 DSCP to PHB, PHB include server class a'
                            + 'nd color.'
                              ;
                  key dscp-value ;
                  leaf dscp-value {
                    description 'IPv4 DSCP value, support <0-63>.'
                                ;
                    type uint32 {
                      range 0..63 {
                        description 'IPv4 DSCP value, support <0-63>'
                                    ;
                      }
                    }
                  }
                  leaf server-class {
                    description 'Specify server class of PHB info, support <af1'
                              + ',af2,af3,af4,be,cs6,cs7,ef>.'
                                ;
                    type qos-service-class ;
                    mandatory true ;
                  }
                  leaf color-type {
                    description 'Specify packets color, support <green,yellow,r'
                              + 'ed>.'
                                ;
                    type qos-color-type ;
                    mandatory true ;
                  }
                }
                ncd:revise-date 2016-12-20 ;
              }
              container ipv4-dscp-ranges {
                description 'Configure the mapping based on IPv4 DSCP.'
                            ;
                list ipv4-dscp-range {
                  description 'Map IPv4 DSCP to PHB, PHB include server class a'
                            + 'nd color.'
                              ;
                  key dscp-value ;
                  leaf dscp-value {
                    description 'IPv4 DSCP value, support single DSCP value or '
                              + 'range(max num:4;spacing mark:,) in <0-63>. For'
                              + ' example,"6,10-30,40,50-60",etc.'
                                ;
                    type qos-dscp-bitmap ;
                  }
                  leaf server-class {
                    description 'Specify server class of PHB info, support <af1'
                              + ',af2,af3,af4,be,cs6,cs7,ef>.'
                                ;
                    type qos-service-class ;
                    mandatory true ;
                  }
                  leaf color-type {
                    description 'Specify packets color, support <green,yellow,r'
                              + 'ed>.'
                                ;
                    type qos-color-type ;
                    mandatory true ;
                  }
                }
                ncd:revise-date 2016-12-20 ;
              }
              container ipv4-acls {
                description 'Configure the mapping based on IPv4 access list'
                            ;
                list ipv4-acl {
                  description 'Map IPv4 access list to PHB, PHB include server '
                            + 'class and color.'
                              ;
                  key acl-name ;
                  leaf acl-name {
                    description 'Set ipv4-access-list name, support 1-31 charac'
                              + 'ters'
                                ;
                    type string {
                      length 1..31 {
                        description 'Name of ACL, support 1-31 characters'
                                    ;
                      }
                    }
                  }
                  leaf server-class {
                    description 'Specify server class of PHB info, support <af1'
                              + ',af2,af3,af4,be,cs6,cs7,ef>'
                                ;
                    type qos-service-class ;
                    mandatory true ;
                  }
                  leaf color-type {
                    description 'Specify packets color, support <green,yellow,r'
                              + 'ed>'
                                ;
                    type qos-color-type ;
                    mandatory true ;
                  }
                }
              }
              container ipv4-mixed-acls {
                description 'Configure the mapping based on IPv4 mixed access l'
                          + 'ist'
                            ;
                list ipv4-mixed-acl {
                  description 'Map IPv4 mixed access list to PHB, PHB include s'
                            + 'erver class and color.'
                              ;
                  key acl-name ;
                  leaf acl-name {
                    description 'Set ipv4-mixed-access-list name, support 1-31 '
                              + 'characters'
                                ;
                    type string {
                      length 1..31 {
                        description 'Name of ACL, support 1-31 characters'
                                    ;
                      }
                    }
                  }
                  leaf server-class {
                    description 'Specify server class of PHB info, support <af1'
                              + ',af2,af3,af4,be,cs6,cs7,ef>'
                                ;
                    type qos-service-class ;
                    mandatory true ;
                  }
                  leaf color-type {
                    description 'Specify packets color, support <green,yellow,r'
                              + 'ed>'
                                ;
                    type qos-color-type ;
                    mandatory true ;
                  }
                }
              }
              container ipv6-dscps {
                status obsolete {
                  ncd:revise-date 2016-12-20 ;
                }
                description 'Configure the mapping based on IPv6 DSCP'
                            ;
                list ipv6-dscp {
                  status obsolete {
                    ncd:revise-date 2016-12-20 ;
                  }
                  description 'Map IPv6 DSCP to PHB, PHB include server class a'
                            + 'nd color.'
                              ;
                  key dscp-value ;
                  leaf dscp-value {
                    status obsolete {
                      ncd:revise-date 2016-12-20 ;
                    }
                    description 'IPv6 DSCP value, support <0-63>'
                                ;
                    type uint32 {
                      range 0..63 {
                        description 'IPv6 DSCP value, support <0-63>'
                                    ;
                      }
                    }
                  }
                  leaf server-class {
                    status obsolete {
                      ncd:revise-date 2016-12-20 ;
                    }
                    description 'Specify server class of PHB info, support <af1'
                              + ',af2,af3,af4,be,cs6,cs7,ef>'
                                ;
                    type qos-service-class ;
                    mandatory true ;
                  }
                  leaf color-type {
                    status obsolete {
                      ncd:revise-date 2016-12-20 ;
                    }
                    description 'Specify packets color, support <green,yellow,r'
                              + 'ed>'
                                ;
                    type qos-color-type ;
                    mandatory true ;
                  }
                }
              }
              container ipv6-dscp-singles {
                description 'Configure the mapping based on IPv6 DSCP.'
                            ;
                list ipv6-dscp-single {
                  description 'Map IPv6 DSCP to PHB, PHB include server class a'
                            + 'nd color.'
                              ;
                  key dscp-value ;
                  leaf dscp-value {
                    description 'IPv6 DSCP value, support <0-63>.'
                                ;
                    type uint32 {
                      range 0..63 {
                        description 'IPv6 DSCP value, support <0-63>'
                                    ;
                      }
                    }
                  }
                  leaf server-class {
                    description 'Specify server class of PHB info, support <af1'
                              + ',af2,af3,af4,be,cs6,cs7,ef>.'
                                ;
                    type qos-service-class ;
                    mandatory true ;
                  }
                  leaf color-type {
                    description 'Specify packets color, support <green,yellow,r'
                              + 'ed>.'
                                ;
                    type qos-color-type ;
                    mandatory true ;
                  }
                }
                ncd:revise-date 2016-12-20 ;
              }
              container ipv6-dscp-ranges {
                description 'Configure the mapping based on IPv6 DSCP.'
                            ;
                list ipv6-dscp-range {
                  description 'Map IPv6 DSCP to PHB, PHB include server class a'
                            + 'nd color.'
                              ;
                  key dscp-value ;
                  leaf dscp-value {
                    description 'IPv6 DSCP value, support single DSCP value or '
                              + 'range(max num:4;spacing mark:,) in <0-63>. For'
                              + ' example,"6,10-30,40,50-60",etc.'
                                ;
                    type qos-dscp-bitmap ;
                  }
                  leaf server-class {
                    description 'Specify server class of PHB info, support <af1'
                              + ',af2,af3,af4,be,cs6,cs7,ef>.'
                                ;
                    type qos-service-class ;
                    mandatory true ;
                  }
                  leaf color-type {
                    description 'Specify packets color, support <green,yellow,r'
                              + 'ed>.'
                                ;
                    type qos-color-type ;
                    mandatory true ;
                  }
                }
                ncd:revise-date 2016-12-20 ;
              }
              container ipv6-acls {
                description 'Configure the mapping based on IPv6 access list'
                            ;
                list ipv6-acl {
                  description 'Map IPv6 access list to PHB, PHB include server '
                            + 'class and color.'
                              ;
                  key acl-name ;
                  leaf acl-name {
                    description 'Set ipv6-access-list name, support 1-31 charac'
                              + 'ters'
                                ;
                    type string {
                      length 1..31 {
                        description 'Name of ACL, support 1-31 characters'
                                    ;
                      }
                    }
                  }
                  leaf server-class {
                    description 'Specify server class of PHB info, support <af1'
                              + ',af2,af3,af4,be,cs6,cs7,ef>'
                                ;
                    type qos-service-class ;
                    mandatory true ;
                  }
                  leaf color-type {
                    description 'Specify packets color, support <green,yellow,r'
                              + 'ed>'
                                ;
                    type qos-color-type ;
                    mandatory true ;
                  }
                }
              }
              container ipv6-mixed-acls {
                description 'Configure the mapping based on IPv6 mixed access l'
                          + 'ist'
                            ;
                list ipv6-mixed-acl {
                  description 'Map IPv6 mixed access list to PHB, PHB include s'
                            + 'erver class and color.'
                              ;
                  key acl-name ;
                  leaf acl-name {
                    description 'Set ipv6-mixed-access-list name, support 1-31 '
                              + 'characters'
                                ;
                    type string {
                      length 1..31 {
                        description 'Name of ACL, support 1-31 characters'
                                    ;
                      }
                    }
                  }
                  leaf server-class {
                    description 'Specify server class of PHB info, support <af1'
                              + ',af2,af3,af4,be,cs6,cs7,ef>'
                                ;
                    type qos-service-class ;
                    mandatory true ;
                  }
                  leaf color-type {
                    description 'Specify packets color, support <green,yellow,r'
                              + 'ed>'
                                ;
                    type qos-color-type ;
                    mandatory true ;
                  }
                }
              }
            }
          }
        }
      }
      container qos-ds-domains {
        if-feature qos-ds-domains ;
        description 'Configure the used diffserv domain template'
                    ;
        list qos-ds-domain {
          description 'Configure interface binding DS domain'
                      ;
          key if-name ;
          leaf if-name {
            description 'Specify the name of interface binding DS domain, suppo'
                      + 'rt 1-31 characters'
                        ;
            type ncd:ifname {
              length 1..31 {
                description 'Name of the interface, support 1-31 characters'
                            ;
              }
            }
          }
          leaf ds-domain-name {
            description 'Name of the diffserv domain, support 1-31 characters'
                        ;
            type string {
              length 1..31 {
                description 'Name of the diffserv domain, support 1-31 characte'
                          + 'rs'
                            ;
              }
            }
            mandatory true ;
          }
          leaf bound-type {
            description 'Specify the bind mode, as follows,'+"\n"
                      + '     overwrite Set DS-domain bound on link-ports with '
                      + 'overwrite'
                        ;
            type enumeration {
              enum overwrite {
                value 2 ;
                description 'Set DS-domain bound on link-ports with overwrite'
                            ;
              }
            }
            ncd:revise-date 2018-09-19 ;
          }
        }
      }
      container qos-prioritys {
        if-feature qos-prioritys ;
        description 'Configure the type of priority trusted by QoS'
                    ;
        list qos-priority {
          description 'Configure the type of priority trusted by QoS'
                      ;
          key if-name ;
          leaf if-name {
            description 'Specify the name of interface applied, support 1-31 ch'
                      + 'aracters'
                        ;
            type ncd:ifname {
              length 1..31 {
                description 'Name of the interface, support 1-31 characters'
                            ;
              }
            }
          }
          leaf priority-type {
            description 'Set the priority type trusted by interface, such as 80'
                      + '2.1p, dscp, mpls-exp'
                        ;
            type enumeration {
              enum 8021p {
                value 1 ;
                description 'Based on 802.1p'
                            ;
              }
              enum ip-dscp {
                value 2 ;
                description 'Based on IP DSCP'
                            ;
              }
              enum mpls-exp {
                value 3 ;
                description 'Based on MPLS-EXP'
                            ;
              }
            }
            mandatory true ;
          }
        }
      }
      container qos-schedule {
        if-feature qos-schedule ;
        description 'Set scheduling policy for a certain transmitting entity'
                    ;
        container interfaces {
          description 'Set scheduling policy for a certain interface'
                      ;
          list interface {
            description 'Set scheduling policy for a certain interface'
                        ;
            key if-name ;
            leaf if-name {
              description 'Name of the attaching tunnel'
                          ;
              type ncd:ifname {
                length 1..31 {
                  description 'Name of the attaching tunnel'
                              ;
                }
              }
            }
            choice schedule {
              description 'Configure schedule policy'
                          ;
              mandatory true ;
              case sche-group {
                description 'Configure schedule based on the combination of sch'
                          + 'edule policy'
                            ;
                container queue-schedule {
                  description 'Configure queue schedule'
                              ;
                  presence 'Configure queue schedule'
                           ;
                  choice queue-schedule {
                    description 'Select the type of queue schedule'
                                ;
                    mandatory true ;
                    case pq {
                      description 'Set PQ(Priority Queuing) scheduling between '
                                + 'transmitting entities'
                                  ;
                      leaf priority-level {
                        description 'Set the priority level of PQ, support <1-4>'
                                    ;
                        type uint8 {
                          range 1..4 {
                            description 'The priority level of PQ, support<1-4>'
                                        ;
                          }
                        }
                      }
                    }
                    case wfq {
                      description 'Set WFQ(Weighted Fair Queuing) scheduling be'
                                + 'tween transmitting entities'
                                  ;
                      leaf wfq-weight {
                        description 'Set the weight of WFQ, support <1-100>'
                                    ;
                        type uint8 {
                          range 1..100 {
                            description 'The weight of WFQ, support <1-100>'
                                        ;
                          }
                        }
                      }
                    }
                  }
                }
                leaf pmap-name {
                  description 'Name of scheduling policy based on PHB, support '
                            + '1-31 characters'
                              ;
                  type string {
                    length 1..31 {
                      description 'Name of the policy map, support 1-31 charact'
                                + 'ers'
                                  ;
                    }
                  }
                }
              }
            }
          }
        }
        container pws {
          description 'Set scheduling policy for a certain PW'
                      ;
          list pw {
            description 'Set scheduling policy for a certain PW'
                        ;
            key pw-name ;
            leaf pw-name {
              description 'Name of the PW, support 1-31 characters'
                          ;
              type string {
                length 1..31 {
                  description 'The name of PW, support 1-31 characters'
                              ;
                }
              }
            }
            choice schedule {
              description 'Configure schedule policy'
                          ;
              mandatory true ;
              case sche-group {
                description 'Configure schedule based on the combination of sch'
                          + 'edule policy'
                            ;
                container queue-schedule {
                  description 'Configure queue schedule'
                              ;
                  presence 'Configure queue schedule'
                           ;
                  choice queue-schedule {
                    description 'Select the type of queue schedule'
                                ;
                    mandatory true ;
                    case pq {
                      description 'Set PQ(Priority Queuing) scheduling between '
                                + 'transmitting entities'
                                  ;
                      leaf priority-level {
                        description 'Set the priority level of PQ, support <1-4>'
                                    ;
                        type uint8 {
                          range 1..4 {
                            description 'The priority level of PQ, support<1-4>'
                                        ;
                          }
                        }
                      }
                    }
                    case wfq {
                      description 'Set WFQ(Weighted Fair Queuing) scheduling be'
                                + 'tween transmitting entities'
                                  ;
                      leaf wfq-weight {
                        description 'Set the weight of WFQ, support <1-100>'
                                    ;
                        type uint8 {
                          range 1..100 {
                            description 'The weight of WFQ, support <1-100>'
                                        ;
                          }
                        }
                      }
                    }
                  }
                }
                leaf pmap-name {
                  description 'Name of scheduling policy based on PHB, support '
                            + '1-31 characters'
                              ;
                  type string {
                    length 1..31 {
                      description 'Name of the policy map, support 1-31 charact'
                                + 'ers'
                                  ;
                    }
                  }
                }
                leaf statistical-share {
                  description 'Set statistical share, as follows,'+"\n"
                            + '     false  statistical-share is not configured'+"\n"
                            + '     ture   statistical-share is configured'
                              ;
                  type boolean ;
                  default false ;
                  ncd:revise-date 2021-03-04 ;
                }
              }
            }
          }
        }
        container pw-ins {
          description 'Set ingress scheduling policy for a certain PW'
                      ;
          list pw-in {
            description 'Set ingress scheduling policy for a certain PW'
                        ;
            key pw-name ;
            leaf pw-name {
              description 'Name of the PW, support 1-31 characters'
                          ;
              type string {
                length 1..31 {
                  description 'The name of PW, support 1-31 characters'
                              ;
                }
              }
            }
            choice schedule {
              description 'Configure schedule policy'
                          ;
              mandatory true ;
              case sche-group {
                description 'Configure schedule based on the combination of sch'
                          + 'edule policy'
                            ;
                container queue-schedule {
                  description 'Configure queue schedule'
                              ;
                  presence 'Configure queue schedule'
                           ;
                  choice queue-schedule {
                    description 'Select the type of queue schedule'
                                ;
                    mandatory true ;
                    case pq {
                      description 'Set PQ(Priority Queuing) scheduling between '
                                + 'transmitting entities'
                                  ;
                      leaf priority-level {
                        description 'Set the priority level of PQ, support <1-4>'
                                    ;
                        type uint8 {
                          range 1..4 {
                            description 'The priority level of PQ, support<1-4>'
                                        ;
                          }
                        }
                      }
                    }
                    case wfq {
                      description 'Set WFQ(Weighted Fair Queuing) scheduling be'
                                + 'tween transmitting entities'
                                  ;
                      leaf wfq-weight {
                        description 'Set the weight of WFQ, support <1-100>'
                                    ;
                        type uint8 {
                          range 1..100 {
                            description 'The weight of WFQ, support <1-100>'
                                        ;
                          }
                        }
                      }
                    }
                  }
                }
                leaf pmap-name {
                  description 'Name of scheduling policy based on PHB, support '
                            + '1-31 characters'
                              ;
                  type string {
                    length 1..31 {
                      description 'Name of the policy map, support 1-31 charact'
                                + 'ers'
                                  ;
                    }
                  }
                }
                leaf statistical-share {
                  description 'Set statistical share, as follows,'+"\n"
                            + '     false  statistical-share is not configured'+"\n"
                            + '     ture   statistical-share is configured'
                              ;
                  type boolean ;
                  default false ;
                  ncd:revise-date 2021-03-04 ;
                }
              }
            }
          }
          ncd:revise-date 2021-01-18 ;
        }
        container tes {
          description 'Set scheduling policy for a certain TE.'
                      ;
          list te {
            description 'Set scheduling policy for a certain TE.'
                        ;
            key te-tunnel ;
            leaf te-tunnel {
              description 'Name of the attaching tunnel.'
                          ;
              type ncd:ifname ;
            }
            choice schedule {
              description 'Configure schedule policy'
                          ;
              mandatory true ;
              case sche-group {
                description 'Configure schedule based on the combination of sch'
                          + 'edule policy'
                            ;
                container queue-schedule {
                  description 'Configure queue schedule'
                              ;
                  presence 'Configure queue schedule'
                           ;
                  choice queue-schedule {
                    description 'Select the type of queue schedule'
                                ;
                    mandatory true ;
                    case pq {
                      description 'Set PQ(Priority Queuing) scheduling between '
                                + 'transmitting entities'
                                  ;
                      leaf priority-level {
                        description 'Set the priority level of PQ, support <1-4>'
                                    ;
                        type uint8 {
                          range 1..4 {
                            description 'The priority level of PQ, support<1-4>'
                                        ;
                          }
                        }
                      }
                    }
                    case wfq {
                      description 'Set WFQ(Weighted Fair Queuing) scheduling be'
                                + 'tween transmitting entities'
                                  ;
                      leaf wfq-weight {
                        description 'Set the weight of WFQ, support <1-100>'
                                    ;
                        type uint8 {
                          range 1..100 {
                            description 'The weight of WFQ, support <1-100>'
                                        ;
                          }
                        }
                      }
                    }
                  }
                }
                leaf pmap-name {
                  description 'Name of scheduling policy based on PHB, support '
                            + '1-31 characters'
                              ;
                  type string {
                    length 1..31 {
                      description 'Name of the policy map, support 1-31 charact'
                                + 'ers'
                                  ;
                    }
                  }
                }
              }
            }
          }
          ncd:revise-date 2021-03-24 ;
        }
        container bgp-ads {
          description 'Set scheduling policy for a certain BGP-AD.'
                      ;
          list bgp-ad {
            description 'Set scheduling policy for a certain BGP-AD.'
                        ;
            key 'vpls-name peer-router-id'
                ;
            leaf vpls-name {
              description 'Set VPLS instance name, support 1-32 characters.'
                          ;
              type string {
                length 1..32 ;
              }
            }
            leaf peer-router-id {
              description 'Set peer router id.'
                          ;
              type ncd:ipv4-address ;
            }
            choice schedule {
              description 'Configure schedule policy'
                          ;
              mandatory true ;
              case sche-group {
                description 'Configure schedule based on the combination of sch'
                          + 'edule policy'
                            ;
                container queue-schedule {
                  description 'Configure queue schedule'
                              ;
                  presence 'Configure queue schedule'
                           ;
                  choice queue-schedule {
                    description 'Select the type of queue schedule'
                                ;
                    mandatory true ;
                    case pq {
                      description 'Set PQ(Priority Queuing) scheduling between '
                                + 'transmitting entities'
                                  ;
                      leaf priority-level {
                        description 'Set the priority level of PQ, support <1-4>'
                                    ;
                        type uint8 {
                          range 1..4 {
                            description 'The priority level of PQ, support<1-4>'
                                        ;
                          }
                        }
                      }
                    }
                    case wfq {
                      description 'Set WFQ(Weighted Fair Queuing) scheduling be'
                                + 'tween transmitting entities'
                                  ;
                      leaf wfq-weight {
                        description 'Set the weight of WFQ, support <1-100>'
                                    ;
                        type uint8 {
                          range 1..100 {
                            description 'The weight of WFQ, support <1-100>'
                                        ;
                          }
                        }
                      }
                    }
                  }
                }
                leaf pmap-name {
                  description 'Name of scheduling policy based on PHB, support '
                            + '1-31 characters'
                              ;
                  type string {
                    length 1..31 {
                      description 'Name of the policy map, support 1-31 charact'
                                + 'ers'
                                  ;
                    }
                  }
                }
              }
            }
          }
          ncd:revise-date 2021-01-11 ;
        }
      }
      container switch-fabrics {
        if-feature switch-fabric ;
        description 'Configure H-QoS switch fabric policy bind'
                    ;
        container normals {
          description 'Configure H-QoS switch fabric policy bind based on shelf'
                    + ' and slot'
                      ;
          list normal {
            description 'Configure H-QoS switch fabric policy bind based on she'
                      + 'lf and slot'
                        ;
            key 'shelf slot mode'
                ;
            leaf shelf {
              description 'Specify the shelf number, support <0-7>'
                          ;
              type uint8 {
                range 0..7 {
                  description 'The shelf number, support <0-7>'
                              ;
                }
              }
            }
            leaf slot {
              description 'Specify the slot number, support <0-17>'
                          ;
              type uint8 {
                range 0..17 {
                  description 'The slot number, support <0-17>'
                              ;
                }
              }
            }
            leaf mode {
              description 'Set switch fabric mode, such as unicast, multicast'
                          ;
              type enumeration {
                enum unicast {
                  value 1 ;
                  description 'Specify unicast mode'
                              ;
                }
                enum multicast {
                  value 2 ;
                  description 'Specify multicast mode'
                              ;
                }
              }
            }
            leaf pmap-name {
              description 'Name of the policy based on switch-fabric, support 1'
                        + '-31 characters'
                          ;
              type string {
                length 1..31 {
                  description 'Name of the policy map, support 1-31 characters'
                              ;
                }
              }
              mandatory true ;
            }
          }
        }
        container subslots {
          description 'Configure H-QoS switch fabric policy bind, support subsl'
                    + 'ot'
                      ;
          list subslot {
            description 'Configure H-QoS switch fabric policy bind, support sub'
                      + 'slot'
                        ;
            key 'shelf slot mode subslot'
                ;
            leaf shelf {
              description 'Specify the shelf number, support <0-7>'
                          ;
              type uint8 {
                range 0..7 {
                  description 'The shelf number, support <0-7>'
                              ;
                }
              }
            }
            leaf slot {
              description 'Specify the slot number, support <0-17>'
                          ;
              type uint8 {
                range 0..17 {
                  description 'The slot number, support <0-17>'
                              ;
                }
              }
            }
            leaf mode {
              description 'Set switch fabric mode, only unicast in the case of '
                        + 'supporting subslot'
                          ;
              type enumeration {
                enum unicast {
                  value 1 ;
                  description 'Specify unicast mode'
                              ;
                }
              }
            }
            leaf subslot {
              description 'Specify the subslot number, support <0-3>'
                          ;
              type uint8 {
                range 0..3 {
                  description 'The subslot number, support <0-3>'
                              ;
                }
              }
            }
            leaf pmap-name {
              description 'Name of the policy based on switch-fabric, support 1'
                        + '-31 characters'
                          ;
              type string {
                length 1..31 {
                  description 'Name of the policy map, support 1-31 characters'
                              ;
                }
              }
              mandatory true ;
            }
          }
          container group1s {
            description 'Configure H-QoS switch fabric policy bind, support par'
                      + 'ameter template for subslot 0 and 1'
                        ;
            list group1 {
              description 'Configure H-QoS switch fabric policy bind, support p'
                        + 'arameter template for subslot 0 and 1'
                          ;
              key 'shelf slot mode'
                  ;
              leaf shelf {
                description 'Specify the shelf number, support <0-7>'
                            ;
                type uint8 {
                  range 0..7 {
                    description 'The shelf number, support <0-7>'
                                ;
                  }
                }
              }
              leaf slot {
                description 'Specify the slot number, support <0-17>'
                            ;
                type uint8 {
                  range 0..17 {
                    description 'The slot number, support <0-17>'
                                ;
                  }
                }
              }
              leaf mode {
                description 'Set switch fabric mode, only multicast in the case'
                          + ' of supporting parameter template for subslot 0 an'
                          + 'd 1'
                            ;
                type enumeration {
                  enum multicast {
                    value 2 ;
                    description 'Specify multicast mode'
                                ;
                  }
                }
              }
              leaf pmap-name {
                description 'Name of the policy based on switch-fabric, support'
                          + ' 1-31 characters'
                            ;
                type string {
                  length 1..31 {
                    description 'Name of the policy map, support 1-31 characters'
                                ;
                  }
                }
                mandatory true ;
              }
            }
          }
          container group2s {
            description 'Configure H-QoS switch fabric policy bind, support par'
                      + 'ameter template for subslot 2 and 3'
                        ;
            list group2 {
              description 'Configure H-QoS switch fabric policy bind, support p'
                        + 'arameter template for subslot 2 and 3'
                          ;
              key 'shelf slot mode'
                  ;
              leaf shelf {
                description 'Specify the shelf number, support <0-7>'
                            ;
                type uint8 {
                  range 0..7 {
                    description 'The shelf number, support <0-7>'
                                ;
                  }
                }
              }
              leaf slot {
                description 'Specify the slot number, support <0-17>'
                            ;
                type uint8 {
                  range 0..17 {
                    description 'The slot number, support <0-17>'
                                ;
                  }
                }
              }
              leaf mode {
                description 'Set switch fabric mode, only multicast in the case'
                          + ' of supporting parameter template for subslot 2 an'
                          + 'd 3'
                            ;
                type enumeration {
                  enum multicast {
                    value 2 ;
                    description 'Specify multicast mode'
                                ;
                  }
                }
              }
              leaf pmap-name {
                description 'Name of the policy based on switch-fabric, support'
                          + ' 1-31 characters'
                            ;
                type string {
                  length 1..31 {
                    description 'Name of the policy map, support 1-31 characters'
                                ;
                  }
                }
                mandatory true ;
              }
            }
          }
          container ports {
            description 'Configure H-QoS switch fabric policy bind, support port'
                        ;
            list port {
              description 'Configure H-QoS switch fabric policy bind, support p'
                        + 'ort'
                          ;
              key 'shelf slot mode subslot port'
                  ;
              leaf shelf {
                description 'Specify the shelf number, support <0-7>'
                            ;
                type uint8 {
                  range 0..7 {
                    description 'The shelf number, support <0-7>'
                                ;
                  }
                }
              }
              leaf slot {
                description 'Specify the slot number, support <0-17>'
                            ;
                type uint8 {
                  range 0..17 {
                    description 'The slot number, support <0-17>'
                                ;
                  }
                }
              }
              leaf mode {
                description 'Set switch fabric mode, only unicast and switch-po'
                          + 'rt in the case of supporting parameter template fo'
                          + 'r subslot'
                            ;
                type enumeration {
                  enum unicast {
                    value 1 ;
                    description 'Specify unicast mode'
                                ;
                  }
                  enum switch-port {
                    value 3 ;
                    description 'Specify switch-port mode'
                                ;
                  }
                }
              }
              leaf subslot {
                description 'Specify the subslot number, support <0-3>'
                            ;
                type uint8 {
                  range 0..3 {
                    description 'The subslot number, support <0-3>'
                                ;
                  }
                }
              }
              leaf port {
                description 'Specify the port number, support <1-48>'
                            ;
                type uint8 {
                  range 1..48 {
                    description 'The port number, support <1-48>'
                                ;
                  }
                }
              }
              leaf pmap-name {
                description 'Name of the policy based on switch-fabric, support'
                          + ' 1-31 characters'
                            ;
                type string {
                  length 1..31 {
                    description 'Name of the policy map, support 1-31 characters'
                                ;
                  }
                }
                mandatory true ;
              }
            }
          }
        }
        container interfaces {
          description 'Configure H-QoS switch fabric policy bind based on inter'
                    + 'face.'
                      ;
          list interface {
            description 'Configure H-QoS switch fabric policy bind based on int'
                      + 'erface.'
                        ;
            key 'interface mode'
                ;
            leaf interface {
              description 'Configure the name of the attaching interface.'
                          ;
              type ncd:ifname ;
            }
            leaf mode {
              description 'Set switch fabric mode, such as unicast.'
                          ;
              type enumeration {
                enum unicast {
                  value 1 ;
                  description 'Specify unicast mode'
                              ;
                }
              }
            }
            leaf pmap-name {
              description 'Name of the policy based on switch-fabric.'
                          ;
              type string {
                length 1..31 ;
              }
              mandatory true ;
            }
          }
          ncd:revise-date 2020-08-25 ;
        }
      }
      container traffic-shapes {
        if-feature traffic-shape ;
        description 'Configure traffic shape'
                    ;
        list traffic-shape {
          description 'Configure traffic shape'
                      ;
          key if-name ;
          leaf if-name {
            description 'Name of the interface'
                        ;
            type ncd:ifname {
              length 1..31 {
                description 'Name of the interface, support 1-31 characters'
                            ;
              }
            }
          }
          leaf rate {
            description 'Rate in kilobits per second, support <8-100000000>'
                        ;
            type uint32 {
              range 8..100000000 {
                description 'Rate in kilobits per second'
                            ;
              }
            }
            units kbps ;
            mandatory true ;
          }
          container burst {
            description 'Configure burst and exburst size in KB'
                        ;
            presence 'Configure burst and exburst size in KB'
                     ;
            leaf burst-size {
              description 'Burst size in KB, support <2-250000000>'
                          ;
              type uint32 {
                range 2..250000000 {
                  description 'Burst size in KB, support <2-250000000>'
                              ;
                }
              }
              units KB ;
              mandatory true ;
            }
            container excess-burst {
              description 'Configure exburst'
                          ;
              presence 'Configure exburst'
                       ;
              leaf exburst-size {
                description 'Excess burst size in KB, support <2-250000000>'
                            ;
                type uint32 {
                  range 2..250000000 {
                    description 'Excess burst size in KB, support <2-250000000>'
                                ;
                  }
                }
                units KB ;
                mandatory true ;
              }
            }
          }
          container network-header-len {
            description 'Length of network header'
                        ;
            presence 'Length of network header'
                     ;
            leaf network-header-length {
              description 'Length of network header'
                          ;
              type int32 {
                range -63..63 {
                  description 'Length of network header'
                              ;
                }
              }
              mandatory true ;
            }
            ncd:revise-date 2020-06-02 ;
          }
          leaf statistical-share {
            description 'Set statistical share, as follows,'+"\n"
                      + '     false  statistical-share is not configured'+"\n"
                      + '     ture   statistical-share is configured'
                        ;
            type boolean ;
            default false ;
            ncd:revise-date 2021-01-18 ;
          }
        }
      }
      container traffic-shape-dirs {
        if-feature traffic-shape-dir ;
        description 'Configure traffic shape on the specific interface and dire'
                  + 'ction'
                    ;
        list traffic-shape-dir {
          description 'Configure traffic shape on the specific interface and di'
                    + 'rection'
                      ;
          key 'if-name direction'
              ;
          leaf if-name {
            description 'Name of the interface'
                        ;
            type ncd:ifname {
              length 1..31 {
                description 'Name of the interface, support 1-31 characters'
                            ;
              }
            }
          }
          leaf direction {
            description 'Configure the interface direction, as follow'+"\n"
                      + '     input  Attaches to the input interface'
                        ;
            type enumeration {
              enum input {
                value 1 ;
                description 'Attaches to the input interface'
                            ;
              }
            }
          }
          leaf rate {
            description 'Rate in kilobits per second, support <8-100000000>'
                        ;
            type uint32 {
              range 8..100000000 {
                description 'Rate in kilobits per second'
                            ;
              }
            }
            units kbps ;
            mandatory true ;
          }
          container burst {
            description 'Configure burst and exburst size in KB'
                        ;
            presence 'Configure burst and exburst size in KB'
                     ;
            leaf burst-size {
              description 'Burst size in KB, support <2-250000000>'
                          ;
              type uint32 {
                range 2..250000000 {
                  description 'Burst size in KB, support <2-250000000>'
                              ;
                }
              }
              units KB ;
              mandatory true ;
            }
            container excess-burst {
              description 'Configure exburst'
                          ;
              presence 'Configure exburst'
                       ;
              leaf exburst-size {
                description 'Excess burst size in KB, support <2-250000000>'
                            ;
                type uint32 {
                  range 2..250000000 {
                    description 'Excess burst size in KB, support <2-250000000>'
                                ;
                  }
                }
                units KB ;
                mandatory true ;
              }
            }
          }
          container network-header-len {
            description 'Length of network header'
                        ;
            presence 'Length of network header'
                     ;
            leaf network-header-length {
              description 'Length of network header'
                          ;
              type int32 {
                range -63..63 {
                  description 'Length of network header'
                              ;
                }
              }
              mandatory true ;
            }
            ncd:revise-date 2020-06-02 ;
          }
          leaf statistical-share {
            description 'Set statistical share, as follows,'+"\n"
                      + '     false  statistical-share is not configured'+"\n"
                      + '     ture   statistical-share is configured'
                        ;
            type boolean ;
            default false ;
            ncd:revise-date 2021-01-18 ;
          }
        }
        ncd:revise-date 2017-01-16 ;
      }
      container qos-policys {
        status obsolete {
          ncd:revise-date 2015-04-15 ;
        }
        description 'Bind qos-policy to interface'
                    ;
        list qos-policy {
          status obsolete {
            ncd:revise-date 2015-04-15 ;
          }
          description 'Configue QPPB(QOS Policy Propagation Through the Border '
                    + 'Gateway Protocol)'
                      ;
          key 'if-name option direction'
              ;
          leaf if-name {
            status obsolete {
              ncd:revise-date 2015-04-15 ;
            }
            description 'Name of an interface, support 1-31 characters'
                        ;
            type ncd:ifname {
              length 1..31 {
                description 'Name of the interface, support 1-31 characters'
                            ;
              }
            }
          }
          leaf option {
            status obsolete {
              ncd:revise-date 2015-04-15 ;
            }
            description 'Specify ip precedence or qos id'
                        ;
            type enumeration {
              enum ip-precedence {
                value 3 ;
                description 'Set IP precedence'
                            ;
              }
              enum qos-id {
                value 4 ;
                description 'Set qos id'
                            ;
              }
            }
          }
          leaf direction {
            status obsolete {
              ncd:revise-date 2015-04-15 ;
            }
            description 'Specify the direction of IP, such as source, destinati'
                      + 'on'
                        ;
            type enumeration {
              enum source {
                value 1 ;
                description 'Check routemap by source IP'
                            ;
              }
              enum destination {
                value 2 ;
                description 'Check routemap by destination IP'
                            ;
              }
            }
          }
        }
      }
      container qos-policy-exs {
        description 'Bind qos-policy to interface'
                    ;
        list qos-policy-ex {
          description 'Configue QPPB(QOS Policy Propagation Through the Border '
                    + 'Gateway Protocol)'
                      ;
          key 'if-name option direction ip-protocol'
              ;
          leaf if-name {
            description 'Name of an interface, support 1-31 characters'
                        ;
            type ncd:ifname {
              length 1..31 {
                description 'Name of the interface, support 1-31 characters'
                            ;
              }
            }
          }
          leaf option {
            description 'Specify ip precedence or qos id'
                        ;
            type enumeration {
              enum ip-precedence {
                value 3 ;
                description 'Set IP precedence'
                            ;
              }
              enum qos-id {
                value 4 ;
                description 'Set qos id'
                            ;
              }
            }
          }
          leaf direction {
            description 'Specify the direction of IP, such as source, destinati'
                      + 'on'
                        ;
            type enumeration {
              enum source {
                value 1 ;
                description 'Check routemap by source IP'
                            ;
              }
              enum destination {
                value 2 ;
                description 'Check routemap by destination IP'
                            ;
              }
            }
          }
          leaf ip-protocol {
            description 'Specify the type of IP protocol, such as ipv4, ipv6.'
                        ;
            type enumeration {
              enum ipv4 {
                value 0 ;
                description 'IPv4 protocol'
                            ;
              }
              enum ipv6 {
                value 1 ;
                description 'IPv6 protocol'
                            ;
              }
            }
          }
        }
        ncd:revise-date 2015-04-15 ;
      }
      container mls-qos-modes {
        description 'Configure priority inherit on the interface'
                    ;
        list mls-qos-mode {
          description 'Configure priority inherit on the interface'
                      ;
          key if-name ;
          leaf if-name {
            description 'Configure the name of the attaching interface'
                        ;
            type ncd:ifname {
              length 1..31 {
                description 'Name of the attaching interface, support 1-31 char'
                          + 'acters'
                            ;
              }
            }
          }
          choice inherit-mode {
            description 'Inherit mode'
                        ;
            mandatory true ;
            case uniform {
              description 'Select uniform inherit mode'
                          ;
              leaf uniform {
                description 'Specify uniform inherit mode'
                            ;
                type empty ;
                mandatory true ;
              }
            }
            case pipe {
              description 'Select pipe inherit mode'
                          ;
              container pipe {
                description 'Select pipe inherit mode'
                            ;
                leaf pipe {
                  description 'Specify pipe inherit mode'
                              ;
                  type empty ;
                  mandatory true ;
                }
                container servclass-color {
                  description 'Configure service-calss and color'
                              ;
                  presence 'Configure service-calss and color'
                           ;
                  leaf service-class {
                    description 'Specify server class of PHB info, support <af1'
                              + ',af2,af3,af4,be,cs6,cs7,ef>'
                                ;
                    type qos-service-class ;
                    mandatory true ;
                  }
                  leaf color-type {
                    description 'Specify packets color, support <green,yellow,r'
                              + 'ed>'
                                ;
                    type qos-color-type ;
                    mandatory true ;
                  }
                }
              }
            }
            case short-pipe {
              description 'Select short-pipe inherit mode'
                          ;
              container short-pipe {
                description 'Select short-pipe inherit mode'
                            ;
                leaf short-pipe {
                  description 'Specify short-pipe inherit mode'
                              ;
                  type empty ;
                  mandatory true ;
                }
                container servclass-color {
                  description 'Configure service-calss and color'
                              ;
                  presence 'Configure service-calss and color'
                           ;
                  leaf service-class {
                    description 'Specify server class of PHB info, support <af1'
                              + ',af2,af3,af4,be,cs6,cs7,ef>'
                                ;
                    type qos-service-class ;
                    mandatory true ;
                  }
                  leaf color-type {
                    description 'Specify packets color, support <green,yellow,r'
                              + 'ed>'
                                ;
                    type qos-color-type ;
                    mandatory true ;
                  }
                }
              }
            }
          }
        }
      }
      container qos-dot1p {
        description 'Configure 802.1p inherit on the interface'
                    ;
        container cvlan-ins {
          description 'Inherit from ingress 802.1p on inner VLAN'
                      ;
          list cvlan-in {
            description 'Inherit from ingress 802.1p on inner VLAN'
                        ;
            key if-name ;
            leaf if-name {
              description 'Configure the name of the attaching interface'
                          ;
              type ncd:ifname {
                length 1..31 {
                  description 'Name of the attaching interface, support 1-31 ch'
                            + 'aracters'
                              ;
                }
              }
            }
          }
        }
        container cvlan-outs {
          description 'Inherit from egress 802.1p on inner VLAN'
                      ;
          list cvlan-out {
            description 'Inherit from egress 802.1p on inner VLAN'
                        ;
            key if-name ;
            leaf if-name {
              description 'Configure the name of the attaching interface'
                          ;
              type ncd:ifname {
                length 1..31 {
                  description 'Name of the attaching interface, support 1-31 ch'
                            + 'aracters'
                              ;
                }
              }
            }
          }
        }
        container defaults {
          description 'Inherit by default way, that is, inherit from 802.1p on '
                    + 'outer VLAN with ingress and egress'
                      ;
          list default {
            description 'Inherit by default way, that is, inherit from 802.1p o'
                      + 'n outer VLAN with ingress and egress'
                        ;
            key if-name ;
            leaf if-name {
              description 'Configure the name of the attaching interface'
                          ;
              type ncd:ifname {
                length 1..31 {
                  description 'Name of the attaching interface, support 1-31 ch'
                            + 'aracters'
                              ;
                }
              }
            }
          }
        }
      }
      container ttl-qos-modes {
        description 'Configure TTL duplicate on the interface'
                    ;
        list ttl-qos-mode {
          description 'Configure TTL duplicate on the interface'
                      ;
          key if-name ;
          leaf if-name {
            description 'Configure the name of the attaching interface'
                        ;
            type ncd:ifname {
              length 1..31 {
                description 'Name of the attaching interface, support 1-31 char'
                          + 'acters'
                            ;
              }
            }
          }
          leaf inherit-mode {
            description 'Specify inherit mode, such as uniform, pipe'
                        ;
            type enumeration {
              enum uniform {
                value 1 ;
                description 'Select uniform mode'
                            ;
              }
              enum pipe {
                value 2 ;
                description 'Select pipe mode'
                            ;
              }
            }
            mandatory true ;
          }
        }
      }
      container qos-stats {
        description 'To enable or disable the QoS flow statistics'
                    ;
        container stats-switch {
          description 'The QoS flow statistics switch'
                      ;
          list stats-switches {
            description 'The QoS flow statistics switch'
                        ;
            key 'if-name flow-direction'
                ;
            leaf if-name {
              description 'The interface which to be enbled statistics'
                          ;
              type ncd:ifname ;
            }
            leaf flow-direction {
              description 'The flow direction, as follows,'+"\n"
                        + '     input  Attaches to the input flow'+"\n"
                        + '     output Attaches to the output flow'
                          ;
              type qos-direction ;
            }
            leaf statistics-group {
              description 'Specify statistics group ID.'
                          ;
              type uint32 {
                range 1..4000 ;
              }
              ncd:revise-date 2021-03-24 ;
            }
          }
        }
        ncd:revise-date 2015-11-04 ;
      }
      container pw-schedule-stats {
        description 'The configuration about PW schedule statistics.'
                    ;
        container stats-switches {
          description 'The PW schedule statistics switch in output direction.'
                      ;
          list stats-switch {
            description 'The PW schedule statistics switch in output direction.'
                        ;
            key pw-name ;
            leaf pw-name {
              description 'Name of the PW, support 1-31 characters.'
                          ;
              type string {
                length 1..31 {
                  description 'Name of the PW, support 1-31 characters.'
                              ;
                }
              }
            }
            leaf statistics-group {
              description 'Specify statistics group ID.'
                          ;
              type uint32 {
                range 1..4000 ;
              }
              ncd:revise-date 2021-03-24 ;
            }
          }
        }
        container stats-switch-ins {
          description 'The PW schedule statistics switch in input direction.'
                      ;
          list stats-switch-in {
            description 'The PW schedule statistics switch in input direction.'
                        ;
            key pw-name ;
            leaf pw-name {
              description 'Name of the PW, support 1-31 characters.'
                          ;
              type string {
                length 1..31 {
                  description 'Name of the PW, support 1-31 characters.'
                              ;
                }
              }
            }
            leaf statistics-group {
              description 'Specify statistics group ID.'
                          ;
              type uint32 {
                range 1..4000 ;
              }
              ncd:revise-date 2021-03-24 ;
            }
          }
          ncd:revise-date 2021-01-18 ;
        }
        ncd:revise-date 2016-05-03 ;
      }
      container te-schedule-stats {
        description 'The configuration about TE schedule statistics.'
                    ;
        container stats-switches {
          description 'The TE schedule statistics switch in output direction.'
                      ;
          list stats-switch {
            description 'The TE schedule statistics switch in output direction.'
                        ;
            key te-tunnel ;
            leaf te-tunnel {
              description 'Name of the attaching tunnel.'
                          ;
              type ncd:ifname ;
            }
            leaf statistics-group {
              description 'Specify statistics group ID.'
                          ;
              type uint32 {
                range 1..4000 ;
              }
            }
          }
        }
        ncd:revise-date 2021-03-24 ;
      }
      container bgpad-schedule-stats {
        description 'The configuration about BGP-AD schedule statistics.'
                    ;
        container stats-switches {
          description 'The BGP-AD schedule statistics switch.'
                      ;
          list stats-switches {
            description 'The BGP-AD schedule statistics switch.'
                        ;
            key 'vpls-name peer-router-id'
                ;
            leaf vpls-name {
              description 'Set VPLS instance name, support 1-32 characters.'
                          ;
              type string {
                length 1..32 ;
              }
            }
            leaf peer-router-id {
              description 'Set peer router id.'
                          ;
              type ncd:ipv4-address ;
            }
            leaf statistics-group {
              description 'Specify statistics group ID.'
                          ;
              type uint32 {
                range 1..4000 ;
              }
              ncd:revise-date 2021-03-24 ;
            }
          }
        }
        ncd:revise-date 2021-01-11 ;
      }
      container qos-vni-instances {
        if-feature qos-vni-instance ;
        description 'Bind H-QoS policys to the vni-instance.'
                    ;
        list qos-vni-instance {
          description 'Bind H-QoS policys to the vni-instance.'
                      ;
          key 'vni direction'
              ;
          leaf vni {
            description 'VNI value, range is 1-16777215.'
                        ;
            type uint32 {
              range 1..16777215 {
                description 'VNI value.'
                            ;
              }
            }
          }
          leaf direction {
            description 'Configure the direction, as follows,'+"\n"
                      + '     input  Attach to the direction of input.'+"\n"
                      + '     output Attach to the direction of output.'
                        ;
            type qos-direction ;
          }
          leaf pmap-name {
            description 'Name of the policy map bound on the vni-instance, supp'
                      + 'ort 1-31 characters.'
                        ;
            type string {
              length 1..31 {
                description 'Name of the policy map bound on the vni-instance.'
                            ;
              }
            }
            mandatory true ;
          }
        }
        ncd:revise-date 2016-06-30 ;
      }
      container flowspec {
        description 'Configure flowspec parameters.'
                    ;
        container address-family-ips {
          description 'Configure IP address family.'
                      ;
          list address-family-ip {
            description 'Configure IP address family.'
                        ;
            key ip-type ;
            leaf ip-type {
              description 'Specify IP type, such as IPv4.'
                          ;
              type enumeration {
                enum ipv4 {
                  value 4 ;
                  description 'IPv4 type.'
                              ;
                }
                enum ipv6 {
                  value 24 ;
                  description 'IPv6 type.'
                              ;
                }
              }
            }
            container interfaces {
              description 'Specify interface to enable/disable flowspec.'
                          ;
              list interface {
                description 'Specify interface to enable/disable flowspec.'
                            ;
                key if-name ;
                leaf if-name {
                  description 'Interface name.'
                              ;
                  type ncd:ifname ;
                }
                leaf flag {
                  description 'Configure the flag to indicate enable/disable fl'
                            + 'owspec feature.'
                              ;
                  type enumeration {
                    enum enable {
                      value 1 ;
                      description 'Enable flowspec.'
                                  ;
                    }
                    enum disable {
                      value 0 ;
                      description 'Disable flowspec.'
                                  ;
                    }
                  }
                }
              }
            }
            container local-install {
              description 'Local install.'
                          ;
              presence local-install ;
              leaf interface-all {
                description 'Specify all interface to enable flowspec.'
                            ;
                type empty ;
                mandatory true ;
              }
            }
            container service-policys {
              description 'Configure H-QoS policy.'
                          ;
              list service-policy {
                description 'Configure H-QoS policy.'
                            ;
                key pmap-name ;
                leaf pmap-name {
                  description 'Name of attaching policy, support 1-31 character'
                            + 's.'
                              ;
                  type string {
                    length 1..31 {
                      description 'Name of attaching policy, support 1-31 chara'
                                + 'cters.'
                                  ;
                    }
                  }
                }
              }
            }
          }
        }
        container address-family-vrfs {
          description 'Configure VRF address family.'
                      ;
          list address-family-vrf {
            description 'Configure VRF address family.'
                        ;
            key 'ip-type vrf-name'
                ;
            leaf ip-type {
              description 'Specify IP type, such as IPv4.'
                          ;
              type enumeration {
                enum ipv4 {
                  value 4 ;
                  description 'IPv4 type.'
                              ;
                }
                enum ipv6 {
                  value 24 ;
                  description 'IPv6 type.'
                              ;
                }
              }
            }
            leaf vrf-name {
              description 'Virtual route forwarding name, support 1-32 characte'
                        + 'rs.'
                          ;
              type string {
                length 1..32 {
                  description 'Virtual route forwarding name, support 1-32 char'
                            + 'acters.'
                              ;
                }
              }
            }
            container interfaces {
              description 'Specify interface to enable/disable flowspec.'
                          ;
              list interface {
                description 'Specify interface to enable/disable flowspec.'
                            ;
                key if-name ;
                leaf if-name {
                  description 'Interface name.'
                              ;
                  type ncd:ifname ;
                }
                leaf flag {
                  description 'Configure the flag to indicate enable/disable fl'
                            + 'owspec feature.'
                              ;
                  type enumeration {
                    enum enable {
                      value 1 ;
                      description 'Enable flowspec.'
                                  ;
                    }
                    enum disable {
                      value 0 ;
                      description 'Disable flowspec.'
                                  ;
                    }
                  }
                }
              }
            }
            container local-install {
              description 'Local install.'
                          ;
              presence local-install ;
              leaf interface-all {
                description 'Specify all interface to enable flowspec.'
                            ;
                type empty ;
                mandatory true ;
              }
            }
            container service-policys {
              description 'Configure H-QoS policy.'
                          ;
              list service-policy {
                description 'Configure H-QoS policy.'
                            ;
                key pmap-name ;
                leaf pmap-name {
                  description 'Name of attaching policy, support 1-31 character'
                            + 's.'
                              ;
                  type string {
                    length 1..31 {
                      description 'Name of attaching policy, support 1-31 chara'
                                + 'cters.'
                                  ;
                    }
                  }
                }
              }
            }
          }
        }
        ncd:revise-date 2017-06-12 ;
      }
      container qos-prioritys-remark {
        if-feature qos-prioritys-remark ;
        description 'Configure the type of priority remarked by QoS'
                    ;
        list qos-priority-remark {
          description 'Configure the type of priority remarked by QoS'
                      ;
          key 'if-name priority-type'
              ;
          leaf if-name {
            description 'Specify the name of interface applied, support 1-31 ch'
                      + 'aracters'
                        ;
            type ncd:ifname {
              length 1..31 {
                description 'Name of the interface, support 1-31 characters'
                            ;
              }
            }
          }
          leaf priority-type {
            description 'Set the priority type remarked by interface, such as 8'
                      + '02.1p, dscp or exp.'
                        ;
            type enumeration {
              enum 8021p {
                value 1 ;
                description 'Based on 802.1p'
                            ;
              }
              enum ip-dscp {
                value 2 ;
                description 'Based on IP DSCP'
                            ;
              }
              enum mpls-exp {
                value 3 ;
                description 'Based on MPLS EXP'
                            ;
              }
            }
          }
          leaf enable-switch {
            if-feature ds-interf-priority-remark-enable ;
            description 'Configure the interface priority modification is enabl'
                      + 'ed or disable.'
                        ;
            type enumeration {
              enum enable {
                value 1 ;
                description 'The switch is enable.'
                            ;
              }
              enum disable {
                value 2 ;
                description 'The switch is disable.'
                            ;
              }
            }
            mandatory true ;
            ncd:revise-date 2021-01-25 ;
          }
        }
        ncd:revise-date 2018-08-18 ;
      }
      container queue-templates {
        description 'Configure the queue template'
                    ;
        list queue-template {
          description 'Configure the queue template'
                      ;
          key queue-temp-name ;
          leaf queue-temp-name {
            description 'Name of the queue template (1-31 characters)'
                        ;
            type string {
              length 1..31 {
                description 'Name of the queue template (1-31 characters)'
                            ;
              }
            }
          }
          container queue-nos {
            description 'Specify queue'
                        ;
            list queue-no {
              description 'Specify queue'
                          ;
              key queue ;
              leaf queue {
                description 'Select service class of PHB info, see below:'+"\n"
                          + '  be (1) Best effort'+"\n"
                          + '  af1(2) Assured forwarding class 1'+"\n"
                          + '  af2(3) Assured forwarding class 2'+"\n"
                          + '  af3(4) Assured forwarding class 3'+"\n"
                          + '  af4(5) Assured forwarding class 4'+"\n"
                          + '  ef (6) Expedited forward'+"\n"
                          + '  cs6(7) Internetwork control service class'+"\n"
                          + '  cs7(8) Network control service class'
                            ;
                type qos-service-class ;
              }
              container priority-level {
                description 'Configure PQ(Priority Queuing) priority level'
                            ;
                presence 'Configure PQ priority level'
                         ;
                leaf priority-value {
                  description 'Set the priority level of PQ, support <1-8>'
                              ;
                  type uint32 {
                    range 1..16 ;
                  }
                  mandatory true ;
                }
              }
              container queue-limit {
                description 'Configure queue depth'
                            ;
                presence 'Configure queue depth'
                         ;
                leaf queue-depth {
                  description 'Set queue depth, such as 64KB, 128KB, 512KB, 100'
                            + '0KB, 4000KB, 8000KB, 24000KB, 64000KB, 96000KB, '
                            + '192000KB,1000000KB,128000KB,16KB,16000KB,2000KB,'
                            + '24KB,512000KB,7KB,8000000KB'
                              ;
                  type enumeration {
                    enum 64 {
                      value 3 ;
                      description 'Set queue depth to 64KB'
                                  ;
                    }
                    enum 128 {
                      value 14 ;
                      description 'Set queue depth to 128KB'
                                  ;
                    }
                    enum 512 {
                      value 4 ;
                      description 'Set queue depth to 512KB'
                                  ;
                    }
                    enum 1000 {
                      value 15 ;
                      description 'Set queue depth to 1000KB'
                                  ;
                    }
                    enum 4000 {
                      value 16 ;
                      description 'Set queue depth to 4000KB'
                                  ;
                    }
                    enum 8000 {
                      value 6 ;
                      description 'Set queue depth to 8000KB'
                                  ;
                    }
                    enum 24000 {
                      value 9 ;
                      description 'Set queue depth to 24000KB'
                                  ;
                    }
                    enum 64000 {
                      value 10 ;
                      description 'Set queue depth to 64000KB'
                                  ;
                    }
                    enum 96000 {
                      value 17 ;
                      description 'Set queue depth to 96000KB'
                                  ;
                    }
                    enum 192000 {
                      value 18 ;
                      description 'Set queue depth to 192000KB'
                                  ;
                    }
                    enum 1000000 {
                      value 13 ;
                      description 'Set queue depth to 1000000KB'
                                  ;
                    }
                    enum 128000 {
                      value 11 ;
                      description 'Set queue depth to 128000KB'
                                  ;
                    }
                    enum 16 {
                      value 1 ;
                      description 'Set queue depth to 16KB'
                                  ;
                    }
                    enum 16000 {
                      value 8 ;
                      description 'Set queue depth to 16000KB'
                                  ;
                    }
                    enum 2000 {
                      value 5 ;
                      description 'Set queue depth to 2000KB'
                                  ;
                    }
                    enum 24 {
                      value 2 ;
                      description 'Set queue depth to 24KB'
                                  ;
                    }
                    enum 512000 {
                      value 12 ;
                      description 'Set queue depth to 512000KB'
                                  ;
                    }
                    enum 7 {
                      value 7 ;
                      description 'Set queue depth to 7KB'
                                  ;
                    }
                    enum 8000000 {
                      value 21 ;
                      description 'Set queue depth to 8000000KB'
                                  ;
                    }
                  }
                  units KB ;
                  mandatory true ;
                }
              }
              container shape {
                description 'Configure shape'
                            ;
                presence 'Configure shape'
                         ;
                choice shape {
                  description 'Configure shape'
                              ;
                  mandatory true ;
                  case cir-cbs {
                    description 'Configure the CIR(Committed Information Rate) '
                              + 'value'
                                ;
                    leaf cir {
                      description 'Configure the CIR(Committed Information Rate'
                                + ') value (default: kilobits per second),suppo'
                                + 'rt <8-4294967295>'
                                  ;
                      type uint32 {
                        range 8..4294967295 {
                          description 'The CIR value (default: kilobits per sec'
                                    + 'ond),support <8-4294967295>.'
                                      ;
                        }
                      }
                      mandatory true ;
                    }
                    leaf cbs {
                      description 'Configure the CBS(Committed Burst Size) size'
                                + ' (default: KB), support <1-4294967295>.'
                                  ;
                      type uint32 {
                        range 1..4294967295 {
                          description 'The CBS(Committed Burst Size) size (defa'
                                    + 'ult: KB), support <1-4294967295>'
                                      ;
                        }
                      }
                    }
                    container pir-pbs {
                      description 'Configure the PIR.'
                                  ;
                      presence pir ;
                      leaf pir-value {
                        description 'Configure the EIR(Excess Information Rate)'
                                  + ' value (default: kilobits per second)'
                                    ;
                        type uint32 {
                          range 8..4294967295 {
                            description 'The PIR value.'
                                        ;
                          }
                        }
                        mandatory true ;
                      }
                      leaf pbs-value {
                        description 'Configure the PBS.'
                                    ;
                        type uint32 {
                          range 1..4294967295 {
                            description 'The PBS.'
                                        ;
                          }
                        }
                      }
                      ncd:revise-date 2021-01-25 ;
                    }
                  }
                  case cir-percentage {
                    description 'Set the CIR percentage'
                                ;
                    leaf percentage {
                      description 'Set the CIR percentage,support <1-100>'
                                  ;
                      type uint8 {
                        range 1..100 {
                          description 'Set the CIR percentage,support <1-100>.'
                                      ;
                        }
                      }
                      mandatory true ;
                    }
                    container pir-percentage {
                      description 'Configure PIR in percentage.'
                                  ;
                      leaf pir-percentage {
                        description 'Configure PIR in percentage.'
                                    ;
                        type uint8 {
                          range 1..100 {
                            description 'Configure PIR with percentage form.'
                                        ;
                          }
                        }
                      }
                      ncd:revise-date 2021-01-25 ;
                    }
                  }
                  ncd:revise-date 2019-06-13 ;
                }
              }
              container wfq-weight {
                description 'Configure WFQ weight'
                            ;
                presence 'Configure WFQ weight'
                         ;
                leaf percentage {
                  description 'Set the weight of WFQ, support <1-100>'
                              ;
                  type uint32 {
                    range 1..100 ;
                  }
                  mandatory true ;
                }
              }
              container random-detect {
                description 'Configure WRED information'
                            ;
                presence 'Configure WRED information'
                         ;
                container color {
                  description 'Configure WRED thresholds based on color'
                              ;
                  presence 'Configure WRED thresholds based on color'
                           ;
                  container green {
                    description 'Green packets'
                                ;
                    presence 'Green packets'
                             ;
                    choice threshold {
                      description 'Set the threshold'
                                  ;
                      mandatory true ;
                      case threshold-value {
                        description 'Set the threshold value'
                                    ;
                        leaf min-threshold {
                          description 'Set the minimum threshold in kilobytes, '
                                    + 'support <1-1024000>'
                                      ;
                          type uint32 {
                            range 1..4294967295 {
                              description 'Set the minimum threshold in kilobytes'
                                          ;
                            }
                          }
                          units KB ;
                          mandatory true ;
                        }
                        leaf max-threshold {
                          description 'Set the maximum threshold in kilobytes, '
                                    + 'support <1-1024000>'
                                      ;
                          type uint32 {
                            range 1..4294967295 {
                              description 'Set the maximum threshold in kilobytes'
                                          ;
                            }
                          }
                          units KB ;
                          mandatory true ;
                        }
                      }
                      case threshold-percentage {
                        description 'Set the threshold percentage'
                                    ;
                        container threshold-percentage {
                          description 'Set the threshold percentage'
                                      ;
                          leaf min-threshold-percentage {
                            description 'Set the minimum threshold percentage, support <1-100>'
                                        ;
                            type uint32 {
                              range 1..100 ;
                            }
                            mandatory true ;
                          }
                          leaf max-threshold-percentage {
                            description 'Set the maximum threshold percentage, support <1-100>'
                                        ;
                            type uint32 {
                              range 1..100 ;
                            }
                            mandatory true ;
                          }
                        }
                        ncd:revise-date 2020-11-11 ;
                      }
                    }
                    leaf probility {
                      description 'Set mark probability denominator, support <1'
                                + '-100>'
                                  ;
                      type uint32 {
                        range 1..100 {
                          description 'Set mark probability denominator'
                                      ;
                        }
                      }
                      mandatory true ;
                    }
                  }
                  container yellow {
                    description 'Yellow packets'
                                ;
                    presence 'Yellow packets'
                             ;
                    choice threshold {
                      description 'Set the threshold'
                                  ;
                      mandatory true ;
                      case threshold-value {
                        description 'Set the threshold value'
                                    ;
                        leaf min-threshold {
                          description 'Set the minimum threshold in kilobytes, '
                                    + 'support <1-1024000>'
                                      ;
                          type uint32 {
                            range 1..4294967295 {
                              description 'Set the minimum threshold in kilobytes'
                                          ;
                            }
                          }
                          units KB ;
                          mandatory true ;
                        }
                        leaf max-threshold {
                          description 'Set the maximum threshold in kilobytes, '
                                    + 'support <1-1024000>'
                                      ;
                          type uint32 {
                            range 1..4294967295 {
                              description 'Set the maximum threshold in kilobytes'
                                          ;
                            }
                          }
                          units KB ;
                          mandatory true ;
                        }
                      }
                      case threshold-percentage {
                        description 'Set the threshold percentage'
                                    ;
                        container threshold-percentage {
                          description 'Set the threshold percentage'
                                      ;
                          leaf min-threshold-percentage {
                            description 'Set the minimum threshold percentage, support <1-100>'
                                        ;
                            type uint32 {
                              range 1..100 ;
                            }
                            mandatory true ;
                          }
                          leaf max-threshold-percentage {
                            description 'Set the maximum threshold percentage, support <1-100>'
                                        ;
                            type uint32 {
                              range 1..100 ;
                            }
                            mandatory true ;
                          }
                        }
                        ncd:revise-date 2020-11-11 ;
                      }
                    }
                    leaf probility {
                      description 'Set mark probability denominator, support <1'
                                + '-100>'
                                  ;
                      type uint32 {
                        range 1..100 {
                          description 'Set mark probability denominator'
                                      ;
                        }
                      }
                      mandatory true ;
                    }
                  }
                  container red {
                    description 'Red packets'
                                ;
                    presence 'Red packets'
                             ;
                    choice threshold {
                      description 'Set the threshold'
                                  ;
                      mandatory true ;
                      case threshold-value {
                        description 'Set the threshold value'
                                    ;
                        leaf min-threshold {
                          description 'Set the minimum threshold in kilobytes, '
                                    + 'support <1-1024000>'
                                      ;
                          type uint32 {
                            range 1..4294967295 {
                              description 'Set the minimum threshold in kilobytes'
                                          ;
                            }
                          }
                          units KB ;
                          mandatory true ;
                        }
                        leaf max-threshold {
                          description 'Set the maximum threshold in kilobytes, '
                                    + 'support <1-1024000>'
                                      ;
                          type uint32 {
                            range 1..4294967295 {
                              description 'Set the maximum threshold in kilobytes'
                                          ;
                            }
                          }
                          units KB ;
                          mandatory true ;
                        }
                      }
                      case threshold-percentage {
                        description 'Set the threshold percentage'
                                    ;
                        container threshold-percentage {
                          description 'Set the threshold percentage'
                                      ;
                          leaf min-threshold-percentage {
                            description 'Set the minimum threshold percentage, support <1-100>'
                                        ;
                            type uint32 {
                              range 1..100 ;
                            }
                            mandatory true ;
                          }
                          leaf max-threshold-percentage {
                            description 'Set the maximum threshold percentage, support <1-100>'
                                        ;
                            type uint32 {
                              range 1..100 ;
                            }
                            mandatory true ;
                          }
                        }
                        ncd:revise-date 2020-11-11 ;
                      }
                    }
                    leaf probility {
                      description 'Set mark probability denominator, support <1'
                                + '-100>'
                                  ;
                      type uint32 {
                        range 1..100 {
                          description 'Set mark probability denominator'
                                      ;
                        }
                      }
                      mandatory true ;
                    }
                  }
                }
                container weight {
                  description 'Configure WRED exponential weight factor'
                              ;
                  presence 'Configure WRED exponential weight factor'
                           ;
                  leaf weight-value {
                    description 'Specify exponent used in weighted average calc'
                              + 'ulation, support <1-16>'
                                ;
                    type uint32 {
                      range 1..16 {
                        description Range. ;
                      }
                    }
                  }
                  ncd:revise-date 2021-01-25 ;
                }
                ncd:revise-date 2019-06-13 ;
              }
            }
          }
        }
        ncd:revise-date 2018-08-30 ;
      }
      container queue-interfaces {
        description 'Configure queue template bind on the interface'
                    ;
        list queue-interface {
          description 'Configure queue template bind on the interface'
                      ;
          key 'if-name if-direction'
              ;
          leaf if-name {
            description 'Configure the name of the attaching interface'
                        ;
            type ncd:ifname {
              length 1..31 {
                description 'Name of the attaching interface, support 1-31 char'
                          + 'acters'
                            ;
              }
            }
          }
          leaf if-direction {
            description 'Configure the interface direction, as follows,'+"\n"
                      + '     input  Attaches to the input interface'+"\n"
                      + '     output Attaches to the output interface'
                        ;
            type enumeration {
              enum input {
                value 1 ;
                description 'Attaches to the input interface'
                            ;
              }
              enum output {
                value 2 ;
                description 'Attaches to the output interface'
                            ;
              }
            }
          }
          leaf queue-temp-name {
            description 'Name of the queue template bound on the interface, sup'
                      + 'port 1-31 characters'
                        ;
            type string {
              length 1..31 {
                description 'Name of the queue template, support 1-31 characters'
                            ;
              }
            }
            mandatory true ;
          }
          leaf statistical-share {
            description 'Set statistical share, as follows,'+"\n"
                      + '     false  statistical-share is not configured'+"\n"
                      + '     ture   statistical-share is configured'
                        ;
            type boolean ;
          }
        }
        ncd:revise-date 2018-08-30 ;
      }
      container flow-behavior-application {
        description 'Configure flow-behavior application.'
                    ;
        container flow-behavior-apply-global {
          description 'Flow-behavior applied to global.'
                      ;
          presence 'Flow-behavior applied to global'
                   ;
          leaf pmap-name {
            description 'Name of the policy map bound on global, support 1-31 c'
                      + 'haracters.'
                        ;
            type string {
              length 1..31 {
                description 'Name of the policy map bound on the vni-instance.'
                            ;
              }
            }
            mandatory true ;
          }
          leaf flow-behavior-apply-desc {
            description 'Description of flow behavior application, support 1-79'
                      + ' characters.'
                        ;
            type ncd:string-with-blank {
              length 1..79 {
                description 'Description of flow behavior application, support '
                          + '1-79 characters.'
                            ;
              }
            }
            ncd:revise-date 2020-06-18 ;
          }
        }
        container flow-behavior-apply-vrfs {
          description 'Flow-behavior applied to VRF.'
                      ;
          list flow-behavior-apply-vrf {
            description 'Flow-behavior applied to VRF.'
                        ;
            key vrf ;
            leaf vrf {
              description 'Name of VRF.'
                          ;
              type string ;
            }
            leaf pmap-name {
              description 'Name of the policy map bound on the VRF, support 1-3'
                        + '1 characters.'
                          ;
              type string {
                length 1..31 {
                  description 'Name of the policy map bound on the vni-instance.'
                              ;
                }
              }
              mandatory true ;
            }
            leaf flow-behavior-apply-desc {
              description 'Description of flow behavior application, support 1-'
                        + '79 characters.'
                          ;
              type ncd:string-with-blank {
                length 1..79 {
                  description 'Description of flow behavior application, suppor'
                            + 't 1-79 characters.'
                              ;
                }
              }
              ncd:revise-date 2020-06-18 ;
            }
          }
        }
        ncd:revise-date 2019-04-15 ;
      }
      container ttl-mode-global {
        description 'Configure global TTL duplicate'
                    ;
        presence 'Configure global TTL duplicate'
                 ;
        leaf inherit-mode {
          description 'Specify inherit mode, such as uniform, pipe'
                      ;
          type enumeration {
            enum uniform {
              value 1 ;
              description 'Select uniform mode'
                          ;
            }
            enum pipe {
              value 2 ;
              description 'Select pipe mode'
                          ;
            }
          }
          mandatory true ;
        }
        ncd:revise-date 2020-03-24 ;
      }
      container qos-global-prioritys-remark {
        if-feature qos-global-prioritys-remark ;
        description 'Configure the type of global priority and the global modif'
                  + 'ication enable switch of QoS.'
                    ;
        list qos-global-priority-remark {
          description 'Configure the type of global priority and the global mod'
                    + 'ification enable switch of QoS.'
                      ;
          key priority-type ;
          leaf priority-type {
            description 'Set the priority type remarked by global.'
                        ;
            type enumeration {
              enum all {
                value 4 ;
                description 'Based on all.'
                            ;
              }
            }
          }
          leaf enable-switch {
            description 'Configure the global priority modification is enabled '
                      + 'or disable.'
                        ;
            type enumeration {
              enum enable {
                value 1 ;
                description 'The switch is enable.'
                            ;
              }
              enum disable {
                value 2 ;
                description 'The switch is disable.'
                            ;
              }
            }
            mandatory true ;
          }
        }
        ncd:revise-date 2021-01-25 ;
      }
      container traffic-policy-stats {
        if-feature traffic-policy ;
        description 'To enable or disable the QoS traffic policy statistics'
                    ;
        container stats-switch-interfaces {
          description 'The QoS traffic policy statistics switch for interface.'
                      ;
          list stats-switch-interface {
            description 'The QoS traffic policy statistics switch for interface.'
                        ;
            key 'if-name direction'
                ;
            leaf if-name {
              description 'The interface which to be enbled statistics.'
                          ;
              type ncd:ifname ;
            }
            leaf direction {
              description 'The direction which to be enbled statistics.'
                          ;
              type qos-direction ;
            }
          }
        }
        ncd:revise-date 2021-01-25 ;
      }
      container qos-pw-ds-domains {
        if-feature qos-pw-ds-domains ;
        description 'Configure the used diffserv domain template by PW interfac'
                  + 'e.'
                    ;
        list qos-pw-ds-domain {
          description 'Configure the PW binding DS domain.'
                      ;
          key pw-name ;
          leaf pw-name {
            description 'Name of the PW, support 1-31 characters.'
                        ;
            type string {
              length 1..31 {
                description 'Name of the PW, support 1-31 characters.'
                            ;
              }
            }
          }
          leaf ds-domain-name {
            description 'Name of the diffserv domain, support 1-31 characters.'
                        ;
            type string {
              length 1..31 {
                description 'Name of the diffserv domain, support 1-31 characte'
                          + 'rs.'
                            ;
              }
            }
            mandatory true ;
          }
        }
        ncd:revise-date 2021-01-25 ;
      }
    }
  }
  container operation {
    config false ;
    description 'Operation model'
                ;
    container qos {
      description 'Operation about QoS.'
                  ;
      container stats-clear {
        description 'Clear QoS statistic data.'
                    ;
        container pw-schedules {
          description 'Clear QoS statistic data of PW schedule.'
                      ;
          list pw-schedule {
            description 'Clear QoS statistic data of PW schedule.'
                        ;
            key pw-name ;
            leaf pw-name {
              description 'Name of the PW, support 1-31 characters.'
                          ;
              type string {
                length 1..31 {
                  description 'Name of the PW, support 1-31 characters.'
                              ;
                }
              }
            }
          }
        }
        container pw-in-schedules {
          description 'Clear QoS statistic data of ingress PW schedule.'
                      ;
          list pw-in-schedule {
            description 'Clear QoS statistic data of ingress PW schedule.'
                        ;
            key pw-name ;
            leaf pw-name {
              description 'Name of the PW, support 1-31 characters.'
                          ;
              type string {
                length 1..31 {
                  description 'Name of the PW, support 1-31 characters.'
                              ;
                }
              }
            }
          }
          ncd:revise-date 2021-01-18 ;
        }
        container te-schedules {
          description 'Clear QoS statistic data of TE schedule.'
                      ;
          list te-schedule {
            description 'Clear QoS statistic data of TE schedule.'
                        ;
            key te-tunnel ;
            leaf te-tunnel {
              description 'Name of the attaching tunnel.'
                          ;
              type ncd:ifname ;
            }
          }
          ncd:revise-date 2021-03-24 ;
        }
        container bgpad-schedules {
          description 'Clear QoS statistic data of BGP-AD schedule.'
                      ;
          list bgpad-schedule {
            description 'Clear QoS statistic data of BGP-AD schedule.'
                        ;
            key 'vpls-name peer-router-id'
                ;
            leaf vpls-name {
              description 'Set VPLS instance name, support 1-32 characters.'
                          ;
              type string {
                length 1..32 ;
              }
            }
            leaf peer-router-id {
              description 'Set peer router id.'
                          ;
              type ncd:ipv4-address ;
            }
          }
          ncd:revise-date 2021-01-11 ;
        }
        container interfaces {
          description 'Clear the QoS flow statistics.'
                      ;
          list interface {
            description 'Clear the QoS flow statistics.'
                        ;
            key 'if-name flow-direction'
                ;
            leaf if-name {
              description 'The interface which to be enbled statistics'
                          ;
              type ncd:ifname ;
            }
            leaf flow-direction {
              description 'The flow direction, as follows,'+"\n"
                        + '     input  Attaches to the input flow'+"\n"
                        + '     output Attaches to the output flow'
                          ;
              type qos-direction ;
            }
          }
          ncd:revise-date 2021-03-24 ;
        }
      }
      container traffic-policy-stats-clear {
        if-feature traffic-policy ;
        description 'Clear QoS traffic policy statistic data.'
                    ;
        container stats-clear-interfaces {
          description 'Clear QoS traffic policy statistic data for interface.'
                      ;
          list stats-clear-interface {
            description 'Clear QoS traffic policy statistic data for interface.'
                        ;
            key 'if-name direction'
                ;
            leaf if-name {
              description 'The name of interface.'
                          ;
              type ncd:ifname ;
            }
            leaf direction {
              description 'The direction to clear.'
                          ;
              type qos-direction ;
            }
          }
        }
        ncd:revise-date 2021-01-25 ;
      }
    }
    ncd:revise-date 2016-05-03 ;
  }
}
