module zxr10-routing-table-management-dev-t8000 {
  namespace 'http://www.zte.com.cn/zxr10/netconf/schema/rosng/routing-table-man'
          + 'agement-dev-t8000'
            ;
  prefix routing-table-management-dev-t8000 ;
  import zxr10-routing-table-management {
    prefix rtm ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The deviation of routing-table-management for t8000'
              ;
  revision 2016-12-29 {
    description 'Add deviation of routing-table-management for t8000'
                ;
  }
  deviation '/rtm:configuration/rtm:rtm/rtm:ldsh/rtm:hash/rtm:ldsh-hash-fields/'
          + 'rtm:ldsh-hash-fields/rtm:hash-element/rtm:l3src'
            {
    description 'T8000 cannot config l3 original information of upstream flow p'
              + 'articipating hash operation.'
                ;
    deviate not-supported ;
  }
}
