module zxr10-protect-group-list {
  namespace 'http://www.zte.com.cn/zxr10/netconf/schema/rosng/protect-group-lis'
          + 't'
            ;
  prefix pglist ;
  import zxr10-netconf-defs {
    prefix ncd ;
    revision-date 2013-11-22 ;
  }
  organization 'ZTE Corporation' ;
  contact "ZTE Corporation  
\n"
        + "   Nanjing Institute of ZTE Corporation 
\n"
        + "   No.68 Zijinghua Rd. Yuhuatai District, Nanjing, China 
\n"
        + '   Tel: +86-25-52870000'
          ;
  description 'The netconf module to describe the protect group list.' ;
  revision 2013-12-12 {
    description "1.Add import clause.
\n"
              + '2.Change the type of master-pw-group-name leaf node from strin'
              + "g to \"ncd:ifname\".
\n"
              + '3.Change the type of slave-pw-group-name leaf node from string'
              + ' to "ncd:ifname".'
                ;
  }
  revision 2013-11-04 {
    description "1.Remove the import clause.
\n"
              + "2.Add pw-group-list feature and tunnel-group-list feature. 
\n"
              + "3.Add container slave-tunnel-groups and slave-pw-groups.
\n"
              + '4.Add if-feature clause on case clause.'
                ;
  }
  revision 2013-07-03 {
    description 'Initial version.' ;
  }
  feature pw-group-list {
    description 'PW group list.' ;
  }
  feature tunnel-group-list {
    description 'Tunnel group list.' ;
  }
  container configuration {
    description 'Configuration model information of protect group list.' ;
    container protect-group-list {
      description 'The configuration information of protect group list, depend '
                + 'zxr10-tunnel-group and zxr10-l2vpn.'
                  ;
      list group-list {
        description 'Configure protect group list.ID of tunnel protect group li'
                  + 'st is between [1,x], ID of PW protect group list is betwee'
                  + 'n [y+1,z].The value of x,y and z depends on the performanc'
                  + 'e parameters, the default value of x is 4096, the default '
                  + 'value of y is 4096, the default value of z is 8192.'
                    ;
        key group-list-id ;
        unique group-list-id ;
        max-elements 8192 ;
        leaf group-list-id {
          description 'Configure ID of protect group list.' ;
          type uint32 {
            range 1..8192 {
              description 'ID of protect group list.' ;
            }
          }
        }
        choice type {
          description 'You can configure tunnel protect group list or PW protec'
                    + 't group list.'
                      ;
          mandatory true ;
          case tunnel-group {
            if-feature tunnel-group-list ;
            description 'Configure tunnel protect group list.The maximum number'
                      + ' of tunnel protect group list instance depends on the '
                      + 'performance parameter, the default value is 4096.The m'
                      + 'aximum member number each tunnel protect group list de'
                      + 'pends on the performance parameter, the default value '
                      + 'is 32, one master tunnel group and 31 slave tunnel gro'
                      + 'ups.The maximum member number of all tunnel protect gr'
                      + 'oup list depends on the performance parameter, the def'
                      + 'ault value is 8192.'
                        ;
            leaf master-tunnel-group-id {
              description 'Configure master tunnel group of tunnel protect grou'
                        + 'p list.Each tunnel protect group list can only confi'
                        + 'gure one master tunnel group.'
                          ;
              type uint32 {
                range 1..32768 {
                  description 'Tunnel group ID.' ;
                }
              }
              mandatory true ;
            }
            container slave-tunnel-groups {
              description 'Configure slave tunnel groups of tunnel protect grou'
                        + 'p list.The maximum member number each tunnel protect'
                        + ' group list depends on the performance parameter, th'
                        + 'e default value is 32, one master tunnel group and 3'
                        + '1 slave tunnel groups.Because each tunnel protect gr'
                        + 'oup list can only configure one master tunnel group,'
                        + 'so the slave tunnel group number depends on the perf'
                        + 'ormance parameter too.'
                          ;
              presence 'Configure slave tunnel groups' ;
              list slave-tunnel-group {
                description 'Configure slave tunnel group of tunnel protect gro'
                          + 'up list.'
                            ;
                key slave-tunnel-group-id ;
                max-elements 31 ;
                leaf slave-tunnel-group-id {
                  description 'Configure slave tunnel group ID.' ;
                  type uint32 {
                    range 1..32768 {
                      description 'Tunnel group ID.' ;
                    }
                  }
                }
              }
            }
          }
          case pw-group {
            if-feature pw-group-list ;
            description 'Configure PW protect group list.The maximum number of '
                      + 'PW protect group list instance depends on the performa'
                      + 'nce parameter, the default value is 4096.The maximum m'
                      + 'ember number each PW protect group list depends on the'
                      + ' performance parameter, the default value is 32, one m'
                      + 'aster PW group and 31 slave PW groups.The maximum memb'
                      + 'er number of all PW protect group list depends on the '
                      + 'performance parameter, the default value is 8192.'
                        ;
            leaf master-pw-group-name {
              description 'Configure master PW group of PW protect group list.E'
                        + 'ach PW protect group list can only configure one mas'
                        + 'ter PW group.'
                          ;
              type ncd:ifname ;
              mandatory true ;
            }
            container slave-pw-groups {
              description 'Configure slave PW groups of PW protect group list.T'
                        + 'he maximum member number each PW protect group list '
                        + 'depends on the performance parameter, the default va'
                        + 'lue is 32, one master PW group and 31 slave PW group'
                        + 's.Because each PW protect group list can only config'
                        + 'ure one master PW group,so the slave PW group number'
                        + ' depends on the performance parameter too.'
                          ;
              presence 'Configure slave PW groups' ;
              list slave-pw-group {
                description 'Configure slave PW group of PW protect group list.' ;
                key slave-pw-group-name ;
                max-elements 31 ;
                leaf slave-pw-group-name {
                  description 'Configure slave PW group name.' ;
                  type ncd:ifname ;
                }
              }
            }
          }
        }
      }
    }
  }
}
