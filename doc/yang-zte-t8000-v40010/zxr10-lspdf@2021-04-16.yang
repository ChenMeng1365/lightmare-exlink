module zxr10-lspdf {
  namespace 'http://www.zte.com.cn/zxr10/netconf/schema/rosng/lspdf'
            ;
  prefix lspdf ;
  yang-version 1 ;
  import zxr10-netconf-defs {
    prefix ncd ;
    revision-date 2019-07-16 ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe LSPDF. LSPDF describes a simple a'
            + 'nd efficient mechanism that can be used to detect data plane fai'
            + 'lures in MPLS Label Switched Paths.'
              ;
  revision 2021-04-16 {
    description '1. Add projections:6100 and 61v5_1 in the feature of sr-mpls-p'
              + 'olicy.'
                ;
  }
  revision 2021-01-06 {
    description '1. Add operation/lspdf/lsp-traces/lsp-trace/lsp-trace-option/e'
              + 'xp.'
                ;
  }
  revision 2020-10-29 {
    description '1. Add operation/lspdf/lsp-pings/lsp-ping/lsp-ping-type/sr-pol'
              + 'icy'+"\n"
              + '2. Add operation/lspdf/lsp-traces/lsp-trace/lsp-trace-type/sr-'
              + 'policy'+"\n"
              + '3. Add notification-lsp-pings/lsp-mpath-pings'+"\n"
              + '4. Add notification-lsp-traces/lsp-mpath-traces'+"\n"
              + '5. Add notification-lsp-trace-results/lsp-mpath-trace-results'
                ;
  }
  revision 2020-10-16 {
    description '1. Add operation/lspdf/lsp-pings/lsp-ping/lsp-ping-type/evpn-v'
              + 'pls'+"\n"
              + '1. Add operation/lspdf/lsp-traces/lsp-trace/lsp-trace-type/evp'
              + 'n-vpls'
                ;
  }
  revision 2020-09-03 {
    description '1.Choice operation/lspdf/lsp-pings/lsp-ping/lsp-ping-type/evpn'
              + '-vpws/source-address'+"\n"
              + '2.Choice operation/lspdf/lsp-traces/lsp-trace/lsp-trace-type/e'
              + 'vpn-vpws/source-address'+"\n"
              + '3.Choice operation/lspdf/lsp-pings/lsp-ping/lsp-ping-type/evpn'
              + '/vpws/vpws-key'+"\n"
              + '4.Choice operation/lspdf/lsp-traces/lsp-trace/lsp-trace-type/e'
              + 'vpn-vpws/vpws-key'
                ;
  }
  revision 2020-07-30 {
    description '1.Add leaf operation/lspdf/lsp-pings/lsp-ping/lsp-ping-option/'
              + 'exp.'+"\n"
              + '2.Add Choice operation/lspdf/lsp-pings/lsp-ping/lsp-ping-optio'
              + 'n/speed.'
                ;
  }
  revision 2020-07-01 {
    description '1.Add leaf operation/lspdf/lsp-pings/lsp-ping/lsp-ping-type/ev'
              + 'pn-vpws/ecmp-frr'
                ;
  }
  revision 2020-06-09 {
    description '1 Add enum item of operation/lspdf/lsp-pings/lsp-ping/lsp-ping'
              + '-option/reply-mode.'+"\n"
              + '2 Add leaf operation/lspdf/lsp-pings/lsp-ping/lsp-ping-option/'
              + 'specify-path/tunnel.'
                ;
  }
  revision 2020-03-10 {
    description '1 Add a case of evpn-vpws in lsp-ping-type'+"\n"
              + '2 Add a case of evpn-vpws in lsp-trace-type'
                ;
  }
  revision 2019-09-24 {
    description '1.add leaf operation/lspdf/lsp-pings/lsp-ping/lsp-ping-type/tr'
              + 'affic-eng/ipv6-source'+"\n"
              + '2.add leaf operation/lspdf/lsp-traces/lsp-trace/lsp-trace-type'
              + '/traffic-eng/ipv6-source'+"\n"
              + '3.add leaf operation/lspdf/lsp-traces/lsp-trace/lsp-trace-type'
              + '/traffic-eng/ttl-model'
                ;
  }
  revision 2019-08-28 {
    description '1 Add a case of nil-fec in lsp-ping-type'+"\n"
              + '2 Add a case of nil-fec in lsp-trace-type'
                ;
  }
  revision 2019-08-19 {
    description '1 Add leaf without-explicit-null-label in lsp-ping traffic-eng'
              + ''+"\n"
              + '2 Add leaf without-explicit-null-label in lsp-trace traffic-en'
              + 'g'
                ;
  }
  revision 2019-07-10 {
    description '1:/lspdf:operation/lspdf:lspdf/lspdf:lsp-pings/lspdf:lsp-ping/'
              + 'lspdf:lsp-ping-option add pattern leaf'+"\n"
              + '2:/lspdf:operation/lspdf:lspdf/lspdf:lsp-traces/lspdf:lsp-trac'
              + 'e/lspdf:lsp-trace-option add pattern leaf'
                ;
  }
  revision 2019-07-02 {
    description '1 Add a case of igpv6 in lsp-ping-type'+"\n"
              + '2 Add a case of igpv6 in lsp-trace-type'
                ;
  }
  revision 2019-05-14 {
    description '1 Add a case of igp in lsp-ping-type'+"\n"
              + '1 Add a case of igp in lsp-trace-type'
                ;
  }
  revision 2018-12-12 {
    description 'Add hop-status value 6'
                ;
  }
  revision 2018-09-12 {
    description 'Add hop-label-list to /lspdf:notification-lsp-traces/lspdf:lsp'
              + '-traces/lspdf:lsp-trace and'+"\n"
              + '/lspdf:state/lspdf:lspdf/lspdf:lsp-traces/lspdf:lspdf-trace'
                ;
  }
  revision 2015-06-08 {
    description "1.split notification to notification-lsp-pings,notification-ls"
              + "p-traces,lsp-trace_result.
\n2 Modify /operation/lspdf/lsp-pin"
              + "gs/lsp-ping/lsp-ping-option/time-out 's range from 1-20 to 1-6"
              + "03 
\n3 Modify /operation/lspdf/lsp-traces/lsp-trace/lsp-trace"
              + "-option/time-out 's range from 1-20 to 1-60"
                ;
  }
  revision 2015-01-05 {
    description 'Add LSPDF notification function.'
                ;
  }
  revision 2014-04-21 {
    description '1.Modify the mandatory attribute of status and lsp-type.'+"\n"
              + '2.Modify the name of enable and disable.'
                ;
  }
  revision 2014-01-15 {
    description 'Initial version.'
                ;
  }
  feature nil-fec ;
  feature evpn-vpws ;
  feature evpn-vpls ;
  feature sr-mpls-policy ;
  typedef path-role {
    type enumeration {
      enum master {
        value 1 ;
        description Master ;
      }
      enum slave {
        value 2 ;
        description Slave ;
      }
    }
    description 'Path role'
                ;
  }
  container operation {
    config false ;
    description 'LSPDF operations model info.'
                ;
    container lspdf {
      description 'LSPDF operation parameters.'
                  ;
      container lsp-pings {
        description 'Lsp ping operation parameters.'
                    ;
        list lsp-ping {
          description 'Lsp ping operation parameters.'
                      ;
          key serial-num ;
          leaf serial-num {
            description 'Lsp ping serial number.'
                        ;
            type uint64 ;
          }
          choice status {
            description 'The switch for turning on/off lsp ping.'
                        ;
            mandatory true ;
            case enable {
              description 'Start lsp ping function.'
                          ;
              leaf ping-enable {
                description 'Start lsp ping function.'
                            ;
                type empty ;
                mandatory true ;
              }
              container lsp-ping-type {
                description 'Detect type parameters for lsp ping.'
                            ;
                choice lsp-type {
                  description 'Detect type for lsp ping.'
                              ;
                  mandatory true ;
                  case ipv4 {
                    description 'LDP IPv4 detect type.'
                                ;
                    container ipv4 {
                      description 'LDP IPv4 detect type.'
                                  ;
                      leaf fec-address {
                        description 'FEC address for IPv4 lsp ping.'
                                    ;
                        type ncd:ipv4-address ;
                        mandatory true ;
                      }
                      leaf mask-length {
                        description 'FEC mask length for IPv4 lsp ping.'
                                    ;
                        type uint16 {
                          range 0..32 {
                            description 'FEC mask length for IPv4 lsp ping.'
                                        ;
                          }
                        }
                        mandatory true ;
                      }
                      leaf out-if {
                        description 'Output interface for IPv4 lsp ping.'
                                    ;
                        type ncd:ifname ;
                      }
                      leaf source {
                        description 'Source IPv4 address.'
                                    ;
                        type ncd:ipv4-address ;
                      }
                    }
                  }
                  case ipv6 {
                    description 'LDP IPv6 detect type.'
                                ;
                    container ipv6 {
                      description 'LDP IPv6 detect type.'
                                  ;
                      leaf ipv6-fec-address {
                        description 'FEC address for IPv6 lsp ping.'
                                    ;
                        type ncd:ipv6-address ;
                        mandatory true ;
                      }
                      leaf ipv6-mask-len {
                        description 'FEC mask length for IPv6 lsp ping.'
                                    ;
                        type uint16 {
                          range 0..128 {
                            description 'FEC mask length for IPv6 lsp ping.'
                                        ;
                          }
                        }
                        mandatory true ;
                      }
                      leaf source {
                        description 'Source IPv6 address.'
                                    ;
                        type ncd:ipv6-address ;
                      }
                    }
                  }
                  case traffic-eng {
                    description 'TE tunnel detect type.'
                                ;
                    container traffic-eng {
                      description 'TE tunnel detect type.'
                                  ;
                      leaf tunnel-name {
                        description 'TE tunnel name.'
                                    ;
                        type ncd:ifname ;
                        mandatory true ;
                      }
                      leaf lsp-role {
                        description 'Lsp role for TE lsp ping, include master a'
                                  + 'nd slave.'
                                    ;
                        type enumeration {
                          enum master {
                            value 1 ;
                            description 'The master lsp of TUNNEL.'
                                        ;
                          }
                          enum slave {
                            value 2 ;
                            description 'The slave lsp of TUNNEL.'
                                        ;
                          }
                        }
                      }
                      leaf source {
                        description 'Source IPv4 address.'
                                    ;
                        type ncd:ipv4-address ;
                      }
                      leaf ipv6-source {
                        description 'Source IPv6 address.'
                                    ;
                        type ncd:ipv6-address ;
                        ncd:revise-date 2019-09-24 ;
                      }
                      leaf without-explicit-null-label {
                        description 'No extra explicit null label included, 0: '
                                  + 'include, 1: exclude. Default value of this'
                                  + ' parameter depends on the device.'
                                    ;
                        type uint8 {
                          range 0..1 {
                            description 'No extra explicit null label included, 0: include, 1: exclude.'
                                        ;
                          }
                        }
                        ncd:revise-date 2019-08-19 ;
                      }
                    }
                  }
                  case pseudowire {
                    description 'PW detect type.'
                                ;
                    container pseudowire {
                      description 'PW detect type.'
                                  ;
                      leaf mspw-flag {
                        description 'The flag which identify the PW is MSPW or '
                                  + 'not.'
                                    ;
                        type enumeration {
                          enum sspw {
                            value 0 ;
                          }
                          enum mspw {
                            value 1 ;
                          }
                        }
                        default sspw ;
                      }
                      leaf pw-name {
                        description 'PW name for lsp ping.'
                                    ;
                        type string ;
                        mandatory true ;
                      }
                      leaf remote-address {
                        description 'Remote address of PW.'
                                    ;
                        type ncd:ipv4-address ;
                      }
                      leaf vc-id {
                        description 'Remote vc-id of PW.'
                                    ;
                        type uint32 {
                          range 1..4294967295 {
                            description 'Remote vc-id of PW.'
                                        ;
                          }
                        }
                      }
                      leaf source {
                        description 'Source IPv4 address.'
                                    ;
                        type ncd:ipv4-address ;
                      }
                    }
                  }
                  case igp {
                    description 'SR BE detect type.'
                                ;
                    container igp {
                      description 'SR BE detect type.'
                                  ;
                      leaf fec-address {
                        description 'FEC address for SR BE lsp ping.'
                                    ;
                        type ncd:ipv4-address ;
                        mandatory true ;
                      }
                      leaf mask-length {
                        description 'FEC mask length for SR BE lsp ping.'
                                    ;
                        type uint16 {
                          range 0..32 {
                            description 'FEC mask length for IPv4 lsp ping.'
                                        ;
                          }
                        }
                        mandatory true ;
                      }
                      leaf source {
                        description 'Source IPv4 address.'
                                    ;
                        type ncd:ipv4-address ;
                      }
                    }
                    ncd:revise-date 2019-05-14 ;
                  }
                  case igpv6 {
                    description 'SR-BE IPv6 detect type.'
                                ;
                    container igpv6 {
                      description 'SR-BE IPv6 detect type.'
                                  ;
                      leaf ipv6-fec-address {
                        description 'FEC address for SR-BE IPv6 LSP ping.'
                                    ;
                        type ncd:ipv6-address ;
                        mandatory true ;
                      }
                      leaf ipv6-mask-len {
                        description 'FEC mask length for SR-BE IPv6 LSP ping.'
                                    ;
                        type uint16 {
                          range 0..128 {
                            description 'FEC mask length for SR-BE IPv6 LSP ping.'
                                        ;
                          }
                        }
                        mandatory true ;
                      }
                      leaf source {
                        description 'IPv6 Source address.'
                                    ;
                        type ncd:ipv6-address ;
                      }
                    }
                    ncd:revise-date 2019-07-02 ;
                  }
                  case nil-fec {
                    if-feature nil-fec ;
                    description 'NIL FEC detect type.'
                                ;
                    container nil-fec {
                      description 'NIL FEC detect type.'
                                  ;
                      leaf-list labels {
                        description 'List of nil-fec labels'
                                    ;
                        type uint32 {
                          range 16..1048575 ;
                        }
                        min-elements 1 ;
                        ncd:revise-date 2020-10-16 ;
                      }
                      leaf out-if {
                        description 'Outgoing interface for nil fec lsp ping.'
                                    ;
                        type ncd:ifname ;
                      }
                      choice address-paras {
                        description 'Address paras'
                                    ;
                        case ipv6 {
                          container ipv6 {
                            leaf nexthop {
                              description 'nexthop address'
                                          ;
                              type ncd:ipv6-address-none-zero ;
                            }
                            leaf source {
                              description 'source address'
                                          ;
                              type ncd:ipv6-address-none-zero ;
                            }
                          }
                        }
                        case ipv4 {
                          container ipv4 {
                            leaf nexthop {
                              description 'nexthop address'
                                          ;
                              type ncd:ipv4-address-none-zero ;
                            }
                            leaf source {
                              description 'source address'
                                          ;
                              type ncd:ipv4-address-none-zero ;
                            }
                          }
                        }
                      }
                    }
                    ncd:revise-date 2019-08-28 ;
                  }
                  case evpn-vpws {
                    if-feature evpn-vpws ;
                    description 'EVPN VPWS detect type.'
                                ;
                    container evpn-vpws {
                      description 'EVPN VPWS detect type.'
                                  ;
                      leaf vpws-name {
                        description 'EVPN VPWS instance name.'
                                    ;
                        type string {
                          length 1..32 {
                            description 'VPWS instance name'
                                        ;
                          }
                        }
                        mandatory true ;
                      }
                      choice vpws-key {
                        description 'Access point or EVPN VPWS ID.'
                                    ;
                        mandatory true ;
                        case interface {
                          description 'Access point.'
                                      ;
                          leaf interface {
                            description 'Access point.'
                                        ;
                            type ncd:ifname ;
                            mandatory true ;
                          }
                        }
                        case vpws-id {
                          description 'EVPN VPWS ID.'
                                      ;
                          leaf local-vpws-id {
                            description 'Local EVPN VPWS ID.'
                                        ;
                            type uint32 {
                              range 1..4294967294 ;
                            }
                            mandatory true ;
                          }
                          leaf remote-vpws-id {
                            description 'Remote EVPN VPWS ID.'
                                        ;
                            type uint32 {
                              range 1..4294967294 ;
                            }
                            mandatory true ;
                          }
                          ncd:revise-date 2020-09-03 ;
                        }
                      }
                      choice source-address {
                        description 'Source address.'
                                    ;
                        case source {
                          description 'IPv4 source address.'
                                      ;
                          leaf source {
                            description 'IPv4 source address.'
                                        ;
                            type ncd:ipv4-address-none-zero ;
                          }
                        }
                        case ipv6-source {
                          description 'IPv6 source address.'
                                      ;
                          leaf ipv6-source {
                            description 'IPv6 source address.'
                                        ;
                            type ncd:ipv6-address-none-zero ;
                          }
                          ncd:revise-date 2020-09-03 ;
                        }
                      }
                      choice ecmp-frr {
                        description 'ECMP or FRR.'
                                    ;
                        case ecmp {
                          description 'If detect all active pathes.'
                                      ;
                          leaf ecmp {
                            description 'If detect all active pathes.'
                                        ;
                            type enumeration {
                              enum disable {
                                value 0 ;
                                description 'Detect single path in used.'
                                            ;
                              }
                              enum enable {
                                value 1 ;
                                description 'Detect all pathes in used.'
                                            ;
                              }
                            }
                          }
                        }
                        case frr {
                          description 'Detect master or slave path.'
                                      ;
                          leaf path-role {
                            description 'Path role'
                                        ;
                            type path-role ;
                          }
                        }
                        ncd:revise-date 2020-07-01 ;
                      }
                    }
                    ncd:revise-date 2020-03-10 ;
                  }
                  case evpn-vpls {
                    if-feature evpn-vpls ;
                    description 'EVPN VPLS detect type.'
                                ;
                    container evpn-vpls {
                      description 'EVPN VPLS detect type.'
                                  ;
                      leaf vpls-name {
                        description 'EVPN VPLS instance name.'
                                    ;
                        type string {
                          length 1..32 {
                            description 'VPLS instance name'
                                        ;
                          }
                        }
                        mandatory true ;
                      }
                      choice peer-address {
                        description 'Peer original address.'
                                    ;
                        mandatory true ;
                        case peer {
                          description 'IPv4 Peer original address.'
                                      ;
                          leaf peer {
                            description 'IPv4 peer address.'
                                        ;
                            type ncd:ipv4-address-none-zero ;
                            mandatory true ;
                          }
                        }
                        case ipv6-peer {
                          description 'IPv6 Peer original address.'
                                      ;
                          leaf ipv6-peer {
                            description 'IPv6 peer address.'
                                        ;
                            type ncd:ipv6-address-none-zero ;
                            mandatory true ;
                          }
                        }
                      }
                      leaf eti {
                        description 'Ethernte Tag ID.'
                                    ;
                        type uint32 {
                          range 1..4094 {
                            description 'Ethernte Tag ID.'
                                        ;
                          }
                        }
                      }
                      choice source-address {
                        description 'Source address.'
                                    ;
                        case source {
                          description 'IPv4 source address.'
                                      ;
                          leaf source {
                            description 'IPv4 source address.'
                                        ;
                            type ncd:ipv4-address-none-zero ;
                          }
                        }
                        case ipv6-source {
                          description 'Source IPv6 address.'
                                      ;
                          leaf ipv6-source {
                            description 'IPv6 source address.'
                                        ;
                            type ncd:ipv6-address-none-zero ;
                          }
                        }
                      }
                    }
                    ncd:revise-date 2020-10-16 ;
                  }
                  case sr-policy {
                    if-feature sr-mpls-policy ;
                    description 'SR policy detect type.'
                                ;
                    container sr-policy {
                      description 'SR policy detect type.'
                                  ;
                      choice policy {
                        description 'SR policy detect type.'
                                    ;
                        mandatory true ;
                        case policy-name {
                          description 'Policy name'
                                      ;
                          leaf name {
                            description 'Policy name'
                                        ;
                            type string {
                              length 1..63 ;
                            }
                            mandatory true ;
                          }
                        }
                        case endpoint {
                          description 'Endpoint IP address'
                                      ;
                          leaf address {
                            description 'Endpoint IP address'
                                        ;
                            type ncd:ipv4-address-none-zero ;
                            mandatory true ;
                          }
                          leaf color {
                            description 'Color ID'
                                        ;
                            type uint32 {
                              range 1..4294967295 ;
                            }
                            mandatory true ;
                          }
                        }
                      }
                      leaf source {
                        description 'Source IPv4 address.'
                                    ;
                        type ncd:ipv4-address-none-zero ;
                      }
                      leaf without-explicit-null-label {
                        description 'No extra explicit null label included, 0: '
                                  + 'include, 1: exclude. Default value of this'
                                  + ' parameter depends on the device.'
                                    ;
                        type uint8 {
                          range 0..1 {
                            description 'No extra explicit null label included, 0: include, 1: exclude.'
                                        ;
                          }
                        }
                      }
                      leaf path-type {
                        description 'Path type'
                                    ;
                        type enumeration {
                          enum master {
                            value 1 ;
                            description 'master path'
                                        ;
                          }
                          enum slave {
                            value 2 ;
                            description 'slave path'
                                        ;
                          }
                        }
                      }
                    }
                    ncd:revise-date 2020-10-29 ;
                  }
                }
              }
              container lsp-ping-option {
                description 'Option parameters for lsp ping.'
                            ;
                leaf exp {
                  description 'MPLS experimental field value in the MPLS header.'
                              ;
                  type uint8 {
                    range 0..7 {
                      description 'Exp value of labels.'
                                  ;
                    }
                  }
                  ncd:revise-date 2020-07-30 ;
                }
                leaf repeat {
                  description 'Repeat count of lsp ping.'
                              ;
                  type uint16 {
                    range 1..65535 {
                      description 'Repeat count of lsp ping.'
                                  ;
                    }
                  }
                  default 5 ;
                }
                leaf reply-mode {
                  description 'Reply mode of lsp ping.'
                              ;
                  type enumeration {
                    enum not-reply {
                      value 1 ;
                      description 'Do not reply.'
                                  ;
                    }
                    enum ip {
                      value 2 ;
                      description 'Reply via IPv4/IPv6 UDP.'
                                  ;
                    }
                    enum router-alert {
                      value 3 ;
                      description 'Reply via IPv4/IPv6 UDP with router alert.'
                                  ;
                    }
                    enum application-channel {
                      value 4 ;
                      description 'Reply via application level control channel.'
                                  ;
                    }
                    enum specify-path {
                      value 5 ;
                      description 'Reply via specified path.'
                                  ;
                    }
                  }
                  default ip ;
                }
                leaf size {
                  description 'Datagram size of lsp ping packets.'
                              ;
                  type uint16 {
                    range 100..1500 {
                      description 'Datagram size of lsp ping packets.'
                                  ;
                    }
                  }
                  units byte ;
                  default 120 ;
                }
                leaf ttl {
                  description 'Time to live of lsp ping packets.'
                              ;
                  type uint8 {
                    range 1..255 {
                      description 'Time to live of lsp ping packets.'
                                  ;
                    }
                  }
                  default 255 ;
                }
                leaf time-out {
                  description 'Timeout of lsp ping.'
                              ;
                  type uint8 {
                    range 1..60 {
                      description 'Timeout of lsp ping.'
                                  ;
                    }
                  }
                  units s ;
                  default 2 ;
                }
                leaf pattern {
                  description 'The pad bytes.'
                              ;
                  type string {
                    length 4 {
                      description 'The pattern string.'
                                  ;
                    }
                  }
                  ncd:revise-date 2019-07-10 ;
                }
                choice speed {
                  description 'The mode of sending packets.'
                              ;
                  case limit-mode {
                    description 'The mode which controls how many packets sent '
                              + 'in a second.'
                                ;
                    leaf limit {
                      description 'The number of sending packets in a second, 0'
                                + ' means no limit.'
                                  ;
                      type uint8 {
                        range 0..100 {
                          description 'The number of sending packets in a secon'
                                    + 'd, 0 means no limit.'
                                      ;
                        }
                      }
                    }
                  }
                  case interval-mode {
                    description 'The mode which controls how long between two s'
                              + 'ending packets.'
                                ;
                    leaf interval {
                      description 'The interval between two sending packets.'
                                  ;
                      type uint8 {
                        range 2..10 {
                          description 'The interval between two sending packets.'
                                      ;
                        }
                      }
                      units s ;
                    }
                  }
                  ncd:revise-date 2020-07-30 ;
                }
                container specify-path {
                  description 'Specify path of reply mode.'
                              ;
                  leaf tunnel {
                    description 'Tunnel ID.'
                                ;
                    type uint16 {
                      range 1..65535 ;
                    }
                  }
                  ncd:revise-date 2020-06-09 ;
                }
              }
            }
            case disable {
              description 'Stop lsp ping function.'
                          ;
              leaf ping-disable {
                description 'Stop lsp ping function.'
                            ;
                type empty ;
                mandatory true ;
              }
            }
          }
        }
      }
      container lsp-traces {
        description 'lsp trace operation parameters.'
                    ;
        list lsp-trace {
          description 'Lsp trace operation parameters.'
                      ;
          key serial-num ;
          leaf serial-num {
            description 'Lsp trace serial number.'
                        ;
            type uint64 ;
          }
          choice status {
            description 'The switch for turning on/off lsp trace.'
                        ;
            mandatory true ;
            case enable {
              description 'Start lsp trace function.'
                          ;
              leaf trace-enable {
                description 'Start lsp trace function.'
                            ;
                type empty ;
                mandatory true ;
              }
              container lsp-trace-type {
                description 'Detect type parameters for lsp trace.'
                            ;
                choice lsp-type {
                  description 'Detect type for lsp trace.'
                              ;
                  mandatory true ;
                  case ipv4 {
                    description 'LDP IPv4 detect type.'
                                ;
                    container ipv4 {
                      description 'LDP IPv4 detect type.'
                                  ;
                      leaf fec-address {
                        description 'FEC address for IPv4 lsp trace.'
                                    ;
                        type ncd:ipv4-address ;
                        mandatory true ;
                      }
                      leaf mask-length {
                        description 'FEC mask length for IPv4 lsp trace.'
                                    ;
                        type uint16 {
                          range 0..32 {
                            description 'FEC mask length for IPv4 lsp trace.'
                                        ;
                          }
                        }
                        mandatory true ;
                      }
                      leaf out-if {
                        description 'Output interface for IPv4 lsp trace.'
                                    ;
                        type ncd:ifname ;
                      }
                      leaf source {
                        description 'Source IPv4 address.'
                                    ;
                        type ncd:ipv4-address ;
                      }
                    }
                  }
                  case ipv6 {
                    description 'LDP IPv6 detect type.'
                                ;
                    container ipv6 {
                      description 'LDP IPv6 detect type.'
                                  ;
                      leaf ipv6-fec-address {
                        description 'FEC address for IPv6 lsp trace.'
                                    ;
                        type ncd:ipv6-address ;
                        mandatory true ;
                      }
                      leaf ipv6-mask-len {
                        description 'FEC mask length for IPv6 lsp trace.'
                                    ;
                        type uint16 {
                          range 0..128 {
                            description 'FEC mask length for IPv6 lsp trace.'
                                        ;
                          }
                        }
                        mandatory true ;
                      }
                      leaf source {
                        description 'Source IPv6 address.'
                                    ;
                        type ncd:ipv6-address ;
                      }
                    }
                  }
                  case traffic-eng {
                    description 'TE tunnel detect type.'
                                ;
                    container traffic-eng {
                      description 'TE tunnel detect type.'
                                  ;
                      leaf tunnel-name {
                        description 'TE tunnel name.'
                                    ;
                        type ncd:ifname ;
                        mandatory true ;
                      }
                      leaf lsp-role {
                        description 'Lsp role for TE lsp trace, include master '
                                  + 'and slave.'
                                    ;
                        type enumeration {
                          enum master {
                            value 1 ;
                            description 'The master lsp of TUNNEL.'
                                        ;
                          }
                          enum slave {
                            value 2 ;
                            description 'The slave lsp of TUNNEL.'
                                        ;
                          }
                        }
                      }
                      leaf source {
                        description 'Source IPv4 address.'
                                    ;
                        type ncd:ipv4-address ;
                      }
                      leaf ipv6-source {
                        description 'Source IPv6 address.'
                                    ;
                        type ncd:ipv6-address ;
                        ncd:revise-date 2019-09-24 ;
                      }
                      leaf without-explicit-null-label {
                        description 'No extra explicit null label included, 0: '
                                  + 'include, 1: exclude. Default value of this'
                                  + ' parameter depends on the device.'
                                    ;
                        type uint8 {
                          range 0..1 {
                            description 'No extra explicit null label included, 0: include, 1: exclude.'
                                        ;
                          }
                        }
                        ncd:revise-date 2019-08-19 ;
                      }
                      leaf ttl-mode {
                        description 'Ttl mode of lsp ping.'
                                    ;
                        type enumeration {
                          enum uniform {
                            value 0 ;
                            description 'Uniform mode.'
                                        ;
                          }
                          enum pipe {
                            value 1 ;
                            description 'Pipe mode'
                                        ;
                          }
                        }
                        default uniform ;
                        ncd:revise-date 2019-09-24 ;
                      }
                    }
                  }
                  case pseudowire {
                    description 'PW detect type.'
                                ;
                    container pseudowire {
                      description 'PW detect type.'
                                  ;
                      leaf mspw-flag {
                        description 'The flag which identify the PW is MSPW or '
                                  + 'not.'
                                    ;
                        type enumeration {
                          enum sspw {
                            value 0 ;
                          }
                          enum mspw {
                            value 1 ;
                          }
                        }
                        default sspw ;
                      }
                      leaf pw-name {
                        description 'PW name for lsp ping.'
                                    ;
                        type string ;
                        mandatory true ;
                      }
                      leaf source {
                        description 'Source IPv4 address.'
                                    ;
                        type ncd:ipv4-address ;
                      }
                    }
                  }
                  case igp {
                    description 'SR BE detect type.'
                                ;
                    container igp {
                      description 'SR BE detect type.'
                                  ;
                      leaf fec-address {
                        description 'FEC address for SR BE lsp trace.'
                                    ;
                        type ncd:ipv4-address ;
                        mandatory true ;
                      }
                      leaf mask-length {
                        description 'FEC mask length for SR BE lsp trace.'
                                    ;
                        type uint16 {
                          range 0..32 {
                            description 'FEC mask length for IPv4 lsp trace.'
                                        ;
                          }
                        }
                        mandatory true ;
                      }
                      leaf source {
                        description 'Source IPv4 address.'
                                    ;
                        type ncd:ipv4-address ;
                      }
                    }
                    ncd:revise-date 2019-05-14 ;
                  }
                  case igpv6 {
                    description 'SR-BE IPv6 detect type.'
                                ;
                    container igpv6 {
                      description 'SR-BE IPv6 detect type.'
                                  ;
                      leaf ipv6-fec-address {
                        description 'FEC address for SR-BE IPv6 LSP trace.'
                                    ;
                        type ncd:ipv6-address ;
                        mandatory true ;
                      }
                      leaf ipv6-mask-len {
                        description 'FEC mask length for SR-BE IPv6 LSP trace.'
                                    ;
                        type uint16 {
                          range 0..128 {
                            description 'FEC mask length for SR-BE IPv6 LSP trace.'
                                        ;
                          }
                        }
                        mandatory true ;
                      }
                      leaf source {
                        description 'IPv6 Source address.'
                                    ;
                        type ncd:ipv6-address ;
                      }
                    }
                    ncd:revise-date 2019-07-02 ;
                  }
                  case nil-fec {
                    if-feature nil-fec ;
                    description 'NIL FEC detect type.'
                                ;
                    container nil-fec {
                      description 'NIL FEC detect type.'
                                  ;
                      leaf-list labels {
                        description 'List of nil-fec labels'
                                    ;
                        type int32 {
                          range 16..1048575 ;
                        }
                        min-elements 1 ;
                        ncd:revise-date 2020-10-16 ;
                      }
                      leaf out-if {
                        description 'Outgoing interface for nil fec lsp ping.'
                                    ;
                        type ncd:ifname ;
                      }
                      leaf ttl-mode {
                        description 'Ttl mode of lsp ping.'
                                    ;
                        type enumeration {
                          enum uniform {
                            value 0 ;
                            description 'Uniform mode.'
                                        ;
                          }
                          enum pipe {
                            value 1 ;
                            description 'Pipe mode'
                                        ;
                          }
                        }
                        default uniform ;
                      }
                      choice address-paras {
                        description 'Address paras.'
                                    ;
                        case ipv6 {
                          container ipv6 {
                            leaf nexthop {
                              description 'nexthop address'
                                          ;
                              type ncd:ipv6-address-none-zero ;
                            }
                            leaf source {
                              description 'source address'
                                          ;
                              type ncd:ipv6-address-none-zero ;
                            }
                          }
                        }
                        case ipv4 {
                          container ipv4 {
                            leaf nexthop {
                              description 'nexthop address'
                                          ;
                              type ncd:ipv4-address-none-zero ;
                            }
                            leaf source {
                              description 'source address'
                                          ;
                              type ncd:ipv4-address-none-zero ;
                            }
                          }
                        }
                      }
                    }
                    ncd:revise-date 2019-08-28 ;
                  }
                  case evpn-vpws {
                    if-feature evpn-vpws ;
                    description 'EVPN VPWS detect type.'
                                ;
                    container evpn-vpws {
                      description 'EVPN VPWS detect type.'
                                  ;
                      leaf vpws-name {
                        description 'EVPN VPWS instance name.'
                                    ;
                        type string {
                          length 1..32 {
                            description 'VPWS instance name'
                                        ;
                          }
                        }
                        mandatory true ;
                      }
                      choice vpws-key {
                        description 'Access point or EVPN VPWS ID.'
                                    ;
                        mandatory true ;
                        case interface {
                          description 'Access point.'
                                      ;
                          leaf interface {
                            description 'Access point.'
                                        ;
                            type ncd:ifname ;
                            mandatory true ;
                          }
                        }
                        case vpws-id {
                          description 'EVPN VPWS ID.'
                                      ;
                          leaf local-vpws-id {
                            description 'Local EVPN VPWS ID.'
                                        ;
                            type uint32 {
                              range 1..4294967294 ;
                            }
                            mandatory true ;
                          }
                          leaf remote-vpws-id {
                            description 'Remote EVPN VPWS ID.'
                                        ;
                            type uint32 {
                              range 1..4294967294 ;
                            }
                            mandatory true ;
                          }
                          ncd:revise-date 2020-09-03 ;
                        }
                      }
                      choice source-address {
                        case source {
                          leaf source {
                            description 'IPv4 source address.'
                                        ;
                            type ncd:ipv4-address-none-zero ;
                          }
                        }
                        case ipv6-source {
                          description 'Source IPv6 address.'
                                      ;
                          leaf ipv6-source {
                            description 'IPv6 source address.'
                                        ;
                            type ncd:ipv6-address-none-zero ;
                          }
                          ncd:revise-date 2020-09-03 ;
                        }
                      }
                    }
                    ncd:revise-date 2020-03-10 ;
                  }
                  case evpn-vpls {
                    if-feature evpn-vpls ;
                    description 'EVPN VPLS detect type.'
                                ;
                    container evpn-vpls {
                      description 'EVPN VPLS detect type.'
                                  ;
                      leaf vpls-name {
                        description 'EVPN VPLS instance name.'
                                    ;
                        type string {
                          length 1..32 {
                            description 'VPLS instance name'
                                        ;
                          }
                        }
                        mandatory true ;
                      }
                      choice peer-address {
                        description 'Peer original address.'
                                    ;
                        mandatory true ;
                        case peer {
                          description 'IPv4 Peer original address.'
                                      ;
                          leaf peer {
                            description 'IPv4 peer address.'
                                        ;
                            type ncd:ipv4-address-none-zero ;
                            mandatory true ;
                          }
                        }
                        case ipv6-peer {
                          description 'IPv6 Peer original address.'
                                      ;
                          leaf ipv6-peer {
                            description 'IPv6 peer address.'
                                        ;
                            type ncd:ipv6-address-none-zero ;
                            mandatory true ;
                          }
                        }
                      }
                      leaf eti {
                        description 'Ethernte Tag ID.'
                                    ;
                        type uint32 {
                          range 1..4094 {
                            description 'Ethernet Tag ID.'
                                        ;
                          }
                        }
                      }
                      choice source-address {
                        description 'Source address.'
                                    ;
                        case source {
                          description 'IPv4 source address.'
                                      ;
                          leaf source {
                            description 'IPv4 source address.'
                                        ;
                            type ncd:ipv4-address-none-zero ;
                          }
                        }
                        case ipv6-source {
                          description 'Source IPv6 address.'
                                      ;
                          leaf ipv6-source {
                            description 'IPv6 source address.'
                                        ;
                            type ncd:ipv6-address-none-zero ;
                          }
                        }
                      }
                    }
                    ncd:revise-date 2020-10-16 ;
                  }
                  case sr-policy {
                    if-feature sr-mpls-policy ;
                    description 'SR policy detect type.'
                                ;
                    container sr-policy {
                      description 'SR policy detect type.'
                                  ;
                      choice policy {
                        description 'SR policy detect type.'
                                    ;
                        mandatory true ;
                        case policy-name {
                          description 'Policy name'
                                      ;
                          leaf name {
                            description 'Policy name'
                                        ;
                            type string {
                              length 1..63 ;
                            }
                            mandatory true ;
                          }
                        }
                        case endpoint {
                          leaf address {
                            description 'Endpoint IP address'
                                        ;
                            type ncd:ipv4-address-none-zero ;
                            mandatory true ;
                          }
                          leaf color {
                            description 'Color ID'
                                        ;
                            type uint32 {
                              range 1..4294967295 ;
                            }
                            mandatory true ;
                          }
                        }
                      }
                      leaf source {
                        description 'Source IPv4 address.'
                                    ;
                        type ncd:ipv4-address-none-zero ;
                      }
                      leaf without-explicit-null-label {
                        description 'No extra explicit null label included, 0: '
                                  + 'include, 1: exclude. Default value of this'
                                  + ' parameter depends on the device.'
                                    ;
                        type uint8 {
                          range 0..1 {
                            description 'No extra explicit null label included, 0: include, 1: exclude.'
                                        ;
                          }
                        }
                      }
                      leaf path-type {
                        description 'Path type'
                                    ;
                        type enumeration {
                          enum master {
                            value 1 ;
                            description 'master path'
                                        ;
                          }
                          enum slave {
                            value 2 ;
                            description 'slave path'
                                        ;
                          }
                        }
                      }
                      leaf ttl-mode {
                        description 'Ttl mode of lsp ping.'
                                    ;
                        type enumeration {
                          enum uniform {
                            value 0 ;
                            description 'Uniform mode.'
                                        ;
                          }
                          enum pipe {
                            value 1 ;
                            description 'Pipe mode'
                                        ;
                          }
                        }
                        default uniform ;
                      }
                    }
                    ncd:revise-date 2020-10-29 ;
                  }
                }
              }
              container lsp-trace-option {
                description 'Option parameters for lsp trace.'
                            ;
                leaf exp {
                  description 'MPLS experimental field value in the MPLS header.'
                              ;
                  type uint8 {
                    range 0..7 {
                      description 'Exp value of labels.'
                                  ;
                    }
                  }
                  ncd:revise-date 2021-01-06 ;
                }
                leaf time-out {
                  description 'Timeout of lsp trace.'
                              ;
                  type uint8 {
                    range 1..60 {
                      description 'Timeout of lsp trace.'
                                  ;
                    }
                  }
                  units s ;
                  default 3 ;
                }
                leaf ttl {
                  description 'Max time to live of lsp trace.'
                              ;
                  type uint8 {
                    range 1..255 {
                      description 'Max time to live of lsp trace.'
                                  ;
                    }
                  }
                  default 30 ;
                }
                leaf reply-mode {
                  description 'Reply mode of lsp trace.'
                              ;
                  type enumeration {
                    enum not-reply {
                      value 1 ;
                      description 'Do not reply.'
                                  ;
                    }
                    enum ip {
                      value 2 ;
                      description 'Reply via IPv4/IPv6 UDP.'
                                  ;
                    }
                    enum router-alert {
                      value 3 ;
                      description 'Reply via IPv4/IPv6 UDP with router alert.'
                                  ;
                    }
                    enum application-channel {
                      value 4 ;
                      description 'Reply via application level control channel.'
                                  ;
                    }
                  }
                  default ip ;
                }
                leaf downstream-type {
                  description 'The type of downstream mapping.'
                              ;
                  type enumeration {
                    enum dsmap {
                      value 0 ;
                      description 'Downstream mapping(RFC4379).'
                                  ;
                    }
                    enum ddmap {
                      value 1 ;
                      description 'Downstream detailed mapping(RFC6424).'
                                  ;
                    }
                  }
                  default dsmap ;
                }
                leaf pattern {
                  description 'The pad bytes.'
                              ;
                  type string {
                    length 4 {
                      description 'The pattern string.'
                                  ;
                    }
                  }
                  ncd:revise-date 2019-07-10 ;
                }
              }
            }
            case disable {
              description 'Stop lsp trace function.'
                          ;
              leaf trace-disable {
                description 'Stop lsp trace function.'
                            ;
                type empty ;
                mandatory true ;
              }
            }
          }
        }
      }
    }
  }
  container state {
    config false ;
    description 'LSPDF state model info.'
                ;
    container lspdf {
      description 'LSPDF state models.'
                  ;
      container lsp-pings {
        description 'Lsp ping state models.'
                    ;
        list lsp-ping {
          description 'The detail result information of lsp ping.'
                      ;
          key serial-num ;
          leaf serial-num {
            description 'Lsp ping serial number.'
                        ;
            type uint64 ;
          }
          leaf send-pkts {
            description 'The number of send packets.'
                        ;
            type uint32 ;
          }
          leaf rcv-pkts {
            description 'The number of receive packets.'
                        ;
            type uint32 ;
          }
          leaf min-time {
            description 'The minimum of round trip time in milliseconds.'
                        ;
            type uint32 ;
            units ms ;
          }
          leaf max-time {
            description 'The maximum of round trip time in milliseconds.'
                        ;
            type uint32 ;
            units ms ;
          }
          leaf avg-time {
            description 'The average value of round trip time in milliseconds.'
                        ;
            type uint32 ;
            units ms ;
          }
          leaf wobble-min-time {
            description 'The minimum of wobble time in milliseconds.'
                        ;
            type uint32 ;
            units ms ;
          }
          leaf wobble-max-time {
            description 'The maximum of wobble time in milliseconds.'
                        ;
            type uint32 ;
            units ms ;
          }
          leaf wobble-avg-time {
            description 'The average value of wobble time in milliseconds.'
                        ;
            type uint32 ;
            units ms ;
          }
        }
      }
      container lsp-traces {
        description 'Lsp trace state models.'
                    ;
        list lsp-trace {
          description 'The detail result information of lsp trace.'
                      ;
          key 'serial-num hop-num'
              ;
          leaf serial-num {
            description 'Lsp trace serial number.'
                        ;
            type uint64 ;
          }
          leaf hop-num {
            description 'The num of current hop.'
                        ;
            type uint8 ;
          }
          leaf hop-status {
            description 'The status of current hop.'
                        ;
            type enumeration {
              enum Valid {
                value 0 ;
                description 'Default value.'
                            ;
              }
              enum ! {
                value 1 ;
                description success ;
              }
              enum R {
                value 2 ;
                description 'Route but not target.'
                            ;
              }
              enum Q {
                value 3 ;
                description 'Request not transmitted.'
                            ;
              }
              enum * {
                value 4 ;
                description Timeout. ;
              }
              enum Error {
                value 5 ;
                description 'Other return error.'
                            ;
              }
              enum B {
                value 6 ;
                description 'Route but no forwarding label'
                            ;
              }
            }
          }
          leaf hop-address {
            description 'The address of current hop.'
                        ;
            type string {
              length 0..47 {
                description 'The address of current hop.'
                            ;
              }
            }
          }
          leaf hop-type {
            description 'The type of current hop.'
                        ;
            type enumeration {
              enum Ingress {
                value 0 ;
                description 'Ingress of the path.'
                            ;
              }
              enum Downstream {
                value 1 ;
                description 'The middle point of the path.'
                            ;
              }
              enum Egress {
                value 2 ;
                description 'Egress of the path.'
                            ;
              }
              enum Invalid {
                value 3 ;
                description 'Default value.'
                            ;
              }
            }
          }
          leaf hop-label {
            description 'The label of current hop.'
                        ;
            type uint32 ;
          }
          leaf hop-mtu {
            description 'The maximum transmission unit of current hop.'
                        ;
            type uint16 ;
            units byte ;
          }
          leaf hop-rtt {
            description 'The round trip time of current hop.'
                        ;
            type uint16 ;
          }
          leaf hop-label-list {
            description 'The labels of current hop.'
                        ;
            type string {
              length 0..255 {
                description 'The labels of current hop.'
                            ;
              }
            }
            ncd:revise-date 2018-09-12 ;
          }
          ncd:select serial-num ;
          ncd:select 'serial-num hop-num'
                     ;
        }
      }
    }
  }
  notification notification-lsp-pings {
    description 'Notification of LSP ping.'
                ;
    container lsp-mpath-pings {
      config false ;
      description 'Notification of LSP path ping.'
                  ;
      list lsp-mpath-ping {
        description 'The detail result information of lsp ping.'
                    ;
        key 'serial-num path-num'
            ;
        leaf serial-num {
          description 'Lsp ping serial number.'
                      ;
          type uint64 ;
        }
        leaf path-num {
          type uint32 ;
        }
        leaf segment-list-id {
          description 'Segment-List ID.'
                      ;
          type uint32 ;
        }
        leaf path-type {
          description 'Path type.'
                      ;
          type uint8 ;
        }
        leaf protocol-origin {
          description 'Protocol origin.'
                      ;
          type string {
            length 0..8 ;
          }
        }
        leaf discriminator {
          description Discriminator. ;
          type uint32 ;
        }
        leaf autonomous-system {
          description 'Autonomous System ID.'
                      ;
          type uint32 ;
        }
        leaf originator-address {
          description 'Originator address.'
                      ;
          type string {
            length 0..47 {
              description 'The address of destination.'
                          ;
            }
          }
        }
        leaf send-pkts {
          description 'The number of send packets.'
                      ;
          type uint32 ;
        }
        leaf rcv-pkts {
          description 'The number of receive packets.'
                      ;
          type uint32 ;
        }
        leaf min-time {
          description 'The minimum of round trip time in milliseconds.'
                      ;
          type uint32 ;
          units ms ;
        }
        leaf max-time {
          description 'The maximum of round trip time in milliseconds.'
                      ;
          type uint32 ;
          units ms ;
        }
        leaf avg-time {
          description 'The average value of round trip time in milliseconds.'
                      ;
          type uint32 ;
          units ms ;
        }
        leaf wobble-min-time {
          description 'The minimum of wobble time in milliseconds.'
                      ;
          type uint32 ;
          units ms ;
        }
        leaf wobble-max-time {
          description 'The maximum of wobble time in milliseconds.'
                      ;
          type uint32 ;
          units ms ;
        }
        leaf wobble-avg-time {
          description 'The average value of wobble time in milliseconds.'
                      ;
          type uint32 ;
          units ms ;
        }
      }
      ncd:revise-date 2020-10-29 ;
    }
    container lsp-pings {
      config false ;
      description 'Notification of LSP ping.'
                  ;
      list lsp-ping {
        description 'The detail result information of lsp ping.'
                    ;
        key 'serial-num dest-address'
            ;
        leaf serial-num {
          description 'Lsp ping serial number.'
                      ;
          type uint64 ;
        }
        leaf dest-address {
          description 'The address of destination.It represents peer PE IP addr'
                    + 'ess of current detection when ECMP ping.'
                      ;
          type string {
            length 0..47 {
              description 'The address of destination.'
                          ;
            }
          }
        }
        leaf send-pkts {
          description 'The number of send packets.'
                      ;
          type uint32 ;
        }
        leaf rcv-pkts {
          description 'The number of receive packets.'
                      ;
          type uint32 ;
        }
        leaf min-time {
          description 'The minimum of round trip time in milliseconds.'
                      ;
          type uint32 ;
          units ms ;
        }
        leaf max-time {
          description 'The maximum of round trip time in milliseconds.'
                      ;
          type uint32 ;
          units ms ;
        }
        leaf avg-time {
          description 'The average value of round trip time in milliseconds.'
                      ;
          type uint32 ;
          units ms ;
        }
        leaf wobble-min-time {
          description 'The minimum of wobble time in milliseconds.'
                      ;
          type uint32 ;
          units ms ;
        }
        leaf wobble-max-time {
          description 'The maximum of wobble time in milliseconds.'
                      ;
          type uint32 ;
          units ms ;
        }
        leaf wobble-avg-time {
          description 'The average value of wobble time in milliseconds.'
                      ;
          type uint32 ;
          units ms ;
        }
      }
    }
    ncd:revise-date 2015-06-08 ;
  }
  notification notification-lsp-traces {
    description 'Notification of LSP trace.'
                ;
    container lsp-mpath-traces {
      config false ;
      description 'Notification of LSP trace.'
                  ;
      list lsp-mpath-trace {
        description 'The detail result information of lsp trace.'
                    ;
        key 'serial-num path-num hop-num'
            ;
        leaf serial-num {
          description 'Lsp trace serial number.'
                      ;
          type uint64 ;
        }
        leaf path-num {
          type uint32 ;
        }
        leaf hop-num {
          description 'The num of current hop.'
                      ;
          type uint8 ;
        }
        leaf segment-list-id {
          description 'Segment-List ID.'
                      ;
          type uint32 ;
        }
        leaf path-type {
          description 'Path type.'
                      ;
          type uint8 ;
        }
        leaf protocol-origin {
          description 'Protocol origin.'
                      ;
          type string {
            length 0..8 ;
          }
        }
        leaf discriminator {
          description Discriminator. ;
          type uint32 ;
        }
        leaf autonomous-system {
          description 'Autonomous System ID.'
                      ;
          type uint32 ;
        }
        leaf originator-address {
          description 'Originator address.'
                      ;
          type string {
            length 0..47 {
              description 'The address of destination.'
                          ;
            }
          }
        }
        leaf dest-address {
          description 'The address of destination hop.'
                      ;
          type string {
            length 0..47 {
              description 'The address of destination.'
                          ;
            }
          }
        }
        leaf hop-address {
          description 'The address of current hop.'
                      ;
          type string {
            length 0..47 {
              description 'The address of current hop.'
                          ;
            }
          }
        }
        leaf hop-status {
          description 'The status of current hop.'
                      ;
          type enumeration {
            enum Valid {
              value 0 ;
              description 'Default value.'
                          ;
            }
            enum ! {
              value 1 ;
              description success ;
            }
            enum R {
              value 2 ;
              description 'Route but not target.'
                          ;
            }
            enum Q {
              value 3 ;
              description 'Request not transmitted.'
                          ;
            }
            enum * {
              value 4 ;
              description Timeout. ;
            }
            enum Error {
              value 5 ;
              description 'Other return error.'
                          ;
            }
            enum B {
              value 6 ;
              description 'Route but no forwarding label'
                          ;
            }
          }
        }
        leaf hop-type {
          description 'The type of current hop.'
                      ;
          type enumeration {
            enum Ingress {
              value 0 ;
              description 'Ingress of the path.'
                          ;
            }
            enum Downstream {
              value 1 ;
              description 'The middle point of the path.'
                          ;
            }
            enum Egress {
              value 2 ;
              description 'Egress of the path.'
                          ;
            }
            enum Invalid {
              value 3 ;
              description 'Default value.'
                          ;
            }
          }
        }
        leaf hop-mtu {
          description 'The maximum transmission unit of current hop.'
                      ;
          type uint16 ;
          units byte ;
        }
        leaf hop-rtt {
          description 'The round trip time of current hop.'
                      ;
          type uint16 ;
        }
        leaf hop-label-list {
          description 'The labels of current hop.'
                      ;
          type string {
            length 0..254 {
              description 'The labels of current hop.'
                          ;
            }
          }
        }
        ncd:select serial-num ;
        ncd:select 'serial-num hop-num'
                   ;
      }
      ncd:revise-date 2020-10-29 ;
    }
    container lsp-traces {
      config false ;
      description 'Notification of LSP trace.'
                  ;
      list lsp-trace {
        description 'The detail result information of lsp trace.'
                    ;
        key 'serial-num hop-num dest-address'
            ;
        leaf serial-num {
          description 'Lsp trace serial number.'
                      ;
          type uint64 ;
        }
        leaf hop-num {
          description 'The num of current hop.'
                      ;
          type uint8 ;
        }
        leaf dest-address {
          description 'The address of destination hop.'
                      ;
          type string {
            length 0..47 {
              description 'The address of destination.'
                          ;
            }
          }
        }
        leaf hop-address {
          description 'The address of current hop.'
                      ;
          type string {
            length 0..47 {
              description 'The address of current hop.'
                          ;
            }
          }
        }
        leaf hop-status {
          description 'The status of current hop.'
                      ;
          type enumeration {
            enum Valid {
              value 0 ;
              description 'Default value.'
                          ;
            }
            enum ! {
              value 1 ;
              description success ;
            }
            enum R {
              value 2 ;
              description 'Route but not target.'
                          ;
            }
            enum Q {
              value 3 ;
              description 'Request not transmitted.'
                          ;
            }
            enum * {
              value 4 ;
              description Timeout. ;
            }
            enum Error {
              value 5 ;
              description 'Other return error.'
                          ;
            }
            enum B {
              value 6 ;
              description 'Route but no forwarding label'
                          ;
            }
          }
        }
        leaf hop-type {
          description 'The type of current hop.'
                      ;
          type enumeration {
            enum Ingress {
              value 0 ;
              description 'Ingress of the path.'
                          ;
            }
            enum Downstream {
              value 1 ;
              description 'The middle point of the path.'
                          ;
            }
            enum Egress {
              value 2 ;
              description 'Egress of the path.'
                          ;
            }
            enum Invalid {
              value 3 ;
              description 'Default value.'
                          ;
            }
          }
        }
        leaf hop-label {
          description 'The label of current hop.'
                      ;
          type uint32 ;
        }
        leaf hop-mtu {
          description 'The maximum transmission unit of current hop.'
                      ;
          type uint16 ;
          units byte ;
        }
        leaf hop-rtt {
          description 'The round trip time of current hop.'
                      ;
          type uint16 ;
        }
        leaf hop-label-list {
          description 'The labels of current hop.'
                      ;
          type string {
            length 0..254 {
              description 'The labels of current hop.'
                          ;
            }
          }
          ncd:revise-date 2018-09-12 ;
        }
        ncd:select serial-num ;
        ncd:select 'serial-num hop-num'
                   ;
      }
    }
    ncd:revise-date 2015-06-08 ;
  }
  notification notification-lsp-trace-results {
    container lsp-trace-mpath-results {
      description 'Notification of LSP trace.'
                  ;
      list lsp-trace-mpath-result {
        config false ;
        description 'The detail result information of lsp trace.'
                    ;
        key 'serial-num path-num'
            ;
        leaf serial-num {
          description 'Lsp trace serial number.'
                      ;
          type uint64 ;
        }
        leaf path-num {
          type uint32 ;
        }
        leaf dest-address {
          description 'The address of destination hop.'
                      ;
          type string {
            length 0..47 {
              description 'The address of destination.'
                          ;
            }
          }
        }
        leaf hops-count {
          description 'The number of lsp trace hops.'
                      ;
          type uint8 ;
        }
      }
      ncd:revise-date 2020-10-29 ;
    }
    container lsp-trace-results {
      description 'Notification of LSP trace.'
                  ;
      list lsp-trace-result {
        config false ;
        description 'The detail result information of lsp trace.'
                    ;
        key 'serial-num dest-address'
            ;
        leaf serial-num {
          description 'Lsp trace serial number.'
                      ;
          type uint64 ;
        }
        leaf dest-address {
          description 'The address of destination hop.'
                      ;
          type string {
            length 0..47 {
              description 'The address of destination.'
                          ;
            }
          }
        }
        leaf hops-count {
          description 'The number of lsp trace hops.'
                      ;
          type uint8 ;
        }
      }
    }
    ncd:revise-date 2015-06-08 ;
  }
}
