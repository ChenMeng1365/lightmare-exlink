/*
Copyright (C) 2019-2020 Huawei Technologies Co., Ltd. All rights reserved.
*/
module huawei-trustem {
  namespace "urn:huawei:yang:huawei-trustem";
  prefix trustem;
  import huawei-extension {
    prefix ext;
  } 
  organization
    "Huawei Technologies Co., Ltd.";
  contact
    "Huawei Industrial Base
     Bantian, Longgang
     Shenzhen 518129
     People's Republic of China
     Website: http://www.huawei.com
     Email: support@huawei.com";
  description
    "Indicate TPM (Trusted Platform Module) environment management.";
  revision 2020-04-02 {
    description
      "YANG check.";
    reference
      "Huawei private.";
  }
  revision 2019-05-27 {
    description
      "Initial revision.";
    reference
      "Huawei private.";
  }

  ext:task-name "tpm";
  
  typedef status-type {
    type enumeration {
      enum "active" {
        value 1;
        description
          "Status active.";
      }
    }
    description
      "TPM status.";
  }

  container trustem {
    config false;
    description
      "Indicate trust environment management.";
    container statuss {
      description
        "List of operational state of TPM status information.";
      list status {
        key "slot-id";
        description
          "Operational state of TPM status information.";
        leaf slot-id {
          type string {
            length "1..32";
          }
          description
            "Slot ID of a board.";
        }
        leaf version {
          type string {
            length "1..127";
          }
          description
            "TPM version.";
        }
        leaf manufacturer {
          type string {
            length "1..127";
          }
          description
            "TPM manufacturer.";
        }
        leaf status {
          type status-type;
          description
            "TPM status.";
        }
      }
    }
  }
}
