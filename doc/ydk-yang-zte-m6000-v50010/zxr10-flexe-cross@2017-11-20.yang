module zxr10-flexe-cross {
  namespace 'http://www.zte.com.cn/zxr10/netconf/schema/rosng/flexe-cross'
            ;
  prefix flexe-cross ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe the flexE cross relationships bet'
            + 'ween two flexE client interfaces.'
              ;
  revision 2017-11-20 {
    description 'The initial version'
                ;
  }
  container configuration {
    description 'Describe the configuration of the flexE cross relationships be'
              + 'tween two flexE client interfaces.'
                ;
    container flexe-crosses {
      description 'Describe the parameters of the flexE cross relationships bet'
                + 'ween two flexE client interfaces.'
                  ;
      list flexe-cross {
        description 'The list of the flexE cross relationships between two flex'
                  + 'E client interfaces.'
                    ;
        key flexe-client-x ;
        leaf flexe-client-x {
          description 'The flexE client interface x of the flexE cross relation'
                    + 'ship'
                      ;
          type ncd:ifname ;
        }
        leaf flexe-client-y {
          description 'The flexE client interface y of the flexE cross relation'
                    + 'ship'
                      ;
          type ncd:ifname ;
          mandatory true ;
        }
      }
    }
  }
}
