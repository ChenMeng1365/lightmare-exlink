module zxr10-mdi {
  namespace 'http://www.zte.com.cn/zxr10/netconf/schema/rosng/mdi'
            ;
  prefix mdi ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module of describing MDI.'
              ;
  revision 2017-06-21 {
    description 'Modify the project label.'
                ;
  }
  revision 2017-03-12 {
    description 'Initial version.'
                ;
  }
  container configuration {
    description 'MDI module configuration info.'
                ;
    container mdi {
      description 'MDI module configure root node.'
                  ;
      container mdi-v4 {
        description 'IPv4 MDI module configure information.'
                    ;
        container mdi-detections {
          description 'Public mode of MDI module configure information.'
                      ;
          list mdi-detection {
            description 'Public mode of MDI module configure information.'
                        ;
            key 'source group'
                ;
            leaf source {
              description 'Source address.'
                          ;
              type ncd:ipv4-address ;
            }
            leaf group {
              description 'Group address.'
                          ;
              type ncd:ipv4-address ;
            }
            leaf session-id {
              description 'Session identifier.'
                          ;
              type uint32 ;
            }
            leaf bit-rate-type {
              description 'Bit rate type.'
                          ;
              type enumeration {
                enum vbr {
                  value 1 ;
                  description 'Variable bit rate.'
                              ;
                }
                enum cbr {
                  value 2 ;
                  description 'Constant bit rate.'
                              ;
                }
              }
              default vbr ;
            }
            leaf code-rate {
              description 'Code rate(Kbps).'
                          ;
              type uint32 {
                range 1..1000000 {
                  description 'Code rate(kbps).'
                              ;
                }
              }
            }
            leaf detection-mode {
              description 'Detection mode.'
                          ;
              type enumeration {
                enum pre-activated {
                  value 1 ;
                  description 'Activation patterns in advance.'
                              ;
                }
                enum as-required {
                  value 2 ;
                  description 'According to the need.'
                              ;
                }
              }
              default pre-activated ;
            }
            leaf detection-duration {
              description 'Detection duration(second).'
                          ;
              type uint32 {
                range 10..604800 ;
              }
              default 900 ;
            }
            leaf cal-period {
              description 'Calculate period(second).'
                          ;
              type uint32 {
                range 1 ;
              }
              default 1 ;
            }
            leaf probe-period {
              description 'Probe period(second).'
                          ;
              type uint32 {
                range 10..900 ;
              }
              default 60 ;
            }
          }
        }
        container vrf-mdi-detections {
          description 'Private mode of MDI module configure information.'
                      ;
          list vrf-mdi-detection {
            description 'Private mode of MDI module configure information.'
                        ;
            key 'vrf-name source group'
                ;
            leaf vrf-name {
              description 'VPN Routing/Forwarding instance name.'
                          ;
              type string {
                length 1..32 ;
              }
            }
            leaf source {
              description 'Source address.'
                          ;
              type ncd:ipv4-address ;
            }
            leaf group {
              description 'Group address.'
                          ;
              type ncd:ipv4-address ;
            }
            leaf session-id {
              description 'Session identifier.'
                          ;
              type uint32 ;
            }
            leaf bit-rate-type {
              description 'Bit rate type.'
                          ;
              type enumeration {
                enum vbr {
                  value 1 ;
                  description 'Variable bit rate.'
                              ;
                }
                enum cbr {
                  value 2 ;
                  description 'Constant bit rate.'
                              ;
                }
              }
              default vbr ;
            }
            leaf code-rate {
              description 'Code rate(Kbps).'
                          ;
              type uint32 {
                range 1..1000000 {
                  description 'Code rate(kbps).'
                              ;
                }
              }
            }
            leaf detection-mode {
              description 'Detection mode.'
                          ;
              type enumeration {
                enum pre-activated {
                  value 1 ;
                  description 'Activation patterns in advance.'
                              ;
                }
                enum as-required {
                  value 2 ;
                  description 'According to the need.'
                              ;
                }
              }
              default pre-activated ;
            }
            leaf detection-duration {
              description 'Detection duration(second).'
                          ;
              type uint32 {
                range 10..604800 ;
              }
              default 900 ;
            }
            leaf cal-period {
              description 'Calculate period(second).'
                          ;
              type uint32 {
                range 1 ;
              }
              default 1 ;
            }
            leaf probe-period {
              description 'Probe period(second).'
                          ;
              type uint32 {
                range 10..900 ;
              }
              default 60 ;
            }
          }
        }
      }
    }
  }
  container state {
    description 'MDI module state information.'
                ;
    config false ;
    container mdi {
      description 'MDI module state information.'
                  ;
      container mdi-v4 {
        description 'IPv4 MDI module state information.'
                    ;
        container mdi-detections {
          description 'Public mode of MDI detection information.'
                      ;
          list mdi-detection {
            description 'Public mode of MDI detection information.'
                        ;
            key 'source group'
                ;
            ncd:select 'source group'
                       ;
            leaf source {
              description 'Source address.'
                          ;
              type ncd:ipv4-address ;
            }
            leaf group {
              description 'Group address.'
                          ;
              type ncd:ipv4-address ;
            }
            leaf session-id {
              description 'Session identifier.'
                          ;
              type uint32 {
                range 0..4294967295 ;
              }
            }
            container stats-infos {
              description 'Statistics info.'
                          ;
              list stats-info {
                description 'Statistics info.'
                            ;
                key index ;
                leaf index {
                  description 'Sequence index.'
                              ;
                  type uint32 {
                    range 1..4294967295 ;
                  }
                }
                leaf mlt-15m {
                  description 'The media loss counts in the last fifteen minute'
                            + 's.'
                              ;
                  type string {
                    length 0..23 ;
                  }
                }
                leaf mlt-24h {
                  description 'The media loss counts in the last twenty-four ho'
                            + 'urs.'
                              ;
                  type string {
                    length 0..23 ;
                  }
                }
                leaf df-max {
                  description 'The maximum delay factors(ms).'
                              ;
                  type string {
                    length 0..23 ;
                  }
                }
                leaf df-min {
                  description 'The minimum delay factors(ms).'
                              ;
                  type string {
                    length 0..23 ;
                  }
                }
                leaf df-mean {
                  description 'The average delay factors(ms).'
                              ;
                  type string {
                    length 0..23 ;
                  }
                }
                leaf mlr-max {
                  description 'The maximum media loss rate.'
                              ;
                  type string {
                    length 0..23 ;
                  }
                }
                leaf mlr-min {
                  description 'The minimum media loss rate.'
                              ;
                  type string {
                    length 0..23 ;
                  }
                }
                leaf mlr-mean {
                  description 'The average media loss rate.'
                              ;
                  type string {
                    length 0..23 ;
                  }
                }
              }
            }
          }
        }
        container vrf-mdi-detections {
          description 'Private mode of MDI detection information.'
                      ;
          list vrf-mdi-detection {
            description 'Private mode of MDI detection information.'
                        ;
            key 'vrf-name source group'
                ;
            ncd:select vrf-name ;
            ncd:select 'vrf-name source group'
                       ;
            leaf vrf-name {
              description 'VPN Routing/Forwarding instance name.'
                          ;
              type string {
                length 1..32 ;
              }
            }
            leaf source {
              description 'Source address.'
                          ;
              type ncd:ipv4-address ;
            }
            leaf group {
              description 'Group address.'
                          ;
              type ncd:ipv4-address ;
            }
            leaf session-id {
              description 'Session identifier.'
                          ;
              type uint32 {
                range 0..4294967295 ;
              }
            }
            container stats-infos {
              description 'Statistics info.'
                          ;
              list stats-info {
                description 'Statistics info.'
                            ;
                key index ;
                leaf index {
                  description 'Sequence index.'
                              ;
                  type uint32 {
                    range 1..4294967295 ;
                  }
                }
                leaf mlt-15m {
                  description 'The media loss counts in the last fifteen minute'
                            + 's.'
                              ;
                  type string {
                    length 0..23 ;
                  }
                }
                leaf mlt-24h {
                  description 'The media loss counts in the last twenty-four ho'
                            + 'urs.'
                              ;
                  type string {
                    length 0..23 ;
                  }
                }
                leaf df-max {
                  description 'The maximum delay factors(ms).'
                              ;
                  type string {
                    length 0..23 ;
                  }
                }
                leaf df-min {
                  description 'The minimum delay factors(ms).'
                              ;
                  type string {
                    length 0..23 ;
                  }
                }
                leaf df-mean {
                  description 'The average delay factors(ms).'
                              ;
                  type string {
                    length 0..23 ;
                  }
                }
                leaf mlr-max {
                  description 'The maximum media loss rate.'
                              ;
                  type string {
                    length 0..23 ;
                  }
                }
                leaf mlr-min {
                  description 'The minimum media loss rate.'
                              ;
                  type string {
                    length 0..23 ;
                  }
                }
                leaf mlr-mean {
                  description 'The average media loss rate.'
                              ;
                  type string {
                    length 0..23 ;
                  }
                }
              }
            }
          }
        }
      }
    }
  }
}
