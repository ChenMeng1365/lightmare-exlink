module zxr10-mld-dev-upn {
  namespace 'http://www.zte.com.cn/zxr10/netconf/schema/rosng/mld-dev-upn' ;
  prefix router-mld ;
  import zxr10-mld {
    prefix mld ;
  }
  organization 'ZTE Corporation' ;
  contact "ZTE Corporation  
\n"
        + "   Nanjing Institute of ZTE Corporation 
\n"
        + "   No.68 Zijinghua Rd. Yuhuatai District, Nanjing, China 
\n"
        + '   Tel: +86-25-52870000'
          ;
  description 'MLD in router.' ;
  revision 2015-04-02 {
    description 'Delete the revision date of the import.' ;
  }
  revision 2014-03-11 {
    description 'Initial version.' ;
  }
  deviation /mld:configuration/mld:router-mld/mld:mlds/mld:group-intf-nums {
    description 'Max host limit commands' ;
    deviate not-supported ;
  }
  deviation "/mld:configuration/mld:router-mld/mld:mlds-vrf/mld:mld-vrf/mld:gro"
          + "up-intf-nums"
            {
    description 'Max host limit commands' ;
    deviate not-supported ;
  }
}
