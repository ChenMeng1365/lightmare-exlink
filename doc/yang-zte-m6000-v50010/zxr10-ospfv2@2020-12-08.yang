module zxr10-ospfv2 {
  namespace 'http://www.zte.com.cn/zxr10/netconf/schema/rosng/ospfv2'
            ;
  prefix ospfv2 ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe OSPFV2.'
              ;
  revision 2020-12-08 {
    description 'Add a leaf:'+"\n"
              + '/ospfv2:configuration/ospfv2:ospfv2/ospfv2:processes/ospfv2:pr'
              + 'ocess/ospfv2:areas/ospfv2:area/ospfv2:intfs/ospfv2:intf/ospfv2'
              + ':network-type/ospfv2:network-type/ospfv2:point-to-point/ospfv2'
              + ':point-to-point/ospfv2:ignore-subnet-check'
                ;
  }
  revision 2020-10-22 {
    description 'Add a container:'+"\n"
              + '/ospfv2:configuration/ospfv2:ospfv2/ospfv2:processes/ospfv2:pr'
              + 'ocess/ospfv2:flex-algorithms'+"\n"
              + 'Add a list:'+"\n"
              + '/ospfv2:configuration/ospfv2:ospfv2/ospfv2:processes/ospfv2:pr'
              + 'ocess/ospfv2:flex-algorithms/ospfv2:flex-algorithm'+"\n"
              + 'Add a leaf:'+"\n"
              + '/ospfv2:configuration/ospfv2:ospfv2/ospfv2:processes/ospfv2:pr'
              + 'ocess/ospfv2:flex-algorithms/ospfv2:flex-algorithm/ospfv2:numb'
              + 'er'
                ;
  }
  revision 2020-10-20 {
    description 'modify leaf:&#xD;'+"\n"
              + '/ospfv2:configuration/ospfv2:ospfv2/ospfv2:processes/ospfv2:pr'
              + 'ocess/ospfv2:frr-policy/ospfv2:route-policy/ospfv2:intfs/ospfv'
              + '2:route-policy-name&#xD;'+"\n"
              + '/ospfv2:configuration/ospfv2:ospfv2/ospfv2:processes/ospfv2:pr'
              + 'ocess/ospfv2:distance-policy/ospfv2:policy-name'
                ;
  }
  revision 2020-08-25 {
    description 'add case:/ospfv2:configuration/ospfv2:ospfv2/ospfv2:processes/'
              + 'ospfv2:process/ospfv2:ti-lfa/ospfv2:protection-type/ospfv2:nod'
              + 'e-protecting-choice-clear'+"\n"
              + 'add container:/ospfv2:configuration/ospfv2:ospfv2/ospfv2:proce'
              + 'sses/ospfv2:process/ospfv2:ti-lfa/ospfv2:protection-type/ospfv'
              + '2:node-protecting-choice-clear/ospfv2:node-protecting-all-clea'
              + 'r'
                ;
  }
  revision 2020-07-23 {
    description 'add leaf:/ospfv2:configuration/ospfv2:ospfv2/ospfv2:processes/'
              + 'ospfv2:process/ospfv2:suppress-flapping/ospfv2:adjacency/ospfv'
              + '2:capability'+"\n"
              + 'add container:Data node path:'+"\n"
              + '/ospfv2:configuration/ospfv2:ospfv2/ospfv2:processes/ospfv2:pr'
              + 'ocess/ospfv2:areas/ospfv2:area/ospfv2:intfs/ospfv2:intf/ospfv2'
              + ':suppress-flapping'
                ;
  }
  revision 2020-07-14 {
    description 'update secret key len from 108 to 128'+"\n"
              + '/ospfv2:configuration/ospfv2:ospfv2/ospfv2:processes/ospfv2:pr'
              + 'ocess/ospfv2:interfaces/ospfv2:interface/ospfv2:authentication'
              + '-key'+"\n"
              + '/ospfv2:configuration/ospfv2:ospfv2/ospfv2:processes/ospfv2:pr'
              + 'ocess/ospfv2:interfaces/ospfv2:interface/ospfv2:authenkey-p'+"\n"
              + '/ospfv2:configuration/ospfv2:ospfv2/ospfv2:processes/ospfv2:pr'
              + 'ocess/ospfv2:interfaces/ospfv2:interface/ospfv2:md-key/ospfv2:'
              + 'secret-key/ospfv2:md5-password-type/ospfv2:unencrypted/ospfv2:'
              + 'secret-key'+"\n"
              + '/ospfv2:configuration/ospfv2:ospfv2/ospfv2:processes/ospfv2:pr'
              + 'ocess/ospfv2:interfaces/ospfv2:interface/ospfv2:md-key/ospfv2:'
              + 'secret-key/ospfv2:md5-password-type/ospfv2:encrypted/ospfv2:en'
              + 'cry-secret-key'+"\n"
              + ''+"\n"
              + '/ospfv2:configuration/ospfv2:ospfv2/ospfv2:processes/ospfv2:pr'
              + 'ocess/ospfv2:areas/ospfv2:area/ospfv2:intfs/ospfv2:intf/ospfv2'
              + ':authentication-key'+"\n"
              + '/ospfv2:configuration/ospfv2:ospfv2/ospfv2:processes/ospfv2:pr'
              + 'ocess/ospfv2:areas/ospfv2:area/ospfv2:intfs/ospfv2:intf/ospfv2'
              + ':authenkey-p'+"\n"
              + '/ospfv2:configuration/ospfv2:ospfv2/ospfv2:processes/ospfv2:pr'
              + 'ocess/ospfv2:areas/ospfv2:area/ospfv2:intfs/ospfv2:intf/ospfv2'
              + ':md-keys/ospfv2:md-key/ospfv2:secret-key/ospfv2:md5-password-t'
              + 'ype/ospfv2:unencrypted/ospfv2:secret-key'+"\n"
              + '/ospfv2:configuration/ospfv2:ospfv2/ospfv2:processes/ospfv2:pr'
              + 'ocess/ospfv2:areas/ospfv2:area/ospfv2:intfs/ospfv2:intf/ospfv2'
              + ':md-keys/ospfv2:md-key/ospfv2:secret-key/ospfv2:md5-password-t'
              + 'ype/ospfv2:encrypted/ospfv2:encry-secret-key'+"\n"
              + '/ospfv2:configuration/ospfv2:ospfv2/ospfv2:processes/ospfv2:pr'
              + 'ocess/ospfv2:areas/ospfv2:area/ospfv2:nssa-stub-virtual/ospfv2'
              + ':nssa-stub-virtual/ospfv2:virtual/ospfv2:virtuals/ospfv2:virtu'
              + 'al/ospfv2:auth-password-type/ospfv2:unencrypted/ospfv2:authenk'
              + 'ey'+"\n"
              + '/ospfv2:configuration/ospfv2:ospfv2/ospfv2:processes/ospfv2:pr'
              + 'ocess/ospfv2:areas/ospfv2:area/ospfv2:nssa-stub-virtual/ospfv2'
              + ':nssa-stub-virtual/ospfv2:virtual/ospfv2:virtuals/ospfv2:virtu'
              + 'al/ospfv2:auth-password-type/ospfv2:encrypted/ospfv2:encry-aut'
              + 'henkey'+"\n"
              + ''+"\n"
              + '/ospfv2:configuration/ospfv2:ospfv2/ospfv2:processes/ospfv2:pr'
              + 'ocess/ospfv2:areas/ospfv2:area/ospfv2:nssa-stub-virtual/ospfv2'
              + ':nssa-stub-virtual/ospfv2:virtual/ospfv2:virtuals/ospfv2:virtu'
              + 'al/ospfv2:md5s/ospfv2:md5/ospfv2:secret-key/ospfv2:md5-passwor'
              + 'd-type/ospfv2:unencrypted/ospfv2:secret-key'+"\n"
              + '/ospfv2:configuration/ospfv2:ospfv2/ospfv2:processes/ospfv2:pr'
              + 'ocess/ospfv2:areas/ospfv2:area/ospfv2:nssa-stub-virtual/ospfv2'
              + ':nssa-stub-virtual/ospfv2:virtual/ospfv2:virtuals/ospfv2:virtu'
              + 'al/ospfv2:md5s/ospfv2:md5/ospfv2:secret-key/ospfv2:md5-passwor'
              + 'd-type/ospfv2:encrypted/ospfv2:encry-secret-key'+"\n"
              + '/ospfv2:configuration/ospfv2:ospfv2/ospfv2:processes/ospfv2:pr'
              + 'ocess/ospfv2:areas/ospfv2:area/ospfv2:multi-area-interfaces/os'
              + 'pfv2:multi-area-interfaces/ospfv2:authentication-key/ospfv2:au'
              + 'thentication-key/ospfv2:clear/ospfv2:clear'+"\n"
              + '/ospfv2:configuration/ospfv2:ospfv2/ospfv2:processes/ospfv2:pr'
              + 'ocess/ospfv2:areas/ospfv2:area/ospfv2:multi-area-interfaces/os'
              + 'pfv2:multi-area-interfaces/ospfv2:authentication-key/ospfv2:au'
              + 'thentication-key/ospfv2:encrypted/ospfv2:encrypted'
                ;
  }
  revision 2020-06-22 {
    description 'update:'+"\n"
              + '/ospfv2:configuration/ospfv2:ospfv2/ospfv2:processes/ospfv2:pr'
              + 'ocess/ospfv2:interfaces/ospfv2:interface/ospfv2:authentication'
              + '-key'+"\n"
              + '/ospfv2:configuration/ospfv2:ospfv2/ospfv2:processes/ospfv2:pr'
              + 'ocess/ospfv2:interfaces/ospfv2:interface/ospfv2:authenkey-p'+"\n"
              + '/ospfv2:configuration/ospfv2:ospfv2/ospfv2:processes/ospfv2:pr'
              + 'ocess/ospfv2:interfaces/ospfv2:interface/ospfv2:md-key/ospfv2:'
              + 'secret-key/ospfv2:md5-password-type/ospfv2:unencrypted/ospfv2:'
              + 'secret-key'+"\n"
              + '/ospfv2:configuration/ospfv2:ospfv2/ospfv2:processes/ospfv2:pr'
              + 'ocess/ospfv2:interfaces/ospfv2:interface/ospfv2:md-key/ospfv2:'
              + 'secret-key/ospfv2:md5-password-type/ospfv2:encrypted/ospfv2:en'
              + 'cry-secret-key'+"\n"
              + ''+"\n"
              + '/ospfv2:configuration/ospfv2:ospfv2/ospfv2:processes/ospfv2:pr'
              + 'ocess/ospfv2:areas/ospfv2:area/ospfv2:intfs/ospfv2:intf/ospfv2'
              + ':authentication-key'+"\n"
              + '/ospfv2:configuration/ospfv2:ospfv2/ospfv2:processes/ospfv2:pr'
              + 'ocess/ospfv2:areas/ospfv2:area/ospfv2:intfs/ospfv2:intf/ospfv2'
              + ':authenkey-p'+"\n"
              + '/ospfv2:configuration/ospfv2:ospfv2/ospfv2:processes/ospfv2:pr'
              + 'ocess/ospfv2:areas/ospfv2:area/ospfv2:intfs/ospfv2:intf/ospfv2'
              + ':md-keys/ospfv2:md-key/ospfv2:secret-key/ospfv2:md5-password-t'
              + 'ype/ospfv2:unencrypted/ospfv2:secret-key'+"\n"
              + '/ospfv2:configuration/ospfv2:ospfv2/ospfv2:processes/ospfv2:pr'
              + 'ocess/ospfv2:areas/ospfv2:area/ospfv2:intfs/ospfv2:intf/ospfv2'
              + ':md-keys/ospfv2:md-key/ospfv2:secret-key/ospfv2:md5-password-t'
              + 'ype/ospfv2:encrypted/ospfv2:encry-secret-key'+"\n"
              + '/ospfv2:configuration/ospfv2:ospfv2/ospfv2:processes/ospfv2:pr'
              + 'ocess/ospfv2:areas/ospfv2:area/ospfv2:nssa-stub-virtual/ospfv2'
              + ':nssa-stub-virtual/ospfv2:virtual/ospfv2:virtuals/ospfv2:virtu'
              + 'al/ospfv2:auth-password-type/ospfv2:unencrypted/ospfv2:authenk'
              + 'ey'+"\n"
              + '/ospfv2:configuration/ospfv2:ospfv2/ospfv2:processes/ospfv2:pr'
              + 'ocess/ospfv2:areas/ospfv2:area/ospfv2:nssa-stub-virtual/ospfv2'
              + ':nssa-stub-virtual/ospfv2:virtual/ospfv2:virtuals/ospfv2:virtu'
              + 'al/ospfv2:auth-password-type/ospfv2:encrypted/ospfv2:encry-aut'
              + 'henkey'+"\n"
              + ''+"\n"
              + '/ospfv2:configuration/ospfv2:ospfv2/ospfv2:processes/ospfv2:pr'
              + 'ocess/ospfv2:areas/ospfv2:area/ospfv2:nssa-stub-virtual/ospfv2'
              + ':nssa-stub-virtual/ospfv2:virtual/ospfv2:virtuals/ospfv2:virtu'
              + 'al/ospfv2:md5s/ospfv2:md5/ospfv2:secret-key/ospfv2:md5-passwor'
              + 'd-type/ospfv2:unencrypted/ospfv2:secret-key'+"\n"
              + '/ospfv2:configuration/ospfv2:ospfv2/ospfv2:processes/ospfv2:pr'
              + 'ocess/ospfv2:areas/ospfv2:area/ospfv2:nssa-stub-virtual/ospfv2'
              + ':nssa-stub-virtual/ospfv2:virtual/ospfv2:virtuals/ospfv2:virtu'
              + 'al/ospfv2:md5s/ospfv2:md5/ospfv2:secret-key/ospfv2:md5-passwor'
              + 'd-type/ospfv2:encrypted/ospfv2:encry-secret-key'+"\n"
              + '/ospfv2:configuration/ospfv2:ospfv2/ospfv2:processes/ospfv2:pr'
              + 'ocess/ospfv2:areas/ospfv2:area/ospfv2:multi-area-interfaces/os'
              + 'pfv2:multi-area-interfaces/ospfv2:authentication-key/ospfv2:au'
              + 'thentication-key/ospfv2:clear/ospfv2:clear'+"\n"
              + '/ospfv2:configuration/ospfv2:ospfv2/ospfv2:processes/ospfv2:pr'
              + 'ocess/ospfv2:areas/ospfv2:area/ospfv2:multi-area-interfaces/os'
              + 'pfv2:multi-area-interfaces/ospfv2:authentication-key/ospfv2:au'
              + 'thentication-key/ospfv2:encrypted/ospfv2:encrypted'
                ;
  }
  revision 2020-06-20 {
    description 'Modify range:'+"\n"
              + '/ospfv2:configuration/ospfv2:ospfv2/ospfv2:processes/ospfv2:pr'
              + 'ocess/ospfv2:distribute-list/ospfv2:distribute-list-in/ospfv2:'
              + 'distribute-list-name/ospfv2:prefix-list/ospfv2:name-ip-prefxi-'
              + 'list/ospfv2:prefix-list-gateway'+"\n"
              + '/ospfv2:configuration/ospfv2:ospfv2/ospfv2:processes/ospfv2:pr'
              + 'ocess/ospfv2:distribute-list/ospfv2:distribute-list-in/ospfv2:'
              + 'distribute-list-name/ospfv2:prefix-list/ospfv2:name-ip-prefxi-'
              + 'list/ospfv2:name-ip-prefxi-list'+"\n"
              + '/ospfv2:configuration/ospfv2:ospfv2/ospfv2:processes/ospfv2:pr'
              + 'ocess/ospfv2:distribute-list/ospfv2:distribute-list-in/ospfv2:'
              + 'distribute-list-name/ospfv2:gateway/ospfv2:gatewayt/ospfv2:gat'
              + 'eway'+"\n"
              + '/ospfv2:configuration/ospfv2:ospfv2/ospfv2:processes/ospfv2:pr'
              + 'ocess/ospfv2:distribute-list/ospfv2:distribute-list-in/ospfv2:'
              + 'distribute-list-name/ospfv2:route-map/ospfv2:name-route-map/os'
              + 'pfv2:name-route-map'+"\n"
              + '/ospfv2:configuration/ospfv2:ospfv2/ospfv2:processes/ospfv2:pr'
              + 'ocess/ospfv2:distribute-list/ospfv2:distribute-list-out/ospfv2'
              + ':distribute-list-name/ospfv2:prefix-list-name/ospfv2:prefxi-li'
              + 'st/ospfv2:name-ip-prefxi-list/ospfv2:name-ip-prefxi-list'+"\n"
              + '/ospfv2:configuration/ospfv2:ospfv2/ospfv2:processes/ospfv2:pr'
              + 'ocess/ospfv2:redistribute/ospfv2:redistribute-isiss/ospfv2:red'
              + 'istribute-isis/ospfv2:route-map'+"\n"
              + '/ospfv2:configuration/ospfv2:ospfv2/ospfv2:processes/ospfv2:pr'
              + 'ocess/ospfv2:redistribute/ospfv2:redistribute-bgps/ospfv2:redi'
              + 'stribute-bgp/ospfv2:route-map'+"\n"
              + '/ospfv2:configuration/ospfv2:ospfv2/ospfv2:processes/ospfv2:pr'
              + 'ocess/ospfv2:redistribute/ospfv2:redistribute-pss/ospfv2:redis'
              + 'tribute-ps/ospfv2:route-map'+"\n"
              + '/ospfv2:configuration/ospfv2:ospfv2/ospfv2:processes/ospfv2:pr'
              + 'ocess/ospfv2:redistribute/ospfv2:redistribute-ospfs/ospfv2:red'
              + 'istribute-ospf/ospfv2:route-map'+"\n"
              + '/ospfv2:configuration/ospfv2:ospfv2/ospfv2:processes/ospfv2:pr'
              + 'ocess/ospfv2:redistribute/ospfv2:redistributes/ospfv2:redistri'
              + 'bute/ospfv2:route-map'+"\n"
              + '/ospfv2:configuration/ospfv2:ospfv2/ospfv2:processes/ospfv2:pr'
              + 'ocess/ospfv2:notify-default-route/ospfv2:route-map'+"\n"
              + '/ospfv2:configuration/ospfv2:ospfv2/ospfv2:processes/ospfv2:pr'
              + 'ocess/ospfv2:prefix-prioritys/ospfv2:prefix-priority/ospfv2:pr'
              + 'iority'+"\n"
              + '/ospfv2:configuration/ospfv2:ospfv2/ospfv2:processes/ospfv2:pr'
              + 'ocess/ospfv2:areas/ospfv2:area/ospfv2:filters/ospfv2:filter/os'
              + 'pfv2:prefix-name'+"\n"
              + '/ospfv2:configuration/ospfv2:ospfv2/ospfv2:processes/ospfv2:pr'
              + 'ocess/ospfv2:areas/ospfv2:area/ospfv2:intfs/ospfv2:intf/ospfv2'
              + ':static-remote-lfa/ospfv2:next-hop-prefixs/ospfv2:next-hop-pre'
              + 'fix/ospfv2:prefix-list'
                ;
  }
  revision 2020-06-01 {
    description 'Add three new leafs:'+"\n"
              + '/ospfv2:configuration/ospfv2:ospfv2/ospfv2:processes/ospfv2:pr'
              + 'ocess/ospfv2:bfd/ospfv2:template'+"\n"
              + '/ospfv2:configuration/ospfv2:ospfv2/ospfv2:processes/ospfv2:pr'
              + 'ocess/ospfv2:areas/ospfv2:area/ospfv2:/ospfv2:bfd/ospfv2:templ'
              + 'ate'+"\n"
              + '/ospfv2:configuration/ospfv2:ospfv2/ospfv2:processes/ospfv2:pr'
              + 'ocess/ospfv2:areas/ospfv2:area/ospfv2:/ospfv2:intfs/ospfv2:int'
              + 'f/ospfv2:bfd/ospfv2:template'
                ;
  }
  revision 2020-04-09 {
    description 'Add container:'+"\n"
              + '/ospfv2:configuration/ospfv2:ospfv2/ospfv2:processes/ospfv2:pr'
              + 'ocess/ospfv2:areas/ospfv2:area/ospfv2:intfs/ospfv2:intf/ospfv2'
              + ':ti-lfa'+"\n"
              + 'Add list:'+"\n"
              + '/ospfv2:configuration/ospfv2:ospfv2/ospfv2:processes/ospfv2:pr'
              + 'ocess/ospfv2:areas/ospfv2:area/ospfv2:intfs/ospfv2:intf/ospfv2'
              + ':ti-lfa/ospfv2:srlg'+"\n"
              + 'Add leaf node'+"\n"
              + '/ospfv2:configuration/ospfv2:ospfv2/ospfv2:processes/ospfv2:pr'
              + 'ocess/ospfv2:areas/ospfv2:area/ospfv2:intfs/ospfv2:intf/ospfv2'
              + ':ti-lfa/ospfv2:srlg/ospfv2:srlg-id'
                ;
  }
  revision 2020-03-27 {
    description 'Add new leaf:'+"\n"
              + '/ospfv2:configuration/ospfv2:ospfv2/ospfv2:processes/ospfv2:pr'
              + 'ocess/ospfv2:segment-routing/ospfv2:mpls/ospfv2:adj-sid/ospfv2'
              + ':type'
                ;
  }
  revision 2020-02-04 {
    description 'Add new leaf:'+"\n"
              + '/ospfv2:configuration/ospfv2:ospfv2/ospfv2:processes/ospfv2:pr'
              + 'ocess/ospfv2:te-link-delay'
                ;
  }
  revision 2020-01-09 {
    description 'Add new container'+"\n"
              + '/ospfv2:configuration/ospfv2:ospfv2/ospfv2:processes/ospfv2:pr'
              + 'ocess/ospfv2:areas/ospfv2:area/ospfv2:/ospfv2:multi-area-inter'
              + 'face'
                ;
  }
  revision 2019-12-16 {
    description 'ospfv2 add encrypted auth key'
                ;
  }
  revision 2019-11-23 {
    description 'Add new container:'+"\n"
              + '/ospfv2:configuration/ospfv2:ospfv2/ospfv2:processes/ospfv2:pr'
              + 'ocess/ospfv2:areas/ospfv2:area/ospfv2:intfs/ospfv2:intf/ospfv2'
              + ':cost-bfd-down'+"\n"
              + 'Add new leaf:'+"\n"
              + '/ospfv2:configuration/ospfv2:ospfv2/ospfv2:processes/ospfv2:pr'
              + 'ocess/ospfv2:areas/ospfv2:area/ospfv2:intfs/ospfv2:intf/ospfv2'
              + ':cost-bfd-down/ospfv2:cost-bfd-down/ospfv2:increase-value/ospf'
              + 'v2:increase-value'+"\n"
              + 'Add new leaf:'+"\n"
              + '/ospfv2:configuration/ospfv2:ospfv2/ospfv2:processes/ospfv2:pr'
              + 'ocess/ospfv2:areas/ospfv2:area/ospfv2:intfs/ospfv2:intf/ospfv2'
              + ':cost-bfd-down/ospfv2:cost-bfd-down/ospfv2:maximum/ospfv2:maxi'
              + 'mum'
                ;
  }
  revision 2019-11-12 {
    description 'Add new leaf:'+"\n"
              + '/ospfv2:configuration/ospfv2:ospfv2/ospfv2:processes/ospfv2:pr'
              + 'ocess/ospfv2:segment-routing/ospfv2:mpls/ospfv2:entropy-label/'
              + 'ospfv2:capability'
                ;
  }
  revision 2019-08-21 {
    description '1. Add new leaf:'+"\n"
              + '/ospfv2:configuration/ospfv2:ospfv2/ospfv2:processes/ospfv2:pr'
              + 'ocess/ospfv2:ti-lfa/ospfv2:node-protecting'
                ;
  }
  revision 2019-08-07 {
    description '1. Add new leaf:'+"\n"
              + '/ospfv2:configuration/ospfv2:ospfv2/ospfv2:processes/ospfv2:pr'
              + 'ocess/ospfv2:microloop-prevention/ospfv2:segment-routing/ospfv'
              + '2:mpls/ospfv2:capability'+"\n"
              + '/ospfv2:configuration/ospfv2:ospfv2/ospfv2:processes/ospfv2:pr'
              + 'ocess/ospfv2:microloop-prevention/ospfv2:segment-routing/ospfv'
              + '2:mpls/ospfv2:delay-time'
                ;
  }
  revision 2019-08-03 {
    description 'Add new container:'+"\n"
              + '/ospfv2:configuration/ospfv2:ospfv2/ospfv2:processes/ospfv2:pr'
              + 'ocess/ospfv2:areas/ospfv2:area/ospfv2:intfs/ospfv2:intf/ospfv2'
              + ':cost-lag-down'+"\n"
              + 'Add new leaf:'+"\n"
              + '/ospfv2:configuration/ospfv2:ospfv2/ospfv2:processes/ospfv2:pr'
              + 'ocess/ospfv2:areas/ospfv2:area/ospfv2:intfs/ospfv2:intf/ospfv2'
              + ':cost-lag-down/ospfv2:cost-lag-down/ospfv2:increase-value/ospf'
              + 'v2:increase-value'+"\n"
              + 'Add new leaf:'+"\n"
              + '/ospfv2:configuration/ospfv2:ospfv2/ospfv2:processes/ospfv2:pr'
              + 'ocess/ospfv2:areas/ospfv2:area/ospfv2:intfs/ospfv2:intf/ospfv2'
              + ':cost-lag-down/ospfv2:cost-lag-down/ospfv2:maximum/ospfv2:maxi'
              + 'mum'
                ;
  }
  revision 2019-06-20 {
    description 'Add new leaf:'+"\n"
              + '/ospfv2:configuration/ospfv2:ospfv2/ospfv2:processes/ospfv2:pr'
              + 'ocess/ospfv2:redistribute/ospfv2:redistributes/ospfv2:redistri'
              + 'bute/ospfv2:host-only'
                ;
  }
  revision 2019-03-08 {
    description '1. Add an enumeration value:'+"\n"
              + '/ospfv2:configuration/ospfv2:ospfv2/ospfv2:processes/ospfv2:pr'
              + 'ocess/ospfv2:redistribute/ospfv2:redistributes/ospfv2:redistri'
              + 'bute/ospfv2:protocol'
                ;
  }
  revision 2018-11-28 {
    description 'Add new container:'+"\n"
              + '/ospfv2:configuration/ospfv2:ospfv2/ospfv2:processes/ospfv2:pr'
              + 'ocess/ospfv2:distance-policy'+"\n"
              + 'Add new leaf:'+"\n"
              + '/ospfv2:configuration/ospfv2:ospfv2/ospfv2:processes/ospfv2:pr'
              + 'ocess/ospfv2:distance-policy/ospfv2:policy-type'+"\n"
              + 'Add new leaf:'+"\n"
              + '/ospfv2:configuration/ospfv2:ospfv2/ospfv2:processes/ospfv2:pr'
              + 'ocess/ospfv2:distance-policy/ospfv2:policy-name'
                ;
  }
  revision 2018-05-23 {
    description 'Add new container:'+"\n"
              + '/ospfv2:configuration/ospfv2:ospfv2/ospfv2:processes/ospfv2:pr'
              + 'ocess/ospfv2:ti-lfa'+"\n"
              + 'Add new leaf:'+"\n"
              + '/ospfv2:configuration/ospfv2:ospfv2/ospfv2:processes/ospfv2:pr'
              + 'ocess/ospfv2:frr-priority/ospfv2:ti-lfa'
                ;
  }
  revision 2018-04-12 {
    description 'Add new enumeration value:'+"\n"
              + '/ospfv2:configuration/ospfv2:ospfv2/ospfv2:processes/ospfv2:pr'
              + 'ocess/ospfv2:redistribute/ospfv2:redistributes/ospfv2:redistri'
              + 'bute/ospfv2:protocol'
                ;
  }
  revision 2018-03-06 {
    description 'Add new container:'+"\n"
              + '/ospfv2:configuration/ospfv2:ospfv2/ospfv2:processes/ospfv2:pr'
              + 'ocess/ospfv2:segment-routing'
                ;
  }
  revision 2017-12-12 {
    description 'Add new enumeration value:'+"\n"
              + '/ospfv2:configuration/ospfv2:ospfv2/ospfv2:processes/ospfv2:pr'
              + 'ocess/ospfv2:redistribute/ospfv2:redistributes/ospfv2:redistri'
              + 'bute/ospfv2:protocol'
                ;
  }
  revision 2017-07-05 {
    description 'Add new container:'+"\n"
              + '/ospfv2:configuration/ospfv2:ospfv2/ospfv2:processes/ospfv2:pr'
              + 'ocess/ospfv2:frr-policy'
                ;
  }
  revision 2017-06-09 {
    description 'Modify range:'+"\n"
              + '/ospfv2:configuration/ospfv2:ospfv2/ospfv2:processes/ospfv2:pr'
              + 'ocess/ospfv2:bgp-ls/ospfv2:instance-id'
                ;
  }
  revision 2017-04-05 {
    description 'Add new container:'+"\n"
              + '/ospfv2:configuration/ospfv2:ospfv2/ospfv2:processes/ospfv2:pr'
              + 'ocess/ospfv2:areas/ospfv2:area/ospfv2:intfs/ospfv2:intf/ospfv2'
              + ':link-damping'+"\n"
              + 'Add new leaf:'+"\n"
              + '/ospfv2:state/ospfv2:ospfv2/ospfv2:interfaces/ospfv2:normal-in'
              + 'terfaces/ospfv2:normal-interface/ospfv2:damp-state'+"\n"
              + '/ospfv2:state/ospfv2:ospfv2/ospfv2:interfaces/ospfv2:normal-in'
              + 'terfaces/ospfv2:normal-interface/ospfv2:damp-remain'
                ;
  }
  revision 2017-03-30 {
    description 'Add new enumeration value:'+"\n"
              + '1./ospfv2:state/ospfv2:ospfv2/ospfv2:processes/ospfv2:process/'
              + 'ospfv2:areas/ospfv2:area/ospfv2:sending-sa/ospfv2:authen-algor'
              + 'ithm'+"\n"
              + '2./ospfv2:state/ospfv2:ospfv2/ospfv2:interfaces/ospfv2:normal-'
              + 'interfaces/ospfv2:normal-interface/ospfv2:sending-sa/ospfv2:au'
              + 'then-algorithm'+"\n"
              + '3./ospfv2:state/ospfv2:ospfv2/ospfv2:interfaces/ospfv2:virtual'
              + '-interfaces/ospfv2:virtual-interface/ospfv2:sending-sa/ospfv2:'
              + 'authen-algorithm'
                ;
  }
  revision 2017-03-28 {
    description 'Add new enumeration value:'+"\n"
              + '/ospfv2:configuration/ospfv2:ospfv2/ospfv2:processes/ospfv2:pr'
              + 'ocess/ospfv2:redistribute/ospfv2:redistributes/ospfv2:redistri'
              + 'bute/ospfv2:protocol'
                ;
  }
  revision 2017-02-27 {
    description 'Add new container:'+"\n"
              + '/ospfv2:configuration/ospfv2:ospfv2/ospfv2:processes/ospfv2:pr'
              + 'ocess/ospfv2:bgp-ls'
                ;
  }
  revision 2017-01-17 {
    description 'Add new enumeration value:'+"\n"
              + '1./ospfv2:configuration/ospfv2:ospfv2/ospfv2:processes/ospfv2:'
              + 'process/ospfv2:redistribute/ospfv2:redistributes/ospfv2:redist'
              + 'ribute/ospfv2:protocol'
                ;
  }
  revision 2016-12-08 {
    description 'Add  new leaf:'+"\n"
              + '/ospfv2:configuration/ospfv2:ospfv2/ospfv2:processes/ospfv2:pr'
              + 'ocess/ospfv2:redistribute/ospfv2:redistribute-ospfs/ospfv2:red'
              + 'istribute-ospf/ospfv2:with-orig-metric'+"\n"
              + '/ospfv2:configuration/ospfv2:ospfv2/ospfv2:processes/ospfv2:pr'
              + 'ocess/ospfv2:redistribute/ospfv2:redistribute-isiss/ospfv2:red'
              + 'istribute-isis/ospfv2:with-orig-metric'+"\n"
              + '/ospfv2:configuration/ospfv2:ospfv2/ospfv2:processes/ospfv2:pr'
              + 'ocess/ospfv2:redistribute/ospfv2:redistribute-bgps/ospfv2:redi'
              + 'stribute-bgp/ospfv2:with-orig-metric'+"\n"
              + '/ospfv2:configuration/ospfv2:ospfv2/ospfv2:processes/ospfv2:pr'
              + 'ocess/ospfv2:redistribute/ospfv2:redistributes/ospfv2:redistri'
              + 'bute/ospfv2:with-orig-metric'
                ;
  }
  revision 2016-09-20 {
    description '1. Add new container:'+"\n"
              + '/ospfv2:configuration/ospfv2:ospfv2/ospfv2:processes/ospfv2:pr'
              + 'ocess/ospfv2:microloop-prevention'
                ;
  }
  revision 2016-08-10 {
    description '1. Add new container:'+"\n"
              + '/ospfv2:configuration/ospfv2:ospfv2/ospfv2:processes/ospfv2:pr'
              + 'ocess/ospfv2:areas/ospfv2:area/ospfv2:intfs/ospfv2:intf/ospfv2'
              + ':static-remote-lfa/ospfv2:next-hop/specify-nexthop'+"\n"
              + '/ospfv2:configuration/ospfv2:ospfv2/ospfv2:processes/ospfv2:pr'
              + 'ocess/ospfv2:areas/ospfv2:area/ospfv2:intfs/ospfv2:intf/ospfv2'
              + ':static-remote-lfa/ospfv2:next-hop-prefixs/ospfv2:next-hop-pre'
              + 'fix/specify-nexthop'
                ;
  }
  revision 2016-07-01 {
    description '1.Add leaf node:'+"\n"
              + '/ospfv2:configuration/ospfv2:ospfv2/ospfv2:processes/ospfv2:pr'
              + 'ocess/ospfv2:areas/ospfv2:area/ospfv2:nssa-stub-virtual/ospfv2'
              + ':nssa-stub-virtual/ospfv2:nssa-stub-virtual/ospfv2:stub/ospfv2'
              + ':stub/ospfv2:default-origin'
                ;
  }
  revision 2016-04-01 {
    description 'Modify range:'+"\n"
              + '/ospfv2:state/ospfv2:ospfv2/ospfv2:interfaces/ospfv2:normal-in'
              + 'terfaces/ospfv2:normal-interface/ospfv2:cost'
                ;
  }
  revision 2016-03-14 {
    description 'Obsolete container:'+"\n"
              + '1./ospfv2:configuration/ospfv2:ospfv2/ospfv2:processes/ospfv2:'
              + 'process/ospfv2:networks'+"\n"
              + '2./ospfv2:configuration/ospfv2:ospfv2/ospfv2:processes/ospfv2:'
              + 'process/ospfv2:ospf-te-areas'+"\n"
              + 'Modify enumeration value:'+"\n"
              + '/ospfv2:state/ospfv2:ospfv2/ospfv2:interfaces/ospfv2:normal-in'
              + 'terfaces/ospfv2:normal-interface/ospfv2:ldp-link-state'
                ;
  }
  revision 2016-01-18 {
    description 'Add leaf node:'+"\n"
              + '1./ospfv2:configuration/ospfv2:ospfv2/ospfv2:processes/ospfv2:'
              + 'process/ospfv2:areas/ospfv2:area/ospfv2:authtype/ospfv2:authen'
              + '-keychain/ospfv2:keychain'+"\n"
              + '2./ospfv2:configuration/ospfv2:ospfv2/ospfv2:processes/ospfv2:'
              + 'process/ospfv2:areas/ospfv2:area/ospfv2:nssa-stub-virtual/ospf'
              + 'v2:nssa-stub-virtual/ospfv2:virtuals/ospfv2:virtual/ospfv2:aut'
              + 'htype/ospfv2:authen-keychain/ospfv2:keychain'+"\n"
              + '3./ospfv2:configuration/ospfv2:ospfv2/ospfv2:processes/ospfv2:'
              + 'process/ospfv2:areas/ospfv2:area/ospfv2:intfs/ospfv2:intf/ospf'
              + 'v2:authen-keychain/ospfv2:keychain'+"\n"
              + '4./ospfv2:state/ospfv2:ospfv2/ospfv2:processes/ospfv2:process/'
              + 'ospfv2:areas/ospfv2:area/ospfv2:sending-sa/ospfv2:authen-keyid'
              + ''+"\n"
              + '5./ospfv2:state/ospfv2:ospfv2/ospfv2:processes/ospfv2:process/'
              + 'ospfv2:areas/ospfv2:area/ospfv2:sending-sa/ospfv2:authen-algor'
              + 'ithm'+"\n"
              + '6./ospfv2:state/ospfv2:ospfv2/ospfv2:processes/ospfv2:process/'
              + 'ospfv2:areas/ospfv2:area/ospfv2:sending-sa/ospfv2:authen-keych'
              + 'ain'+"\n"
              + '7./ospfv2:state/ospfv2:ospfv2/ospfv2:interfaces/ospfv2:normal-'
              + 'interfaces/ospfv2:normal-interface/ospfv2:sending-sa/ospfv2:au'
              + 'then-keyid'+"\n"
              + '8./ospfv2:state/ospfv2:ospfv2/ospfv2:interfaces/ospfv2:normal-'
              + 'interfaces/ospfv2:normal-interface/ospfv2:sending-sa/ospfv2:au'
              + 'then-algorithm'+"\n"
              + '9./ospfv2:state/ospfv2:ospfv2/ospfv2:interfaces/ospfv2:normal-'
              + 'interfaces/ospfv2:normal-interface/ospfv2:sending-sa/ospfv2:au'
              + 'then-keychain'+"\n"
              + '10./ospfv2:state/ospfv2:ospfv2/ospfv2:interfaces/ospfv2:virtua'
              + 'l-interfaces/ospfv2:virtual-interface/ospfv2:sending-sa/ospfv2'
              + ':authen-keyid'+"\n"
              + '11./ospfv2:state/ospfv2:ospfv2/ospfv2:interfaces/ospfv2:virtua'
              + 'l-interfaces/ospfv2:virtual-interface/ospfv2:sending-sa/ospfv2'
              + ':authen-algorithm'+"\n"
              + '12./ospfv2:state/ospfv2:ospfv2/ospfv2:interfaces/ospfv2:virtua'
              + 'l-interfaces/ospfv2:virtual-interface/ospfv2:sending-sa/ospfv2'
              + ':authen-keychain'
                ;
  }
  revision 2015-12-28 {
    description 'Modify the type of the node to string:'+"\n"
              + '/ospfv2:state/ospfv2:ospfv2/ospfv2:vertexes/ospfv2:vertex/ospf'
              + 'v2:nexthops/ospfv2:nexthop/ospfv2:backup-nexthops/ospfv2:dynam'
              + 'ic-remote-lfas/ospfv2:dynamic-remote-lfa/ospfv2:update-time'
                ;
  }
  revision 2015-12-24 {
    description '1.Add leaf node:'+"\n"
              + '/ospfv2:state/ospfv2:ospfv2/ospfv2:interfaces/ospfv2:normal-in'
              + 'terfaces/ospfv2:normal-interface/ospfv2:no-cut-edge'+"\n"
              + '2.Modify adn rename leaf node:'+"\n"
              + '/ospfv2:state/ospfv2:ospfv2/ospfv2:interfaces/ospfv2:normal-in'
              + 'terfaces/ospfv2:normal-interface/ospfv2:send-max-metric'+"\n"
              + '3.Delete leaf node:'+"\n"
              + '/ospfv2:state/ospfv2:ospfv2/ospfv2:interfaces/ospfv2:shamlink-'
              + 'interfaces/ospfv2:shamlink-interface/ospfv2:send-max-metric'
                ;
  }
  revision 2015-11-12 {
    description 'Modify enumeration value:'+"\n"
              + '/ospfv2:state/ospfv2:ospfv2/ospfv2:vertexes/ospfv2:vertex/ospf'
              + 'v2:nexthops/ospfv2:nexthop/ospfv2:backup-nexthops/ospfv2:dynam'
              + 'ic-remote-LFAs/ospfv2:dynamic-remote-LFA/ospfv2:protect-type-S'
              + '-PQ'
                ;
  }
  revision 2015-10-20 {
    description 'Add container:
/ospfv2:state/ospfv2:ospfv2/ospfv2:vertexes'
                ;
  }
  revision 2015-09-21 {
    description '1. Add unit:'+"\n"
              + 'ospfv2:state/ospfv2:ospfv2/ospfv2:interfaces/ospfv2:shamlink-i'
              + 'nterfaces/ospfv2:shamlink-interface/ospfv2:hello-interval'+"\n"
              + 'ospfv2:state/ospfv2:ospfv2/ospfv2:interfaces/ospfv2:shamlink-i'
              + 'nterfaces/ospfv2:shamlink-interface/ospfv2:dead-interval'
                ;
  }
  revision 2015-09-10 {
    description 'Add container:'+"\n"
              + '1./ospfv2:configuration/ospfv2:ospfv2/ospfv2:processes/ospfv2:'
              + 'process/ospfv2:dynamic-remote-lfa'+"\n"
              + '2./ospfv2:configuration/ospfv2:ospfv2/ospfv2:processes/ospfv2:'
              + 'process/ospfv2:areas/ospfv2:area/ospfv2:dynamic-remote-lfa'+"\n"
              + '3./ospfv2:configuration/ospfv2:ospfv2/ospfv2:processes/ospfv2:'
              + 'process/ospfv2:frr-priority'
                ;
  }
  revision 2015-07-14 {
    description '1.Delete enum values:'+"\n"
              + '/ospfv2:state/ospfv2:ospfv2/ospfv2:neighbors/ospfv2:normal-nei'
              + 'ghbors/ospfv2:normal-neighbor/ospfv2:neighbor-state'
                ;
  }
  revision 2015-07-08 {
    description '1. Modify range:'+"\n"
              + '/ospfv2:state/ospfv2:ospfv2/ospfv2:processes/ospfv2:process/os'
              + 'pfv2:nsf/ospfv2:last-nsf-restart-use-time'
                ;
  }
  revision 2015-06-24 {
    description '1. Modify range:'+"\n"
              + '/ospfv2:state/ospfv2:ospfv2/ospfv2:interfaces/ospfv2:shamlink-'
              + 'interfaces/ospfv2:shamlink-interface/ospfv2:neighbor-count'+"\n"
              + '2. Delete an enumeration value:'+"\n"
              + '/ospfv2:state/ospfv2:ospfv2/ospfv2:neighbors/ospfv2:shamlink-n'
              + 'eighbors/ospfv2:shamlink-neighbor/ospfv2:neighbor-state'+"\n"
              + '/ospfv2:state/ospfv2:ospfv2/ospfv2:interfaces/ospfv2:normal-in'
              + 'terfaces/ospfv2:normal-interface/ospfv2:network-type'
                ;
  }
  revision 2015-06-17 {
    description '1. Delete an enumeration value:'+"\n"
              + '/ospfv2:state/ospfv2:ospfv2/ospfv2:interfaces/ospfv2:normal-in'
              + 'terfaces/ospfv2:normal-interface/ospfv2:track-state'+"\n"
              + '2. Add default vlaue,unit and description:'+"\n"
              + '/ospfv2:configuration/ospfv2:ospfv2/ospfv2:processes/ospfv2:pr'
              + 'ocess/ospfv2:areas/ospfv2:area/ospfv2:nssa-stub-virtual/ospfv2'
              + ':nssa-stub-virtual/ospfv2:virtuals/ospfv2:virtual/ospfv2:md5s/'
              + 'ospfv2:md5/ospfv2:secret-key/ospfv2:delay-time'+"\n"
              + '3. Add default vlaue: '+"\n"
              + '/ospfv2:configuration/ospfv2:ospfv2/ospfv2:processes/ospfv2:pr'
              + 'ocess/ospfv2:areas/ospfv2:area/ospfv2:intfs/ospfv2:intf/ospfv2'
              + ':md-keys/ospfv2:md-key/ospfv2:secret-key/ospfv2:delay'+"\n"
              + '/ospfv2:configuration/ospfv2:ospfv2/ospfv2:processes/ospfv2:pr'
              + 'ocess/ospfv2:interfaces/ospfv2:interface/ospfv2:md-keys/ospfv2'
              + ':md-key/ospfv2:secret-key/ospfv2:delay'+"\n"
              + '4.Rename and modify description:'+"\n"
              + '/ospfv2:state/ospfv2:ospfv2/ospfv2:interfaces/ospfv2:virtual-i'
              + 'nterfaces/ospfv2:virtual-interface/ospfv2:neighbor-options/osp'
              + 'fv2:np-bit'+"\n"
              + '/ospfv2:state/ospfv2:ospfv2/ospfv2:interfaces/ospfv2:shamlink-'
              + 'interfaces/ospfv2:shamlink-interface/ospfv2:options/ospfv2:np-'
              + 'bit'+"\n"
              + '/ospfv2:state/ospfv2:ospfv2/ospfv2:neighbors/ospfv2:normal-nei'
              + 'ghbors/ospfv2:normal-neighbor/ospfv2:options/ospfv2:np-bit'+"\n"
              + '/ospfv2:state/ospfv2:ospfv2/ospfv2:neighbors/ospfv2:virtual-ne'
              + 'ighbors/ospfv2:virtual-neighbor/ospfv2:options/ospfv2:np-bit'+"\n"
              + '/ospfv2:state/ospfv2:ospfv2/ospfv2:neighbors/ospfv2:shamlink-n'
              + 'eighbors/ospfv2:shamlink-neighbor/ospfv2:options/ospfv2:np-bit'
              + ''+"\n"
              + '/ospfv2:state/ospfv2:ospfv2/ospfv2:interfaces/ospfv2:virtual-i'
              + 'nterfaces/ospfv2:virtual-interface/ospfv2:neighbor-options-fie'
              + 'ld'+"\n"
              + '/ospfv2:state/ospfv2:ospfv2/ospfv2:interfaces/ospfv2:virtual-i'
              + 'nterfaces/ospfv2:virtual-interface/ospfv2:neighbor-options'+"\n"
              + '5.Modify description:'+"\n"
              + '/ospfv2:state/ospfv2:ospfv2/ospfv2:neighbors/ospfv2:shamlink-n'
              + 'eighbors/ospfv2:shamlink-neighbor/ospfv2:options'+"\n"
              + '/ospfv2:state/ospfv2:ospfv2/ospfv2:neighbors/ospfv2:virtual-ne'
              + 'ighbors/ospfv2:virtual-neighbor/ospfv2:options'+"\n"
              + '/ospfv2:state/ospfv2:ospfv2/ospfv2:neighbors/ospfv2:normal-nei'
              + 'ghbors/ospfv2:normal-neighbor/ospfv2:options'+"\n"
              + '/ospfv2:state/ospfv2:ospfv2/ospfv2:interfaces/ospfv2:shamlink-'
              + 'interfaces/ospfv2:shamlink-interface/ospfv2:options'+"\n"
              + '/ospfv2:state/ospfv2:ospfv2/ospfv2:interfaces/ospfv2:shamlink-'
              + 'interfaces/ospfv2:shamlink-interface/ospfv2:options-field'
                ;
  }
  revision 2015-06-08 {
    description '1. Delete an enumeration value:'+"\n"
              + '/ospfv2:state/ospfv2:ospfv2/ospfv2:neighbors/ospfv2:virtual-ne'
              + 'ighbors/ospfv2:virtual-neighbor/ospfv2:neighbor-state'+"\n"
              + '2. Modify range:'+"\n"
              + '/ospfv2:state/ospfv2:ospfv2/ospfv2:neighbors/ospfv2:normal-nei'
              + 'ghbors/ospfv2:normal-neighbor/ospfv2:poll-interval'+"\n"
              + '/ospfv2:state/ospfv2:ospfv2/ospfv2:interfaces/ospfv2:virtual-i'
              + 'nterfaces/ospfv2:virtual-interface/ospfv2:hello-interval'+"\n"
              + '/ospfv2:state/ospfv2:ospfv2/ospfv2:interfaces/ospfv2:virtual-i'
              + 'nterfaces/ospfv2:virtual-interface/ospfv2:dead-interval'+"\n"
              + '/ospfv2:state/ospfv2:ospfv2/ospfv2:interfaces/ospfv2:virtual-i'
              + 'nterfaces/ospfv2:virtual-interface/ospfv2:retransmit-interval'
                ;
  }
  revision 2015-06-01 {
    description 'Add container:'+"\n"
              + '/ospfv2:configuration/ospfv2:ospfv2/ospfv2:processes/ospfv2:pr'
              + 'ocess/ospfv2:areas/ospfv2:area/ospfv2:intfs/ospfv2:intf/ospfv2'
              + ':cost-link-sd'+"\n"
              + 'Add leaf node:'+"\n"
              + '/ospfv2:state/ospfv2:ospfv2/ospfv2:interfaces/ospfv2:normal-in'
              + 'terfaces/ospfv2:normal-interface/ospfv2:sd-status'+"\n"
              + '/ospfv2:state/ospfv2:ospfv2/ospfv2:interfaces/ospfv2:normal-in'
              + 'terfaces/ospfv2:normal-interface/ospfv2:cost-link-sd'
                ;
  }
  revision 2015-05-14 {
    description 'Add container:'+"\n"
              + '/ospfv2:configuration/ospfv2:ospfv2/ospfv2:processes/ospfv2:pr'
              + 'ocess/ospfv2:interfaces/ospfv2:interface/ospfv2:bfd/ospfv2:bfd'
              + '-param'
                ;
  }
  revision 2015-03-26 {
    description 'Add state and operation of OSPFv2.'
                ;
  }
  revision 2015-03-17 {
    description 'Detele default value:'+"\n"
              + '/configuration/ospfv2/processes/process/areas/area/nssa-stub-v'
              + 'irtual/nssa-stub-virtual/nssa-stub-virtual/stub/stub/no-summar'
              + 'y'+"\n"
              + '/configuration/ospfv2/processes/process/areas/area/nssa-stub-v'
              + 'irtual/nssa-stub-virtual/nssa-stub-virtual/nssa/nssa/no-summar'
              + 'y'+"\n"
              + 'Modify default value:'+"\n"
              + '/configuration/ospfv2/processes/process/areas/area/nssa-stub-v'
              + 'irtual/nssa-stub-virtual/nssa-stub-virtual/nssa/nssa/translato'
              + 'r-role'+"\n"
              + 'Add new container:'+"\n"
              + '/configuration/ospfv2/processes/process/bfd'+"\n"
              + 'Obsolete leaf:'+"\n"
              + '/configuration/ospfv2/processes/process/ospf-bfd'+"\n"
              + 'Set leaf to mandatory:'+"\n"
              + '/configuration/ospfv2/processes/process/prefix-priority/prefix'
              + '-prioritys/prefix-priority/prefix-list'
                ;
  }
  revision 2015-03-12 {
    description 'Add default value:'+"\n"
              + '/configuration/ospfv2/processes/process/areas/area/range/nssas'
              + '/nssa/nssa-tag'
                ;
  }
  revision 2015-03-05 {
    description 'Modify length of a leaf node:'+"\n"
              + '/configuration/ospfv2/processes/process/redistribute/redistrib'
              + 'ute-bgps/redistribute-bgp/asno'+"\n"
              + 'Add Patterns of a leaf node:'+"\n"
              + '/configuration/ospfv2/processes/process/redistribute/redistrib'
              + 'ute-bgps/redistribute-bgp/peer-addr'
                ;
  }
  revision 2015-01-04 {
    description '1.modify description:'+"\n"
              + '/configuration/ospfv2/processes/process/thr-timer/lsa/hold-tim'
              + 'e'+"\n"
              + '/configuration/ospfv2/processes/process/thr-timer/lsa/delay-ti'
              + 'me'+"\n"
              + '/configuration/ospfv2/processes/process/thr-timer/lsa/max-dela'
              + 'y-time'+"\n"
              + '2.add container:'+"\n"
              + '/configuration/ospfv2/processes/process/thr-timer/lsa-arrival'
                ;
  }
  revision 2014-11-11 {
    description '1.Add container static-remote-lfa in /ospfv2:configuration/osp'
              + 'fv2:ospfv2/ospfv2:processes/ospfv2:process/ospfv2:areas/ospfv2'
              + ':area/ospfv2:intfs/ospfv2:intf.'
                ;
  }
  revision 2014-10-15 {
    description '1.Add container intfs in /ospfv2:configuration/ospfv2:ospfv2/o'
              + 'spfv2:processes/ospfv2:process/ospfv2:areas/ospfv2:area.'+"\n"
              + '2.Add containers networks,bfd-param and mpls-te in /ospfv2:con'
              + 'figuration/ospfv2:ospfv2/ospfv2:processes/ospfv2:process/ospfv'
              + '2:areas/ospfv2:area.'
                ;
  }
  revision 2014-08-28 {
    description 'Modify Ospf lsa-limit.'+"\n"
              + '/ospfv2:configuration/ospfv2:ospfv2/ospfv2:processes/ospfv2:pr'
              + 'ocess/ospfv2:lsa-limit/ospfv2:lsa-choice/ospfv2:warning/ospfv2'
              + ':warning'+"\n"
              + 'The choice node added.'+"\n"
              + '/ospfv2:configuration/ospfv2:ospfv2/ospfv2:processes/ospfv2:pr'
              + 'ocess/ospfv2:lsa-limit/ospfv2:lsa-choice/ospfv2:limit-config/o'
              + 'spfv2:limit-config'+"\n"
              + 'The chocie node added.'
                ;
  }
  revision 2014-07-31 {
    description 'Add Ospf lsa throttle timers.'+"\n"
              + '/ospfv2:configuration/ospfv2:ospfv2/ospfv2:processes/ospfv2:pr'
              + 'ocess/ospfv2:thr-timer/ospfv2:lsa'+"\n"
              + 'The container node added.'+"\n"
              + '/ospfv2:configuration/ospfv2:ospfv2/ospfv2:processes/ospfv2:pr'
              + 'ocess/ospfv2:thr-timer/ospfv2:lsa/ospfv2:hold-time'+"\n"
              + 'The leaf node added.'+"\n"
              + '/ospfv2:configuration/ospfv2:ospfv2/ospfv2:processes/ospfv2:pr'
              + 'ocess/ospfv2:thr-timer/ospfv2:lsa/ospfv2:delay-time'+"\n"
              + 'The leaf node added.'+"\n"
              + '/ospfv2:configuration/ospfv2:ospfv2/ospfv2:processes/ospfv2:pr'
              + 'ocess/ospfv2:thr-timer/ospfv2:lsa/ospfv2:max-delay-time'+"\n"
              + 'The leaf node added.'
                ;
  }
  revision 2013-12-19 {
    description 'Initial version.'
                ;
  }
  feature ti-lfa {
    description 'The feature is for TI-LFA.'
                ;
  }
  feature segment-routing {
    description 'SR support labels'
                ;
  }
  feature distance-policy {
    description 'The feature is for distance-policy.'
                ;
  }
  container configuration {
    description 'Configure OSPFV2 parameters.'
                ;
    container ospfv2 {
      description 'Configure OSPFV2 parameters.'
                  ;
      container processes {
        description 'Ospf Instance'
                    ;
        list process {
          description 'Ospf Instance'
                      ;
          key pro-id ;
          leaf pro-id {
            description 'Ospf process ID'
                        ;
            type uint32 {
              range 1..65535 {
                description 'Ospf process ID from 1 to 65535'
                            ;
              }
            }
          }
          leaf vrf-name {
            description 'Vrf name'
                        ;
            type string {
              length 1..32 {
                description 'Characters from 1 to 32'
                            ;
              }
            }
          }
          leaf lsa-pacing {
            description 'Ospf LSA group pacing timers,Secs between group of LSA'
                      + ' being refreshed'
                        ;
            type uint32 {
              range 1..1800 {
                description 'Secs between group of LSA being refreshed'
                            ;
              }
            }
            units second ;
            default 1 ;
          }
          leaf timer-frr {
            description 'Ospf ipfrr spf timers, hold time in secs between conse'
                      + 'cutive spf'
                        ;
            type uint32 {
              range 1..65535 {
                description 'Ospf ipfrr spf timers, hold time in secs between c'
                          + 'onsecutive spf'
                            ;
              }
            }
            units second ;
            default 1 ;
          }
          leaf maximum-paths {
            description 'Maximum number of parallel routes OSPF can support'
                        ;
            type uint32 {
              range 1..32 {
                description 'Maximum number of parallel routes OSPF can support'
                            ;
              }
            }
            default 1 ;
          }
          leaf default-metric {
            description 'Ospf default metric'
                        ;
            type uint32 {
              range 1..16777214 {
                description 'Ospf default metric form 1 to 16777214'
                            ;
              }
            }
            default 20 ;
          }
          leaf auto-cost {
            description 'Calculate OSPF interface cost according to bandwidth, '
                      + 'the reference bandwidth in terms of Mbps'
                        ;
            type uint32 {
              range 1..4000000 {
                description 'The reference bandwidth in terms of Mbps'
                            ;
              }
            }
            units Mbps ;
            default 100 ;
          }
          leaf debug-flag {
            description 'Ospf debug information'
                        ;
            type enumeration {
              enum disable {
                value 1 ;
                description disable ;
              }
              enum enable {
                value 2 ;
                description enable ;
              }
            }
            default enable ;
          }
          leaf cap-opaque {
            description 'Ospf Opaque LSA function'
                        ;
            type enumeration {
              enum disable {
                value 1 ;
                description disable ;
              }
              enum enable {
                value 2 ;
                description enable ;
              }
            }
            default enable ;
          }
          leaf cap-vrflite {
            description 'Ignore ospf vrf loop-prevention'
                        ;
            type enumeration {
              enum enable {
                value 1 ;
                description enable ;
              }
              enum disable {
                value 2 ;
                description disable ;
              }
            }
            default disable ;
          }
          leaf rfc1583-value {
            description 'Ospf compatible with rfc1583 when calculating external'
                      + ' route'
                        ;
            type enumeration {
              enum disable {
                value 1 ;
                description disable ;
              }
              enum enable {
                value 2 ;
                description enable ;
              }
            }
            default enable ;
          }
          leaf nsf {
            description 'Non-stop forwarding'
                        ;
            type enumeration {
              enum enable {
                value 1 ;
                description enable ;
              }
              enum disable {
                value 2 ;
                description disable ;
              }
            }
            default disable ;
          }
          leaf local-mt {
            description 'Enable local-mt'
                        ;
            type enumeration {
              enum enable {
                value 1 ;
                description enable ;
              }
              enum disable {
                value 2 ;
                description disable ;
              }
            }
            default disable ;
          }
          leaf ttl-security {
            description 'Configure all interfaces ttl-security hops'
                        ;
            type int32 {
              range 1..254 {
                description 'Ttl-security hops'
                            ;
              }
            }
            units hop ;
          }
          leaf ldp-igp-sync {
            description 'Config MPLS LDP IGP sync'
                        ;
            type empty ;
          }
          leaf ldp-autoconfig {
            description 'Config MPLS LDP IGP autoconfig'
                        ;
            type empty ;
          }
          leaf timer-spf {
            description 'Ospf SPF timers,Seconds'
                        ;
            type uint32 {
              range 1..65535 ;
            }
            units second ;
            default 1 ;
          }
          leaf grace-period {
            description 'Set a grace-period for graceful-restart,Seconds'
                        ;
            type uint32 {
              range 1..1800 ;
            }
            units second ;
            default 120 ;
          }
          leaf vpn-id {
            description 'Vpn ID of vrf'
                        ;
            type uint32 ;
          }
          leaf ospf-bfd {
            status obsolete {
              ncd:revise-date 2015-07-08 ;
            }
            description 'Enable ospf bfd enable'
                        ;
            type empty ;
          }
          leaf te-link-delay {
            description 'Set TE link delay enable'
                        ;
            type enumeration {
              enum enable {
                value 1 ;
                description enable ;
              }
              enum disable {
                value 2 ;
                description disable ;
              }
            }
            default disable ;
            ncd:revise-date 2020-02-04 ;
          }
          container frr-policy {
            description 'Configure OSPF backup route policy.'
                        ;
            presence frr-policy ;
            choice policy-type {
              description 'Configure OSPF backup route policy type.'
                          ;
              mandatory true ;
              case route-policy {
                description 'Configure OSPF backup route-policy.'
                            ;
                leaf route-policy-name {
                  description 'Configure route-policy name.'
                              ;
                  type string {
                    length 1..200 {
                      description 'Name of the route-policy,characters from 1 t'
                                + 'o 200.'
                                  ;
                    }
                  }
                  mandatory true ;
                }
              }
            }
            ncd:revise-date 2017-07-05 ;
          }
          container bfd {
            description 'Enable ospf BFD.'
                        ;
            presence ospf-bfd ;
            leaf bfd {
              description 'Enable ospf BFD.'
                          ;
              type empty ;
              mandatory true ;
            }
            container bfd-parameter {
              description 'BFD parameters.'
                          ;
              presence bfd-parameter ;
              leaf interval {
                description 'Minimum send interval.'
                            ;
                type uint32 {
                  range 10..990 ;
                }
                units millisecond ;
                mandatory true ;
              }
              leaf min-rx {
                description 'Minimum receive interval'
                            ;
                type uint32 {
                  range 10..990 ;
                }
                units millisecond ;
                mandatory true ;
              }
              leaf multiplier {
                description Multiplier. ;
                type uint32 {
                  range 3..50 ;
                }
                mandatory true ;
              }
            }
          }
          container bfd-template {
            description 'Configure BFD template for OSPF'
                        ;
            presence bfd-template ;
            leaf template {
              description 'Configure BFD template for OSPF'
                          ;
              type string {
                length 1..31 ;
              }
              mandatory true ;
            }
            ncd:revise-date 2020-06-01 ;
          }
          container areas {
            description Area ;
            list area {
              description Area ;
              key area-ip ;
              leaf area-ip {
                description 'Area ip'
                            ;
                type ncd:ipv4-address ;
              }
              container networks {
                description 'Ospf network'
                            ;
                list network {
                  description 'Ospf network'
                              ;
                  key 'net-num wild-mask'
                      ;
                  leaf net-num {
                    description 'IP address'
                                ;
                    type ncd:ipv4-address ;
                  }
                  leaf wild-mask {
                    description 'IP MASK'
                                ;
                    type ncd:ipv4-imask ;
                  }
                }
              }
              container ldp-igp-sync {
                description 'Routing protocol commands for LDP'
                            ;
                leaf sync-flag {
                  description 'The flag of MPLS LDP IGP sync'
                              ;
                  type enumeration {
                    enum no-config {
                      value 0 ;
                      description no-config ;
                    }
                    enum enable {
                      value 1 ;
                      description enable ;
                    }
                    enum disable {
                      value 2 ;
                      description disable ;
                    }
                  }
                  default no-config ;
                }
                leaf auto-flag {
                  description 'The flag of MPLS LDP auto-config'
                              ;
                  type enumeration {
                    enum no-config {
                      value 0 ;
                      description no-config ;
                    }
                    enum enable {
                      value 1 ;
                      description enable ;
                    }
                    enum disable {
                      value 2 ;
                      description disable ;
                    }
                  }
                  default no-config ;
                }
              }
              container range {
                description 'Summarize routes matching address/mask'
                            ;
                container summarys {
                  description 'Summarize routes matching address/mask'
                              ;
                  list summary {
                    description 'Summarize routes matching address/mask'
                                ;
                    key 'ip-addr netmask summary-link'
                        ;
                    leaf ip-addr {
                      description 'IP address to match'
                                  ;
                      type ncd:ipv4-address ;
                    }
                    leaf netmask {
                      description 'Subnet mask to match'
                                  ;
                      type ncd:ipv4-mask ;
                    }
                    leaf summary-link {
                      description 'Range of Type-3'
                                  ;
                      type uint8 {
                        range 1 {
                          description 'Range of Type-3'
                                      ;
                        }
                      }
                    }
                    leaf adv-flag {
                      description 'Advertise flag'
                                  ;
                      type enumeration {
                        enum advertise {
                          value 1 ;
                          description advertise ;
                        }
                        enum not-advertise {
                          value 2 ;
                          description not-advertise ;
                        }
                      }
                      default advertise ;
                    }
                    leaf cost-value {
                      description 'Advertised metric for this range'
                                  ;
                      type uint32 {
                        range 1..16777214 {
                          description 'Advertised metric for this range'
                                      ;
                        }
                      }
                    }
                  }
                }
                container nssas {
                  description 'Summarize routes matching address/mask'
                              ;
                  list nssa {
                    description 'Summarize routes matching address/mask'
                                ;
                    key 'ip-addr netmask nssa-external-link'
                        ;
                    leaf ip-addr {
                      description 'IP address to match'
                                  ;
                      type ncd:ipv4-address ;
                    }
                    leaf netmask {
                      description 'Subnet mask to match'
                                  ;
                      type ncd:ipv4-mask ;
                    }
                    leaf nssa-external-link {
                      description 'Range of Type-7'
                                  ;
                      type uint8 {
                        range 2 ;
                      }
                    }
                    leaf adv-flag {
                      description 'Advertise flag'
                                  ;
                      type enumeration {
                        enum advertise {
                          value 1 ;
                        }
                        enum not-advertise {
                          value 2 ;
                        }
                      }
                      default advertise ;
                    }
                    leaf cost-value {
                      description 'Advertised metric for this range'
                                  ;
                      type uint32 {
                        range 1..16777214 {
                          description 'Advertised metric for this range'
                                      ;
                        }
                      }
                    }
                    leaf nssa-tag {
                      description 'Tag(32-bit) value'
                                  ;
                      type uint32;
                      //type uint32 {
                      //  range 0..4294967295 {
                      //    description 'Tag(32-bit) value'
                      //                ;
                      //  }
                      //}
                      default 0 ;
                    }
                  }
                }
              }
              container authtype {
                description 'Authentication type'
                            ;
                presence authtype ;
                container simple-authen {
                  description 'Simple authentication'
                              ;
                  presence simple-authen ;
                  leaf simple-authen {
                    description 'Simple authentication'
                                ;
                    type enumeration {
                      enum config {
                        value 1 ;
                      }
                      enum no-config {
                        value 2 ;
                      }
                    }
                    mandatory true ;
                  }
                }
                container md5 {
                  description 'Md5 authentication'
                              ;
                  presence md5 ;
                  leaf md5 {
                    description 'Md5 authentication'
                                ;
                    type enumeration {
                      enum config {
                        value 1 ;
                      }
                      enum no-config {
                        value 2 ;
                      }
                    }
                    mandatory true ;
                  }
                }
                container authen-keychain {
                  description 'Keychain authentication.'
                              ;
                  presence authen-keychain ;
                  leaf keychain {
                    description 'Keychain authentication.'
                                ;
                    type string {
                      length 1..31 {
                        description 'Name of keychain,characters from 1 to 31'
                                    ;
                      }
                    }
                    mandatory true ;
                  }
                  ncd:revise-date 2016-01-18 ;
                }
              }
              container filters {
                description 'Filter networks between ospf areas'
                            ;
                list filter {
                  description 'Filter networks between ospf areas'
                              ;
                  key direction ;
                  leaf direction {
                    description Direction ;
                    type enumeration {
                      enum in {
                        value 1 ;
                        description in ;
                      }
                      enum out {
                        value 2 ;
                        description out ;
                      }
                    }
                  }
                  leaf prefix-name {
                    description 'Name of an IP prefix-list,characters from 1 to'
                              + ' 169'
                                ;
                    type string {
                      length 1..169 {
                        description 'Name of an IP prefix-list,characters from '
                                  + '1 to 169'
                                    ;
                      }
                    }
                    mandatory true ;
                  }
                }
              }
              container stubhosts {
                description 'Configure ospf host route information'
                            ;
                list stubhost {
                  description 'Configure ospf host route information'
                              ;
                  key ip-addr ;
                  leaf ip-addr {
                    description 'IP address to match'
                                ;
                    type ncd:ipv4-address ;
                  }
                  leaf cost {
                    description 'The cost to the host route'
                                ;
                    type uint32 {
                      range 1..65535 {
                        description 'The cost to the host route'
                                    ;
                      }
                    }
                    mandatory true ;
                  }
                }
              }
              container shamlinks {
                description 'Define a sham link of the area'
                            ;
                list shamlink {
                  description 'Define a sham link of the area'
                              ;
                  key 'src-ipaddr dest-ipaddr'
                      ;
                  leaf src-ipaddr {
                    description 'IP addr associated with sham-link source'
                                ;
                    type ncd:ipv4-address ;
                  }
                  leaf dest-ipaddr {
                    description 'IP addr associated with sham-link destination'
                                ;
                    type ncd:ipv4-address ;
                  }
                  leaf cost {
                    description 'Cost of the sham-link'
                                ;
                    type uint32 {
                      range 1..65535 {
                        description 'Cost of the sham-link,form 1 to 65535'
                                    ;
                      }
                    }
                    default 1 ;
                  }
                }
              }
              container nssa-stub-virtual {
                description 'Nssa,stub and virtual'
                            ;
                container nssa-stub-virtual {
                  description 'Nssa,stub and virtual'
                              ;
                  choice nssa-stub-virtual {
                    description 'Nssa,stub and virtual'
                                ;
                    case nssa {
                      description 'Specify a NSSA area'
                                  ;
                      container nssa {
                        description 'Specify a NSSA area'
                                    ;
                        leaf default-im-on {
                          description 'Generate default Type-7 LSA for this area'
                                      ;
                          type enumeration {
                            enum config {
                              value 1 ;
                            }
                            enum no-config {
                              value 2 ;
                            }
                          }
                          default no-config ;
                        }
                        leaf metric {
                          description 'Ospf metric'
                                      ;
                          type uint32 {
                            range 1..16777214 {
                              description 'Ospf metric,form 1 to 16777214'
                                          ;
                            }
                          }
                          default 1 ;
                        }
                        leaf metric-type {
                          description 'The metric type'
                                      ;
                          type enumeration {
                            enum ext-2 {
                              value 0 ;
                              description ext-2 ;
                            }
                            enum ext-1 {
                              value 1 ;
                              description ext-1 ;
                            }
                          }
                          default ext-2 ;
                        }
                        leaf translator-role {
                          description 'Ospf translator role'
                                      ;
                          type enumeration {
                            enum candidate {
                              value 0 ;
                              description candidate ;
                            }
                            enum always {
                              value 1 ;
                              description always ;
                            }
                          }
                          default candidate ;
                        }
                        leaf trans-stab-intv {
                          description 'Secs,interval time'
                                      ;
                          type uint32 {
                            range 0..65535 {
                              description 'Secs,interval time'
                                          ;
                            }
                          }
                          default 40 ;
                        }
                        leaf no-summary {
                          description 'Do not send summary LSA into area'
                                      ;
                          type enumeration {
                            enum config {
                              value 1 ;
                              description config ;
                            }
                            enum no-config {
                              value 2 ;
                              description no-config ;
                            }
                          }
                        }
                        leaf no-redistribution {
                          description 'Do not redistribute external LSA into NS'
                                    + 'SA area'
                                      ;
                          type enumeration {
                            enum config {
                              value 1 ;
                              description config ;
                            }
                            enum no-config {
                              value 2 ;
                              description no-config ;
                            }
                          }
                          default no-config ;
                        }
                        leaf transt7-supp-fa {
                          description 'Suppress FA when translating Type-7 to T'
                                    + 'ype-5'
                                      ;
                          type enumeration {
                            enum config {
                              value 1 ;
                              description config ;
                            }
                            enum no-config {
                              value 2 ;
                              description no-config ;
                            }
                          }
                          default no-config ;
                        }
                      }
                    }
                    case stub {
                      description 'Specify a stub area'
                                  ;
                      container stub {
                        description 'Specify a stub area'
                                    ;
                        leaf no-summary {
                          description 'Do not send summary LSA into stub area'
                                      ;
                          type enumeration {
                            enum config {
                              value 1 ;
                              description config ;
                            }
                            enum no-config {
                              value 2 ;
                              description no-config ;
                            }
                          }
                        }
                        leaf default-cost {
                          description 'Cost value of stub area'
                                      ;
                          type uint32 {
                            range 1..65535 {
                              description 'Cost value of stub area'
                                          ;
                            }
                          }
                          default 1 ;
                        }
                        leaf default-origin {
                          description 'Origin default route.'
                                      ;
                          type empty ;
                          ncd:revise-date 2016-07-01 ;
                        }
                      }
                    }
                    case virtual {
                      description 'Define a virtual link'
                                  ;
                      container virtuals {
                        description 'Define a virtual link'
                                    ;
                        list virtual {
                          description 'Define a virtual link'
                                      ;
                          key neighbor-id ;
                          leaf neighbor-id {
                            description 'ID associated with virtual link neighbor'
                                        ;
                            type ncd:ipv4-address ;
                          }
                          leaf hellointerval {
                            description 'Hello interval,Seconds'
                                        ;
                            type uint32 {
                              range 1..8192 {
                                description 'Hello interval,Seconds'
                                            ;
                              }
                            }
                            units second ;
                            default 10 ;
                          }
                          leaf retrainterval {
                            description 'Retransmit interval,Seconds'
                                        ;
                            type uint32 {
                              range 1..8192 {
                                description 'Retransmit interval,Seconds'
                                            ;
                              }
                            }
                            units second ;
                            default 5 ;
                          }
                          leaf transmitdelay {
                            description 'Transmit delay,Seconds'
                                        ;
                            type uint32 {
                              range 1..8192 {
                                description 'Transmit delay,Seconds'
                                            ;
                              }
                            }
                            units second ;
                            default 1 ;
                          }
                          leaf deadinterval {
                            description 'Dead interval,Seconds'
                                        ;
                            type uint32 {
                              range 1..8192 {
                                description 'Dead interval,Seconds'
                                            ;
                              }
                            }
                            units second ;
                          }
                          leaf deaddelay {
                            description 'Dead delay,Seconds'
                                        ;
                            type uint32 {
                              range 1..8192 {
                                description 'Dead delay,Seconds'
                                            ;
                              }
                            }
                            units second ;
                          }
                          choice auth-password-type {
                            case unencrypted {
                              leaf authenkey {
                                description 'virtual authentication key'
                                            ;
                                type string {
                                  length 1..8 ;
                                }
                                mandatory true ;
                              }
                            }
                            case encrypted {
                              leaf encry-authenkey {
                                description 'virtual encrypted authentication key'
                                            ;
                                type string {
                                  length 1..128 ;
                                }
                                mandatory true ;
                              }
                              ncd:revise-date 2019-12-16 ;
                            }
                          }
                          container md5s {
                            list md5 {
                              key key-id ;
                              leaf key-id {
                                type uint32 {
                                  range 1..255 ;
                                }
                              }
                              container secret-key {
                                description 'Password to be configured'
                                            ;
                                presence secret-key ;
                                choice md5-password-type {
                                  case unencrypted {
                                    leaf secret-key {
                                      description 'Password to be configured'
                                                  ;
                                      type string {
                                        length 1..16 ;
                                      }
                                      mandatory true ;
                                    }
                                  }
                                  case encrypted {
                                    leaf encry-secret-key {
                                      description 'Encrypted password to be configured'
                                                  ;
                                      type string {
                                        length 1..128 ;
                                      }
                                      mandatory true ;
                                    }
                                    ncd:revise-date 2019-12-16 ;
                                  }
                                }
                                leaf delay-time {
                                  description 'A period of time in minutes'
                                              ;
                                  type uint32 {
                                    range 0..100000 ;
                                  }
                                  units minute ;
                                  default 0 ;
                                }
                              }
                            }
                          }
                          container authtype {
                            description 'The authentication type of virtual link'
                                        ;
                            container authtype {
                              description 'The authentication type of virtual link'
                                          ;
                              choice authtype {
                                description 'The authentication type of virtual link'
                                            ;
                                case null {
                                  description 'No authentication'
                                              ;
                                  container null {
                                    description 'No authentication'
                                                ;
                                    presence null ;
                                    leaf null {
                                      description 'No authentication'
                                                  ;
                                      type empty ;
                                      mandatory true ;
                                    }
                                  }
                                }
                                case md5 {
                                  description 'Md5 authentication'
                                              ;
                                  container md5 {
                                    description 'Md5 authentication'
                                                ;
                                    presence md5 ;
                                    leaf md5 {
                                      description 'Md5 authentication'
                                                  ;
                                      type empty ;
                                      mandatory true ;
                                    }
                                  }
                                }
                                case simple {
                                  description 'Simple authentication'
                                              ;
                                  container simple {
                                    description 'Simple authentication'
                                                ;
                                    presence simple ;
                                    leaf simple {
                                      description 'Simple authentication'
                                                  ;
                                      type empty ;
                                      mandatory true ;
                                    }
                                  }
                                }
                              }
                            }
                            container authen-keychain {
                              description 'Config authentication keychain on virtual link.'
                                          ;
                              presence authen-keychain ;
                              leaf keychain {
                                description 'Config authentication keychain on virtual link.'
                                            ;
                                type string {
                                  length 1..31 {
                                    description 'Name of keychain,characters from 1 to 31'
                                                ;
                                  }
                                }
                                mandatory true ;
                              }
                              ncd:revise-date 2016-01-18 ;
                            }
                          }
                        }
                      }
                    }
                  }
                }
              }
              container bfd {
                description 'Configure all interfaces BFD capability'
                            ;
                presence bfd ;
                leaf enable {
                  description 'Set bfd enable'
                              ;
                  type empty ;
                  mandatory true ;
                }
              }
              container bfd-param {
                description 'Configure all interfaces BFD capability'
                            ;
                presence bfd-param ;
                leaf interval {
                  description Interval ;
                  type uint32 {
                    range 10..990 ;
                  }
                  units millisecond ;
                  mandatory true ;
                }
                leaf min-rx {
                  description Min-rx ;
                  type uint32 {
                    range 10..990 ;
                  }
                  units millisecond ;
                  mandatory true ;
                }
                leaf multiplier {
                  description Multiplier ;
                  type uint32 {
                    range 3..50 ;
                  }
                  mandatory true ;
                }
              }
              container bfd-template {
                description 'Configure BFD template for area'
                            ;
                presence bfd-template ;
                leaf template {
                  description 'Configure BFD template for area'
                              ;
                  type string {
                    length 1..31 ;
                  }
                  mandatory true ;
                }
                ncd:revise-date 2020-06-01 ;
              }
              container intfs {
                description 'An interface to configure'
                            ;
                list intf {
                  description 'An interface to configure'
                              ;
                  key intf-name ;
                  leaf intf-name {
                    description 'Interface name'
                                ;
                    type ncd:ifname {
                      length 1..31 {
                        description 'Interface name'
                                    ;
                      }
                    }
                  }
                  leaf authentication-key {
                    description 'Authentication password (key)'
                                ;
                    type string {
                      length 1..8 {
                        description 'Authentication password (key)'
                                    ;
                      }
                    }
                  }
                  leaf cost {
                    description 'Interface cost'
                                ;
                    type uint32 {
                      range 1..65535 {
                        description 'Interface cost'
                                    ;
                      }
                    }
                  }
                  leaf dead-interval {
                    description 'Interval after which a neighbor is declared de'
                              + 'ad,Seconds'
                                ;
                    type uint32 {
                      range 1..65535 {
                        description 'Interval after which a neighbor is declare'
                                  + 'd dead,Seconds'
                                    ;
                      }
                    }
                    units second ;
                  }
                  leaf hello-interval {
                    description 'Time between hello packets,Seconds'
                                ;
                    type uint32 {
                      range 1..65535 {
                        description 'Time between hello packets,Seconds'
                                    ;
                      }
                    }
                    units second ;
                  }
                  leaf mtu-ignore {
                    description 'Ignore the mtu mismatch when exchanging DD pac'
                              + 'ket'
                                ;
                    type enumeration {
                      enum config {
                        value 1 ;
                        description config ;
                      }
                      enum no-config {
                        value 2 ;
                        description no-config ;
                      }
                    }
                    default no-config ;
                  }
                  leaf priority {
                    description 'Router priority'
                                ;
                    type uint32 {
                      range 0..255 {
                        description 'Router priority'
                                    ;
                      }
                    }
                    default 1 ;
                  }
                  leaf resync-timeout {
                    description 'Interval after which adjacency is reset if oob'
                              + '-resync is not started,Seconds'
                                ;
                    type uint32 {
                      range 1..3600 {
                        description 'Interval after which adjacency is reset if'
                                  + ' oob-resync is not started,Seconds'
                                    ;
                      }
                    }
                    units second ;
                  }
                  leaf retransmit-interval {
                    description 'Time between retransmitting lost link state ad'
                              + 'vertisements,Seconds'
                                ;
                    type uint32 {
                      range 1..65535 {
                        description 'Time between retransmitting lost link stat'
                                  + 'e advertisements,Seconds'
                                    ;
                      }
                    }
                    units second ;
                    default 5 ;
                  }
                  leaf transmit-delay {
                    description 'Link state transmit delay,Seconds'
                                ;
                    type uint32 {
                      range 1..65535 {
                        description 'Link state transmit delay,Seconds'
                                    ;
                      }
                    }
                    units second ;
                    default 1 ;
                  }
                  leaf ttl-security {
                    description 'Configure OSPF ttl-security hops'
                                ;
                    type int32 {
                      range 1..254 {
                        description 'Configure OSPF ttl-security hops'
                                    ;
                      }
                    }
                    units hop ;
                  }
                  leaf authenkey-p {
                    description 'Password to be configured'
                                ;
                    type string {
                      length 1..128 {
                        description 'Password to be configured'
                                    ;
                      }
                    }
                  }
                  leaf ldp-igp-sync {
                    description 'Config MPLS LDP IGP sync'
                                ;
                    type enumeration {
                      enum no-config {
                        value 0 ;
                      }
                      enum enable {
                        value 1 ;
                      }
                      enum disable {
                        value 2 ;
                      }
                    }
                    default no-config ;
                  }
                  leaf ldp-autoconfig {
                    description 'Config MPLS LDP IGP autoconfig'
                                ;
                    type enumeration {
                      enum no-config {
                        value 0 ;
                      }
                      enum enable {
                        value 1 ;
                      }
                      enum disable {
                        value 2 ;
                      }
                    }
                    default no-config ;
                  }
                  container link-damping {
                    description 'Configure interface cost and time when link is'
                              + ' in damping status'
                                ;
                    presence link-damping ;
                    container cost {
                      description 'Configure interface cost when link is in dam'
                                + 'ping status'
                                  ;
                      choice cost-adjust-type {
                        description 'Configure interface cost adjust type'
                                    ;
                        mandatory true ;
                        case maximum {
                          description 'Set maximum cost when link is in damping'
                                    + ' status'
                                      ;
                          leaf maximum {
                            description 'Set maximum cost when link is in damping status'
                                        ;
                            type empty ;
                            mandatory true ;
                          }
                        }
                        case increase-value {
                          description 'Set increase cost when link is in dampin'
                                    + 'g status'
                                      ;
                          leaf increase-value {
                            description 'Set increase cost when link is in damping status'
                                        ;
                            type uint16 {
                              range 100..10000 {
                                description 'Set increase cost range when link is in damping status'
                                            ;
                              }
                            }
                            mandatory true ;
                          }
                        }
                      }
                    }
                    leaf damping-time {
                      description 'Configure interface damping time'
                                  ;
                      type uint32 {
                        range 1..3600000 ;
                      }
                      units millisecond ;
                      mandatory true ;
                    }
                    ncd:revise-date 2017-04-05 ;
                  }
                  container fast-reroute {
                    description 'Fast reroute'
                                ;
                    presence fast-reroute ;
                    leaf disable {
                      description Disable ;
                      type empty ;
                      mandatory true ;
                    }
                  }
                  container md-keys {
                    description 'Message digest authentication key'
                                ;
                    list md-key {
                      description 'Message digest authentication key'
                                  ;
                      key key-id ;
                      leaf key-id {
                        description 'Key ID'
                                    ;
                        type uint32 {
                          range 1..255 {
                            description 'Key ID,from 1 to 255'
                                        ;
                          }
                        }
                      }
                      container secret-key {
                        description 'Password to be configured'
                                    ;
                        choice md5-password-type {
                          case unencrypted {
                            leaf secret-key {
                              description 'Password to be configured'
                                          ;
                              type string {
                                length 1..16 {
                                  description 'Password to be configured,characters from 1 to 16'
                                              ;
                                }
                              }
                              mandatory true ;
                            }
                          }
                          case encrypted {
                            leaf encry-secret-key {
                              description 'Encrypted password to be configured'
                                          ;
                              type string {
                                length 1..128 {
                                  description 'Password to be configured'
                                              ;
                                }
                              }
                              mandatory true ;
                            }
                            ncd:revise-date 2019-12-16 ;
                          }
                        }
                        leaf delay {
                          description 'A period of time in minutes'
                                      ;
                          type uint32 {
                            range 0..100000 {
                              description 'A period of time in minutes'
                                          ;
                            }
                          }
                          units minute ;
                          default 0 ;
                        }
                      }
                    }
                  }
                  container auth-type {
                    description 'Enable authentication on the interface'
                                ;
                    presence auth-type ;
                    leaf type {
                      description 'Enable authentication on the interface'
                                  ;
                      type enumeration {
                        enum null {
                          value 1 ;
                          description null ;
                        }
                        enum simple {
                          value 2 ;
                          description simple ;
                        }
                        enum md5 {
                          value 3 ;
                          description md5 ;
                        }
                      }
                      mandatory true ;
                    }
                  }
                  container authen-keychain {
                    presence authen-keychain ;
                    leaf keychain {
                      description 'Config authentication keychain on the interf'
                                + 'ace.'
                                  ;
                      type string {
                        length 1..31 {
                          description 'Name of keychain,characters from 1 to 31'
                                      ;
                        }
                      }
                      mandatory true ;
                    }
                    ncd:revise-date 2016-01-18 ;
                  }
                  container bfd {
                    description 'Configure BFD for interface'
                                ;
                    presence bfd ;
                    leaf status {
                      description 'Bfd status'
                                  ;
                      type enumeration {
                        enum enable {
                          value 0 ;
                          description enable ;
                        }
                        enum disable {
                          value 1 ;
                          description disable ;
                        }
                      }
                      mandatory true ;
                    }
                  }
                  container bfd-param {
                    description 'Configure BFD for interface'
                                ;
                    presence bfd-param ;
                    leaf interval {
                      description Interval ;
                      type uint32 {
                        range 10..990 ;
                      }
                      units millisecond ;
                      mandatory true ;
                    }
                    leaf min-rx {
                      description Min-rx ;
                      type uint32 {
                        range 10..990 ;
                      }
                      units millisecond ;
                      mandatory true ;
                    }
                    leaf multiplier {
                      description Multiplier ;
                      type uint32 {
                        range 3..50 ;
                      }
                      mandatory true ;
                    }
                  }
                  container bfd-template {
                    description 'Configure BFD template for interface'
                                ;
                    presence bfd-template ;
                    leaf template {
                      description 'Configure BFD template for interface'
                                  ;
                      type string {
                        length 1..31 ;
                      }
                      mandatory true ;
                    }
                    ncd:revise-date 2020-06-01 ;
                  }
                  container network-type {
                    description 'Interface Network type'
                                ;
                    container network-type {
                      choice network-type {
                        description 'Interface Network type'
                                    ;
                        case broadcast {
                          description BROADCAST ;
                          container broadcast {
                            description BROADCAST ;
                            presence broadcast ;
                            leaf broadcast {
                              description BROADCAST ;
                              type enumeration {
                                enum broadcast {
                                  value 1 ;
                                }
                              }
                              mandatory true ;
                            }
                          }
                        }
                        case nbma {
                          description NONBROADCAST ;
                          container nbma {
                            description NONBROADCAST ;
                            presence nbma ;
                            leaf nbma {
                              description NONBROADCAST ;
                              type enumeration {
                                enum nbma {
                                  value 2 ;
                                }
                              }
                              mandatory true ;
                            }
                          }
                        }
                        case point-to-point {
                          description POINT_TO_POINT ;
                          container point-to-point {
                            description POINT_TO_POINT ;
                            presence point-to-point ;
                            leaf point-to-point {
                              description POINT_TO_POINT ;
                              type enumeration {
                                enum point-to-point {
                                  value 3 ;
                                }
                              }
                              mandatory true ;
                            }
                            leaf ignore-subnet-check {
                              description 'IGNORE THE SUBNET CHECK WHEN THE NETWORK IS POINT-TO-POINT'
                                          ;
                              type empty ;
                              ncd:revise-date 2020-12-08 ;
                            }
                          }
                        }
                        case point-to-multipoint {
                          description POINT_TO_MULPOINT ;
                          container point-to-multipoint {
                            description POINT_TO_MULPOINT ;
                            presence point-to-multipoint ;
                            leaf point-to-multipoint {
                              description POINT_TO_MULPOINT ;
                              type enumeration {
                                enum point-to-multipoint {
                                  value 5 ;
                                }
                              }
                              mandatory true ;
                            }
                          }
                        }
                        case ptmp-nb {
                          description POINT_TO_MULPOINT_NB ;
                          container ptmp-nb {
                            description POINT_TO_MULPOINT_NB ;
                            presence ptmp-nb ;
                            leaf ptmp-nb {
                              description POINT_TO_MULPOINT_NB ;
                              type enumeration {
                                enum ptmp-nb {
                                  value 1 ;
                                }
                              }
                              mandatory true ;
                            }
                          }
                        }
                      }
                    }
                  }
                  container static-remote-lfa {
                    description 'Configure static remote lfa for interface'
                                ;
                    container next-hop {
                      description 'Configure the next hop of static remote lfa '
                                + 'for interface'
                                  ;
                      presence next-hop ;
                      leaf next-hop {
                        description 'Configure the next hop of static remote lf'
                                  + 'a for interface'
                                    ;
                        type ncd:ipv4-address ;
                        mandatory true ;
                      }
                      container specify-nexthop {
                        description 'Specify backup interface and gateway'
                                    ;
                        presence specify-nexthop ;
                        leaf backup-intf {
                          description 'Configure the backup interface of static'
                                    + ' remote lfa for interface'
                                      ;
                          type ncd:ifname {
                            length 1..31 {
                              description 'Interface name'
                                          ;
                            }
                          }
                          mandatory true ;
                        }
                        leaf gateway {
                          description 'Configure the gateway of static remote l'
                                    + 'fa for interface'
                                      ;
                          type ncd:ipv4-address-none-zero ;
                          mandatory true ;
                        }
                        ncd:revise-date 2016-08-10 ;
                      }
                    }
                    container next-hop-prefixs {
                      description 'Configure the next hop and prefix-list name '
                                + 'of static remote lfa for interface'
                                  ;
                      list next-hop-prefix {
                        description 'Configure the next hop and prefix-list nam'
                                  + 'e of static remote lfa for interface'
                                    ;
                        key prefix-list ;
                        leaf prefix-list {
                          description 'Name of the prefix-list,characters from '
                                    + '1 to 169'
                                      ;
                          type string {
                            length 1..169 {
                              description 'Name of the prefix-list,characters from 1 to 169'
                                          ;
                            }
                          }
                        }
                        leaf next-hop {
                          description 'Configure the next hop of static remote '
                                    + 'lfa for interface'
                                      ;
                          type ncd:ipv4-address ;
                          mandatory true ;
                        }
                        container specify-nexthop {
                          description 'Specify backup interface and gateway'
                                      ;
                          presence specify-nexthop ;
                          leaf backup-intf {
                            description 'Configure the backup interface of static remote lfa for interface'
                                        ;
                            type ncd:ifname {
                              length 1..31 {
                                description 'Interface name'
                                            ;
                              }
                            }
                            mandatory true ;
                          }
                          leaf gateway {
                            description 'Configure the gateway of static remote lfa for interface'
                                        ;
                            type ncd:ipv4-address-none-zero ;
                            mandatory true ;
                          }
                          ncd:revise-date 2016-08-10 ;
                        }
                      }
                    }
                  }
                  container cost-link-sd {
                    description 'Configure interface cost when link is in SD st'
                              + 'atus'
                                ;
                    choice cost-link-sd {
                      description 'Configure interface cost when link is in SD '
                                + 'status'
                                  ;
                      default increase-value ;
                      case increase-value {
                        description 'Set increase cost when link is in SD status'
                                    ;
                        leaf increase-value {
                          description 'The increase cost value'
                                      ;
                          type uint16 {
                            range 100..10000 ;
                          }
                          default 3000 ;
                        }
                      }
                      case maximum {
                        description 'Set maximum cost when link is in SD status'
                                    ;
                        leaf maximum {
                          description 'Set maximum cost'
                                      ;
                          type empty ;
                        }
                      }
                    }
                    ncd:revise-date 2015-06-01 ;
                  }
                  container cost-lag-down {
                    description 'Configure interface cost when link detects lag'
                              + ' down.'
                                ;
                    choice cost-lag-down {
                      description 'Configure interface cost when link detects l'
                                + 'ag down.'
                                  ;
                      case increase-value {
                        description 'Set increase cost when link detects lag do'
                                  + 'wn.'
                                    ;
                        leaf increase-value {
                          description 'The increase cost value'
                                      ;
                          type uint16 {
                            range 100..10000 ;
                          }
                        }
                      }
                      case maximum {
                        description 'Set maximum cost when link detects lag dow'
                                  + 'n.'
                                    ;
                        leaf maximum {
                          description 'Set maximum cost'
                                      ;
                          type empty ;
                        }
                      }
                    }
                    ncd:revise-date 2019-08-03 ;
                  }
                  container cost-bfd-down {
                    description 'Configure interface cost when link detects bfd'
                              + ' down.'
                                ;
                    choice cost-bfd-down {
                      description 'Configure interface cost when link detects b'
                                + 'fd down.'
                                  ;
                      case increase-value {
                        description 'Set increase cost when link detects bfd do'
                                  + 'wn.'
                                    ;
                        leaf increase-value {
                          description 'The increase cost value'
                                      ;
                          type uint16 {
                            range 100..10000 ;
                          }
                        }
                      }
                      case maximum {
                        description 'Set maximum cost when link detects bfd dow'
                                  + 'n.'
                                    ;
                        leaf maximum {
                          description 'Set maximum cost'
                                      ;
                          type empty ;
                        }
                      }
                    }
                    ncd:revise-date 2019-11-23 ;
                  }
                  container ti-lfa {
                    description 'Ti-lfa related attribute of this interface'
                                ;
                    list srlg {
                      description 'ti-lfa srlg of this interface'
                                  ;
                      key srlg-id ;
                      leaf srlg-id {
                        description 'srlg indentify'
                                    ;
                        type uint32 ;
                      }
                    }
                    ncd:revise-date 2020-04-09 ;
                  }
                  container suppress-flapping {
                    description 'Suppress flapping.'
                                ;
                    container adjacency {
                      description 'Suppress flapping for adjacency.'
                                  ;
                      leaf capability {
                        description 'Capability of suppress flapping for adjace'
                                  + 'ncy.'
                                    ;
                        type enumeration {
                          enum enable {
                            value 1 ;
                            description 'Enable suppress flapping for adjacency.'
                                        ;
                          }
                          enum disable {
                            value 2 ;
                            description 'Disable suppress flapping for adjacency.'
                                        ;
                          }
                        }
                      }
                      container detect-parameter {
                        description 'Set detect parameter of suppress flapping '
                                  + 'for adjacency.'
                                    ;
                        presence detect-parameter ;
                        leaf detect-interval {
                          description 'Detect interval.'
                                      ;
                          type uint16 {
                            range 1..300 ;
                          }
                          units second ;
                          mandatory true ;
                        }
                        leaf threshold {
                          description 'Threshold of flapping.'
                                      ;
                          type uint16 {
                            range 1..1000 ;
                          }
                          units second ;
                          mandatory true ;
                        }
                        leaf resume-interval {
                          description 'Resume interval.'
                                      ;
                          type uint16 {
                            range 2..1000 ;
                          }
                          units second ;
                          mandatory true ;
                        }
                      }
                      container hold-down {
                        description 'Hold down mode.'
                                    ;
                        presence hold-down ;
                        leaf hold-interval {
                          description 'Hold down interval.'
                                      ;
                          type uint16 {
                            range 1..600 ;
                          }
                          units second ;
                          mandatory true ;
                        }
                      }
                    }
                    ncd:revise-date 2020-07-23 ;
                  }
                }
              }
              container multi-area-interfaces {
                description 'Enable multi-area adjacency on this interface'
                            ;
                list multi-area-interface {
                  key interface-name ;
                  leaf interface-name {
                    description 'Interface name'
                                ;
                    type ncd:ifname {
                      length 1..31 ;
                    }
                  }
                  leaf hello-interval {
                    description 'Time between hello packets, Seconds'
                                ;
                    type uint32 {
                      range 1..65535 ;
                    }
                    units second ;
                  }
                  leaf dead-interval {
                    description 'Interval after which a neighbor is declared de'
                              + 'ad, Seconds'
                                ;
                    type uint32 {
                      range 1..65535 ;
                    }
                    units second ;
                  }
                  leaf cost {
                    description 'The cost of sending a data packet on the inter'
                              + 'face, expressed in the link state metric.'
                                ;
                    type uint32 {
                      range 1..65535 ;
                    }
                  }
                  leaf mtu-ignore {
                    description 'Ignore the mtu mismatch when exchanging DD pac'
                              + 'ket'
                                ;
                    type empty ;
                  }
                  leaf retransmit-interval {
                    description 'Time between retransmitting lost link state ad'
                              + 'vertisements, Seconds'
                                ;
                    type uint32 {
                      range 1..65535 ;
                    }
                    units second ;
                    default 5 ;
                  }
                  leaf transmit-delay {
                    description 'The estimated number of seconds it takes to tr'
                              + 'ansmit a LSU packet over this interface.'
                                ;
                    type uint32 {
                      range 1..65535 ;
                    }
                    units second ;
                    default 1 ;
                  }
                  container authentication-key {
                    description 'Simple authentication key'
                                ;
                    choice authentication-key {
                      description 'Simple authentication key'
                                  ;
                      case clear {
                        description 'Cleared key'
                                    ;
                        leaf clear {
                          description 'Cleared key'
                                      ;
                          type string {
                            length 1..8 ;
                          }
                        }
                      }
                      case encrypted {
                        description 'Encrypted key'
                                    ;
                        leaf encrypted {
                          description 'Encrypted key'
                                      ;
                          type string {
                            length 1..128 ;
                          }
                        }
                      }
                    }
                  }
                  container authentication {
                    description 'Authentication configuration'
                                ;
                    choice authentication {
                      description 'Authentication configuration'
                                  ;
                      case null {
                        description 'Null authentication'
                                    ;
                        leaf null {
                          description 'Null authentication'
                                      ;
                          type empty ;
                        }
                      }
                      case simple {
                        description 'Simple authentication'
                                    ;
                        leaf simple {
                          description 'Simple authentication'
                                      ;
                          type empty ;
                        }
                      }
                      case keychain {
                        description 'Keychain authentication'
                                    ;
                        leaf keychain-name {
                          description 'Keychain authentication name'
                                      ;
                          type string {
                            length 1..31 ;
                          }
                        }
                      }
                    }
                  }
                }
                ncd:revise-date 2020-01-09 ;
              }
              container mpls-te {
                description 'Configure an ospf area to run MPLS traffic enginee'
                          + 'ring'
                            ;
                presence mpls-te ;
                leaf mple-te {
                  description 'Configure an ospf area to run MPLS traffic engin'
                            + 'eering'
                              ;
                  type empty ;
                  mandatory true ;
                }
              }
              container dynamic-remote-lfa {
                description 'Configure dynamic remote lfa for areas'
                            ;
                leaf capability {
                  description 'Configure AREA dynamic remote LFA capability'
                              ;
                  type enumeration {
                    enum enable {
                      value 1 ;
                      description Enable ;
                    }
                    enum disable {
                      value 2 ;
                      description Disable ;
                    }
                  }
                }
                leaf maximum-cost {
                  description 'Configure AREA dynamic remote LFA tunnel allowed'
                            + ' maximum cost'
                              ;
                  type uint32 {
                    range 1..16777214 {
                      description 'Maximum cost'
                                  ;
                    }
                  }
                }
                ncd:revise-date 2015-09-10 ;
              }
            }
          }
          container networks {
            status obsolete {
              ncd:revise-date 2016-03-14 ;
            }
            description 'Ospf network'
                        ;
            list network {
              description 'Ospf network'
                          ;
              key 'net-num wild-mask'
                  ;
              leaf net-num {
                description 'IP address'
                            ;
                type ncd:ipv4-address ;
              }
              leaf wild-mask {
                description 'IP MASK'
                            ;
                type ncd:ipv4-imask ;
              }
              leaf area-ip {
                description 'Area IP'
                            ;
                type ncd:ipv4-address ;
                mandatory true ;
              }
            }
          }
          container redistribute {
            description Redistribute ;
            container redistribute-ospfs {
              description 'Redistribute OSPF'
                          ;
              list redistribute-ospf {
                description 'Redistribute OSPF'
                            ;
                key 'protocol ospf-pro-id'
                    ;
                leaf protocol {
                  description 'Protocol Type'
                              ;
                  type enumeration {
                    enum ospf-int {
                      value 4 ;
                      description 'ospf-int route'
                                  ;
                    }
                    enum ospf-ext {
                      value 5 ;
                      description 'ospf-ext route'
                                  ;
                    }
                  }
                }
                leaf ospf-pro-id {
                  description 'Redistribute OSPF process ID'
                              ;
                  type uint32 {
                    range 1..65535 {
                      description 'Process ID from 1 to 65535'
                                  ;
                    }
                  }
                }
                leaf tag {
                  description 'Tag for redistributed routes'
                              ;
                  type uint32;
                  //type uint32 {
                  //  range 0..4294967295 {
                  //    description 'Tag for redistributed routes'
                  //                ;
                  //  }
                  //}
                }
                leaf metric {
                  description 'Ospf metric'
                              ;
                  type uint32 {
                    range 1..16777214 {
                      description 'Ospf metric'
                                  ;
                    }
                  }
                }
                leaf metric-type {
                  description 'The metric type'
                              ;
                  type enumeration {
                    enum ext-2 {
                      value 0 ;
                      description ext-2 ;
                    }
                    enum ext-1 {
                      value 1 ;
                      description ext-1 ;
                    }
                  }
                  default ext-2 ;
                }
                leaf route-map {
                  description 'Name of route-map,characters from 1 to 200'
                              ;
                  type string {
                    length 1..200 {
                      description 'Name of route-map,characters from 1 to 31'
                                  ;
                    }
                  }
                }
                leaf tag-flag {
                  description 'Tag flag'
                              ;
                  type enumeration {
                    enum tag-valid {
                      value 1 ;
                      description tag-valid ;
                    }
                    enum tag-invalid {
                      value 2 ;
                      description tag-invalid ;
                    }
                  }
                  default tag-invalid ;
                }
                leaf with-orig-metric {
                  description 'Use rte metric as default'
                              ;
                  type empty ;
                  ncd:revise-date 2016-12-08 ;
                }
                leaf host-only {
                  description 'Using host-only'
                              ;
                  type empty ;
                  ncd:revise-date 2019-06-20 ;
                }
              }
            }
            container redistribute-isiss {
              description 'Redistribute ISIS'
                          ;
              list redistribute-isis {
                description 'Redistribute ISIS'
                            ;
                key 'protocol isis-pro-id'
                    ;
                leaf protocol {
                  description 'Protocol Type'
                              ;
                  type enumeration {
                    enum isis-1 {
                      value 6 ;
                      description 'isis-1 route'
                                  ;
                    }
                    enum isis-2 {
                      value 7 ;
                      description 'isis-2 route'
                                  ;
                    }
                    enum isis-1-2 {
                      value 8 ;
                      description 'isis-1-2 route'
                                  ;
                    }
                  }
                }
                leaf isis-pro-id {
                  description 'Redistribute ISIS process ID'
                              ;
                  type uint32 {
                    range 0..65535 {
                      description 'Process ID from 0 to 65535'
                                  ;
                    }
                  }
                }
                leaf tag {
                  description 'Tag for redistributed routes'
                              ;
                  type uint32;
                  //type uint32 {
                  //  range 0..4294967295 {
                  //    description 'Tag for redistributed routes'
                  //                ;
                  //  }
                  //}
                }
                leaf metric {
                  description 'Ospf metric'
                              ;
                  type uint32 {
                    range 1..16777214 {
                      description 'Ospf metric'
                                  ;
                    }
                  }
                }
                leaf metric-type {
                  description 'The metric type'
                              ;
                  type enumeration {
                    enum ext-2 {
                      value 0 ;
                      description ext-2 ;
                    }
                    enum ext-1 {
                      value 1 ;
                      description ext-1 ;
                    }
                  }
                  default ext-2 ;
                }
                leaf route-map {
                  description 'Name of route-map,characters from 1 to 200'
                              ;
                  type string {
                    length 1..200 {
                      description 'Name of route-map,characters from 1 to 200'
                                  ;
                    }
                  }
                }
                leaf tag-flag {
                  description 'Tag flag'
                              ;
                  type enumeration {
                    enum tag-valid {
                      value 1 ;
                      description tag-valid ;
                    }
                    enum tag-invalid {
                      value 2 ;
                      description tag-invalid ;
                    }
                  }
                  default tag-invalid ;
                }
                leaf with-orig-metric {
                  description 'Use rte metric as default'
                              ;
                  type empty ;
                  ncd:revise-date 2016-12-08 ;
                }
                leaf host-only {
                  description 'Using host-only'
                              ;
                  type empty ;
                  ncd:revise-date 2019-06-20 ;
                }
              }
            }
            container redistribute-bgps {
              description 'Redistribute BGP'
                          ;
              list redistribute-bgp {
                description 'Redistribute BGP'
                            ;
                key protocol ;
                leaf protocol {
                  description 'Protocol Type'
                              ;
                  type enumeration {
                    enum bgp-ext {
                      value 9 ;
                      description 'bgp-ext route'
                                  ;
                    }
                    enum bgp-int {
                      value 10 ;
                      description 'bgp-int route'
                                  ;
                    }
                  }
                }
                leaf tag {
                  description 'Tag for redistributed routes'
                              ;
                  type uint32;
                  //type uint32 {
                  //  range 0..4294967295 {
                  //    description 'Tag for redistributed routes'
                  //                ;
                  //  }
                  //}
                }
                leaf metric {
                  description 'Ospf metric'
                              ;
                  type uint32 {
                    range 1..16777214 {
                      description 'Ospf metric'
                                  ;
                    }
                  }
                }
                leaf metric-type {
                  description 'The metric type'
                              ;
                  type enumeration {
                    enum ext-2 {
                      value 0 ;
                      description ext-2 ;
                    }
                    enum ext-1 {
                      value 1 ;
                      description ext-1 ;
                    }
                  }
                  default ext-2 ;
                }
                leaf route-map {
                  description 'Name of route-map,characters from 1 to 200'
                              ;
                  type string {
                    length 1..200 {
                      description 'Name of route-map,characters from 1 to 200'
                                  ;
                    }
                  }
                }
                leaf peer-addr {
                  description 'Peer address'
                              ;
                  type ncd:ipv4-address {
                    pattern '([1-9][0-9]*\.[1-9][0-9]*\.[1-9][0-9]*\.[1-9][0-9]'
                          + '*)|([1-9][0-9]*\.0\.0\.0)|(0\.[1-9][0-9]*\.0\.0)|('
                          + '0\.0\.[1-9][0-9]*\.0)|(0\.0\.0\.[1-9][0-9]*)|([1-9'
                          + '][0-9]*\.[1-9][0-9]*\.0\.0)|(0\.[1-9][0-9]*\.[1-9]'
                          + '[0-9]*\.0)|(0\.0\.[1-9][0-9]*\.[1-9][0-9]*)|([1-9]'
                          + '[0-9]*\.0\.0\.[1-9][0-9]*)|(0\.[1-9][0-9]*\.0\.[1-'
                          + '9][0-9]*)|([1-9][0-9]*\.0\.[1-9][0-9]*\.0)|([1-9]['
                          + '0-9]*\.[1-9][0-9]*\.[1-9][0-9]*\.0)|([1-9][0-9]*\.'
                          + '[1-9][0-9]*\.0\.[1-9][0-9]*)|([1-9][0-9]*\.0\.[1-9'
                          + '][0-9]*\.[1-9][0-9]*)|(0\.[1-9][0-9]*\.[1-9][0-9]*'
                          + '\.[1-9][0-9]*)'
                            ;
                  }
                }
                leaf asno {
                  description 'Autonomous system number'
                              ;
                  type ncd:asn-dot {
                    length 1..11 ;
                  }
                }
                leaf tag-flag {
                  description 'Tag flag'
                              ;
                  type enumeration {
                    enum tag-valid {
                      value 1 ;
                      description tag-valid ;
                    }
                    enum tag-invalid {
                      value 2 ;
                      description tag-invalid ;
                    }
                  }
                  default tag-invalid ;
                }
                leaf with-orig-metric {
                  description 'Use rte metric as default'
                              ;
                  type empty ;
                  ncd:revise-date 2016-12-08 ;
                }
                leaf host-only {
                  description 'Using host-only'
                              ;
                  type empty ;
                  ncd:revise-date 2019-06-20 ;
                }
              }
            }
            container redistribute-pss {
              description 'Redistribute PS'
                          ;
              list redistribute-ps {
                description 'Redistribute PS'
                            ;
                key protocol ;
                leaf protocol {
                  description 'Protocol Type'
                              ;
                  type enumeration {
                    enum ps-busi-addr {
                      value 14 ;
                      description 'ps-busi-addr route'
                                  ;
                    }
                    enum ps-user-addr {
                      value 15 ;
                      description 'ps-user-addr route'
                                  ;
                    }
                  }
                }
                leaf tag {
                  description 'Tag for redistributed routes'
                              ;
                  type uint32;
                  //type uint32 {
                  //  range 0..4294967295 {
                  //    description 'Tag for redistributed routes'
                  //                ;
                  //  }
                  //}
                }
                leaf metric {
                  description 'Ospf metric'
                              ;
                  type uint32 {
                    range 1..16777214 {
                      description 'Ospf metric'
                                  ;
                    }
                  }
                }
                leaf metric-type {
                  description 'The metric type'
                              ;
                  type enumeration {
                    enum ext-2 {
                      value 0 ;
                      description ext-2 ;
                    }
                    enum ext-1 {
                      value 1 ;
                      description ext-1 ;
                    }
                  }
                  default ext-2 ;
                }
                leaf route-map {
                  description 'Name of route-map,characters from 1 to 200'
                              ;
                  type string {
                    length 1..200 {
                      description 'Name of route-map,characters from 1 to 200'
                                  ;
                    }
                  }
                }
                leaf with-orig-metric {
                  description 'Use rte metric as default'
                              ;
                  type enumeration {
                    enum orig-metric {
                      value 1 ;
                      description orig-metric ;
                    }
                    enum not-orig-metric {
                      value 2 ;
                      description not-orig-metric ;
                    }
                  }
                  default not-orig-metric ;
                }
                leaf tag-flag {
                  description 'Tag flag'
                              ;
                  type enumeration {
                    enum tag-valid {
                      value 1 ;
                      description tag-valid ;
                    }
                    enum tag-invalid {
                      value 2 ;
                      description tag-invalid ;
                    }
                  }
                  default tag-invalid ;
                }
                leaf host-only {
                  description 'Using host-only'
                              ;
                  type empty ;
                  ncd:revise-date 2019-06-20 ;
                }
              }
            }
            container redistributes {
              description 'Redistribute static,connected and so on'
                          ;
              list redistribute {
                description 'Redistribute static,connected and so on'
                            ;
                key protocol ;
                leaf protocol {
                  description 'Protocol Type'
                              ;
                  type enumeration {
                    enum static {
                      value 1 ;
                      description 'Static route.'
                                  ;
                    }
                    enum connected {
                      value 2 ;
                      description 'Connected route.'
                                  ;
                    }
                    enum rip {
                      value 3 ;
                      description 'Rip route.'
                                  ;
                    }
                    enum nat {
                      value 11 ;
                      description 'NAT route.'
                                  ;
                    }
                    enum subscriber-host {
                      value 12 ;
                      description 'Subscriber-host route.'
                                  ;
                    }
                    enum natpt {
                      value 13 ;
                      description 'Natpt route.'
                                  ;
                    }
                    enum subscriber-aggregation {
                      value 16 ;
                      description 'Subscriber-aggregation route.'
                                  ;
                    }
                    enum user-special {
                      value 17 ;
                      description 'User-special route.'
                                  ;
                    }
                    enum sl-nat64-ipv4 {
                      value 27 ;
                      description 'Stateless NAT64 prefix.'
                                  ;
                    }
                    enum bras-pool {
                      value 18 ;
                      description 'BRAS-pool route.'
                                  ;
                    }
                    enum ipsec {
                      value 19 ;
                      description 'Ipsec route.'
                                  ;
                    }
                    enum nat-mask {
                      value 20 ;
                      description 'Nat-mask route.'
                                  ;
                    }
                    enum zenic-local {
                      value 21 ;
                      description 'Zenic-local route.'
                                  ;
                    }
                    enum dyn-leasedline {
                      value 22 ;
                      description 'Dynamic-leased-line routes assigned by AAA'
                                  ;
                    }
                  }
                }
                leaf tag {
                  description 'Tag for redistributed routes'
                              ;
                  type uint32;
                  //type uint32 {
                  //  range 0..4294967295 {
                  //    description 'Tag for redistributed routes'
                  //                ;
                  //  }
                  //}
                }
                leaf metric {
                  description 'Ospf metric'
                              ;
                  type uint32 {
                    range 1..16777214 {
                      description 'Ospf metric'
                                  ;
                    }
                  }
                }
                leaf metric-type {
                  description 'The metric type'
                              ;
                  type enumeration {
                    enum ext-2 {
                      value 0 ;
                      description ext-2 ;
                    }
                    enum ext-1 {
                      value 1 ;
                      description ext-1 ;
                    }
                  }
                  default ext-2 ;
                }
                leaf route-map {
                  description 'Name of route-map,characters from 1 to 200'
                              ;
                  type string {
                    length 1..200 {
                      description 'Name of route-map,characters from 1 to 200'
                                  ;
                    }
                  }
                }
                leaf tag-flag {
                  description 'Tag flag'
                              ;
                  type enumeration {
                    enum tag-valid {
                      value 1 ;
                      description tag-valid ;
                    }
                    enum tag-invalid {
                      value 2 ;
                      description tag-invalid ;
                    }
                  }
                  default tag-invalid ;
                }
                leaf with-orig-metric {
                  description 'Use rte metric as default'
                              ;
                  type empty ;
                  ncd:revise-date 2016-12-08 ;
                }
                leaf host-only {
                  description 'Using host-only'
                              ;
                  type empty ;
                  ncd:revise-date 2019-06-20 ;
                }
              }
            }
          }
          container passive-intf {
            description 'Passive interface'
                        ;
            container passive-intf-defaults {
              description 'Passive interface'
                          ;
              list passive-intf-default {
                description 'Passive interface'
                            ;
                key default ;
                leaf default {
                  description Default ;
                  type uint8 {
                    range 1 ;
                  }
                }
              }
            }
            container passive-intfs {
              description 'Passive interface'
                          ;
              list passive-intf {
                description 'Passive interface'
                            ;
                key intf-name ;
                leaf intf-name {
                  description 'Interface name'
                              ;
                  type ncd:ifname {
                    length 1..31 {
                      description 'Interface name'
                                  ;
                    }
                  }
                }
                leaf status {
                  description 'The status of passive-interface'
                              ;
                  type enumeration {
                    enum disable {
                      value 1 ;
                      description disable ;
                    }
                    enum enable {
                      value 2 ;
                      description enable ;
                    }
                  }
                  default enable ;
                }
              }
            }
          }
          container neighbors {
            description 'Ospf neighbor'
                        ;
            list neighbor {
              description 'Ospf neighbor'
                          ;
              key ip-addr ;
              leaf ip-addr {
                description 'Ospf neighbor IP address'
                            ;
                type ncd:ipv4-address ;
              }
              leaf cost {
                description 'Ospf cost of point-to-multipoint neighbor'
                            ;
                type uint32 {
                  range 1..65535 {
                    description 'Neighbor cost'
                                ;
                  }
                }
              }
              leaf pri {
                description 'Ospf priority of non-broadcast neighbor'
                            ;
                type uint32 {
                  range 0..255 {
                    description 'Neighbor cost Priority'
                                ;
                  }
                }
                default 1 ;
              }
              leaf poll-interval {
                description 'Poll interval time of non-broadcast neighbor,Secon'
                          + 'ds'
                            ;
                type uint32 {
                  range 1..65535 {
                    description 'Poll interval time of non-broadcast neighbor,S'
                              + 'econds'
                                ;
                  }
                }
                units second ;
              }
            }
          }
          container distribute-list {
            description Distribute-list ;
            container distribute-list-in {
              description 'Filter networks in routing updates'
                          ;
              container distribute-list-name {
                description 'Name of the distribute-list'
                            ;
                choice distribute-list-name {
                  description 'Name of the distribute-list'
                              ;
                  case access-list {
                    description 'Name of the access-list'
                                ;
                    container access-list-name {
                      description 'Name of the access-list'
                                  ;
                      presence access-list-name ;
                      leaf access-list-name {
                        description 'Name of the access-list,characters from 1 '
                                  + 'to 31'
                                    ;
                        type string {
                          length 1..31 {
                            description 'Name of the access-list,characters from 1 to 31'
                                        ;
                          }
                        }
                        mandatory true ;
                      }
                    }
                  }
                  case prefix-list {
                    description 'Name of the prefix-list'
                                ;
                    container name-ip-prefxi-list {
                      description 'Name of the prefix-list'
                                  ;
                      presence name-ip-prefxi-list ;
                      leaf name-ip-prefxi-list {
                        description 'Name of the prefix-list,characters from 1 '
                                  + 'to 169'
                                    ;
                        type string {
                          length 1..169 {
                            description 'Name of the prefix-list,characters from 1 to 169'
                                        ;
                          }
                        }
                        mandatory true ;
                      }
                      leaf prefix-list-gateway {
                        description 'Name of the gateway,characters from 1 to 1'
                                  + '69'
                                    ;
                        type string {
                          length 1..169 {
                            description 'Name of the gateway,characters from 1 to 169'
                                        ;
                          }
                        }
                      }
                    }
                  }
                  case gateway {
                    description 'Name of the gateway'
                                ;
                    container gateway {
                      description 'Name of the gateway'
                                  ;
                      presence gateway ;
                      leaf gateway {
                        description 'Name of the gateway,characters from 1 to 1'
                                  + '69'
                                    ;
                        type string {
                          length 1..169 {
                            description 'Name of the gateway,characters from 1 to 169'
                                        ;
                          }
                        }
                        mandatory true ;
                      }
                    }
                  }
                  case route-map {
                    description 'Name of the route-map'
                                ;
                    container name-route-map {
                      description 'Name of the route-map'
                                  ;
                      presence name-route-map ;
                      leaf name-route-map {
                        description 'Name of the route-map,characters from 1 to'
                                  + ' 200'
                                    ;
                        type string {
                          length 1..200 {
                            description 'Name of the route-map,characters from 1 to 200'
                                        ;
                          }
                        }
                        mandatory true ;
                      }
                      leaf local-mt {
                        description Local-mt ;
                        type empty ;
                      }
                    }
                  }
                }
              }
            }
            container distribute-list-out {
              description 'Filter networks in routing updates'
                          ;
              container distribute-list-name {
                description 'Name of the distribute-list'
                            ;
                choice distribute-list-name {
                  description 'Name of the distribute-list'
                              ;
                  case access-list {
                    description 'Name of the access-list'
                                ;
                    container access-list-name {
                      description 'Name of the access-list'
                                  ;
                      presence access-list-name ;
                      leaf access-list-name {
                        description 'Name of the access-list,characters from 1 '
                                  + 'to 31'
                                    ;
                        type string {
                          length 1..31 {
                            description 'Name of the access-list,characters from 1 to 31'
                                        ;
                          }
                        }
                        mandatory true ;
                      }
                    }
                  }
                  case prefix-list {
                    description 'Name of the prefix-list'
                                ;
                    container name-ip-prefix-list {
                      description 'Name of the prefix-list'
                                  ;
                      presence name-ip-prefix-list ;
                      leaf name-ip-prefix-list {
                        description 'Name of the prefix-list,characters from 1 '
                                  + 'to 169'
                                    ;
                        type string {
                          length 1..169 {
                            description 'Name of the prefix-list,characters from 1 to 169'
                                        ;
                          }
                        }
                        mandatory true ;
                      }
                    }
                  }
                }
              }
            }
          }
          container frr-type {
            description 'Ospf fast-reroute type'
                        ;
            presence frr-type ;
            leaf per-prefix {
              description 'Ospf fast-reroute policy'
                          ;
              type empty ;
              mandatory true ;
            }
          }
          container filters {
            description 'Filter route information'
                        ;
            list filter {
              description 'Filter route information'
                          ;
              key 'ip-addr ip-mask'
                  ;
              leaf ip-addr {
                description 'IP address'
                            ;
                type ncd:ipv4-address ;
              }
              leaf ip-mask {
                description 'Subnet mask'
                            ;
                type ncd:ipv4-mask ;
              }
              leaf exact {
                description 'Map address exactly'
                            ;
                type empty ;
              }
              leaf prefence {
                description 'Route preference'
                            ;
                type uint32 {
                  range 1..255 {
                    description 'Route preference'
                                ;
                  }
                }
                mandatory true ;
              }
            }
          }
          container interfaces {
            description 'An interface to configure'
                        ;
            list interface {
              description 'An interface to configure'
                          ;
              key intf-name ;
              leaf intf-name {
                description 'Interface name'
                            ;
                type ncd:ifname {
                  length 1..31 {
                    description 'Interface name'
                                ;
                  }
                }
              }
              leaf authentication-key {
                description 'Authentication password (key)'
                            ;
                type string {
                  length 1..8 {
                    description 'Authentication password (key)'
                                ;
                  }
                }
              }
              leaf cost {
                description 'Interface cost'
                            ;
                type uint32 {
                  range 1..65535 {
                    description 'Interface cost'
                                ;
                  }
                }
              }
              leaf dead-interval {
                description 'Interval after which a neighbor is declared dead,S'
                          + 'econds'
                            ;
                type uint32 {
                  range 1..65535 {
                    description 'Interval after which a neighbor is declared de'
                              + 'ad,Seconds'
                                ;
                  }
                }
                units second ;
              }
              leaf hello-interval {
                description 'Time between hello packets,Seconds'
                            ;
                type uint32 {
                  range 1..65535 {
                    description 'Time between hello packets,Seconds'
                                ;
                  }
                }
                units second ;
              }
              leaf mtu-ignore {
                description 'Ignore the mtu mismatch when exchanging DD packet'
                            ;
                type enumeration {
                  enum config {
                    value 1 ;
                    description config ;
                  }
                  enum no-config {
                    value 2 ;
                    description no-config ;
                  }
                }
                default no-config ;
              }
              leaf priority {
                description 'Router priority'
                            ;
                type uint32 {
                  range 0..255 {
                    description 'Router priority'
                                ;
                  }
                }
                default 1 ;
              }
              leaf resync-timeout {
                description 'Interval after which adjacency is reset if oob-res'
                          + 'ync is not started,Seconds'
                            ;
                type uint32 {
                  range 1..3600 {
                    description 'Interval after which adjacency is reset if oob'
                              + '-resync is not started,Seconds'
                                ;
                  }
                }
                units second ;
              }
              leaf retransmit-interval {
                description 'Time between retransmitting lost link state advert'
                          + 'isements,Seconds'
                            ;
                type uint32 {
                  range 1..65535 {
                    description 'Time between retransmitting lost link state ad'
                              + 'vertisements,Seconds'
                                ;
                  }
                }
                units second ;
                default 5 ;
              }
              leaf transmit-delay {
                description 'Link state transmit delay,Seconds'
                            ;
                type uint32 {
                  range 1..65535 {
                    description 'Link state transmit delay,Seconds'
                                ;
                  }
                }
                units second ;
                default 1 ;
              }
              leaf ttl-security {
                description 'Configure OSPF ttl-security hops'
                            ;
                type int32 {
                  range 1..254 {
                    description 'Configure OSPF ttl-security hops'
                                ;
                  }
                }
                units hop ;
              }
              leaf authenkey-p {
                description 'Password to be configured'
                            ;
                type string {
                  length 1..128 {
                    description 'Password to be configured'
                                ;
                  }
                }
              }
              leaf ldp-igp-sync {
                description 'Config MPLS LDP IGP sync'
                            ;
                type enumeration {
                  enum no-config {
                    value 0 ;
                    description no-config ;
                  }
                  enum enable {
                    value 1 ;
                    description enable ;
                  }
                  enum disable {
                    value 2 ;
                    description disable ;
                  }
                }
                default no-config ;
              }
              leaf ldp-autoconfig {
                description 'Config MPLS LDP IGP autoconfig'
                            ;
                type enumeration {
                  enum no-config {
                    value 0 ;
                    description no-config ;
                  }
                  enum enable {
                    value 1 ;
                    description enable ;
                  }
                  enum disable {
                    value 2 ;
                    description disable ;
                  }
                }
                default no-config ;
              }
              container fast-reroute {
                description 'Fast reroute'
                            ;
                presence fast-reroute ;
                leaf disable {
                  description Disable ;
                  type empty ;
                  mandatory true ;
                }
              }
              container md-keys {
                description 'Message digest authentication key'
                            ;
                list md-key {
                  description 'Message digest authentication key'
                              ;
                  key key-id ;
                  leaf key-id {
                    description 'Key ID'
                                ;
                    type uint32 {
                      range 1..255 {
                        description 'Key ID,from 1 to 255'
                                    ;
                      }
                    }
                  }
                  container secret-key {
                    description 'Password to be configured'
                                ;
                    choice md5-password-type {
                      case unencrypted {
                        leaf secret-key {
                          description 'Password to be configured'
                                      ;
                          type string {
                            length 1..16 {
                              description 'Password to be configured,characters from 1 to 16'
                                          ;
                            }
                          }
                          mandatory true ;
                        }
                      }
                      case encrypted {
                        leaf encry-secret-key {
                          description 'Encrypted password to be configured'
                                      ;
                          type string {
                            length 1..128 {
                              description 'Password to be configured'
                                          ;
                            }
                          }
                          mandatory true ;
                        }
                        ncd:revise-date 2019-12-16 ;
                      }
                    }
                    leaf delay {
                      description 'A period of time in minutes'
                                  ;
                      type uint32 {
                        range 0..100000 {
                          description 'A period of time in minutes'
                                      ;
                        }
                      }
                      units minute ;
                      default 0 ;
                    }
                  }
                }
              }
              container authtype {
                description 'Enable authentication on the interface'
                            ;
                container authtype {
                  description 'Enable authentication on the interface'
                              ;
                  choice authtype {
                    description 'Enable authentication on the interface'
                                ;
                    case null {
                      description 'No authentication'
                                  ;
                      container null {
                        description 'No authentication'
                                    ;
                        presence null ;
                        leaf null {
                          description 'No authentication'
                                      ;
                          type empty ;
                          mandatory true ;
                        }
                      }
                    }
                    case md5 {
                      description 'Md5 authentication'
                                  ;
                      container md5 {
                        description 'Md5 authentication'
                                    ;
                        presence md5 ;
                        leaf md5 {
                          description 'Md5 authentication'
                                      ;
                          type empty ;
                          mandatory true ;
                        }
                      }
                    }
                    case simple {
                      description 'Simple authentication'
                                  ;
                      container simple {
                        description 'Simple authentication'
                                    ;
                        presence simple ;
                        leaf simple {
                          description 'Simple authentication'
                                      ;
                          type empty ;
                          mandatory true ;
                        }
                      }
                    }
                  }
                }
              }
              container bfd {
                description 'Configure BFD for interface'
                            ;
                presence bfd ;
                leaf status {
                  description 'Bfd status'
                              ;
                  type enumeration {
                    enum enable {
                      value 0 ;
                    }
                    enum disable {
                      value 1 ;
                    }
                  }
                  mandatory true ;
                }
                container bfd-param {
                  description 'Configure BFD for interface'
                              ;
                  presence bfd-param ;
                  leaf interval {
                    description Interval ;
                    type uint32 {
                      range 10..990 ;
                    }
                    units millisecond ;
                    mandatory true ;
                  }
                  leaf min-rx {
                    description Min-rx ;
                    type uint32 {
                      range 10..990 ;
                    }
                    units millisecond ;
                    mandatory true ;
                  }
                  leaf multiplier {
                    description Multiplier ;
                    type uint32 {
                      range 3..50 ;
                    }
                    mandatory true ;
                  }
                  ncd:revise-date 2015-05-14 ;
                }
              }
              container type {
                description 'Interface Network type'
                            ;
                presence type ;
                container type1 {
                  description 'Network type1'
                              ;
                  presence type1 ;
                  leaf network-type1 {
                    description 'Network type1'+"\n"
                              + '(1 BROADCAST 2 NONBROADCAST 3POINT_TO_POINT 5 '
                              + 'POINT_TO_MULPOINT)'
                                ;
                    type enumeration {
                      enum broadcast {
                        value 1 ;
                      }
                      enum non-broadcast {
                        value 2 ;
                      }
                      enum point-to-point {
                        value 3 ;
                      }
                      enum point-to-multipoint {
                        value 5 ;
                      }
                    }
                    mandatory true ;
                  }
                }
                container type2 {
                  description 'Network type2'
                              ;
                  presence type2 ;
                  leaf ptmp-nb {
                    description 'Network type(POINT_TO_MULPOINT_NB)'
                                ;
                    type enumeration {
                      enum point_to_mulpoint_nb {
                        value 1 ;
                      }
                    }
                    mandatory true ;
                  }
                }
              }
            }
          }
          container notify-default-route {
            description 'Notify default route'
                        ;
            leaf always {
              description 'Always notify default route'
                          ;
              type enumeration {
                enum config {
                  value 1 ;
                  description config ;
                }
                enum no-config {
                  value 2 ;
                  description no-config ;
                }
              }
              default no-config ;
            }
            leaf metric {
              description 'Metric value'
                          ;
              type uint32 {
                range 1..16777214 {
                  description 'Metric value'
                              ;
                }
              }
            }
            leaf route-map {
              description 'Name of the route-map,characters from 1 to 200'
                          ;
              type string {
                length 1..200 {
                  description 'Name of the route-map,characters from 1 to 200'
                              ;
                }
              }
            }
            leaf metric-type {
              description 'The metric type'
                          ;
              type enumeration {
                enum ext-2 {
                  value 0 ;
                  description ext-2 ;
                }
                enum ext-1 {
                  value 1 ;
                  description ext-1 ;
                }
              }
              default ext-2 ;
            }
          }
          container summary-addrs {
            description 'Configure IP address summaries'
                        ;
            list summary-addr {
              description 'Configure IP address summaries'
                          ;
              key 'ip-addr net-mask'
                  ;
              leaf ip-addr {
                description 'IP summary address'
                            ;
                type ncd:ipv4-address ;
              }
              leaf net-mask {
                description 'Summary mask'
                            ;
                type ncd:ipv4-mask ;
              }
              leaf cost-value {
                description 'Advertised metric for this summary address'
                            ;
                type uint32 {
                  range 1..16777214 {
                    description 'Advertised metric for this summary address'
                                ;
                  }
                }
              }
            }
          }
          container tracks {
            description 'Ospf track'
                        ;
            list track {
              description 'Ospf track'
                          ;
              key name ;
              leaf name {
                description 'Track name'
                            ;
                type string {
                  length 1..31 {
                    description 'Track name,characters from 1 to 31'
                                ;
                  }
                }
              }
            }
          }
          container domain-tag {
            description 'Ospf domain tag'
                        ;
            presence domain-tag ;
            leaf domain-tag {
              description 'Ospf domain tag'
                          ;
              type uint32 {
                range 1..4294967295 {
                  description 'Ospf domain tag'
                              ;
                }
              }
              mandatory true ;
            }
          }
          container router-id {
            description 'Ospf router-id'
                        ;
            presence router-id ;
            leaf router-id {
              description 'Ospf router-id'
                          ;
              type ncd:ipv4-address ;
              mandatory true ;
            }
          }
          container domain-id {
            description 'Ospf domain-id'
                        ;
            presence domain-id ;
            leaf domain-id {
              description 'Ospf domain-id in IP address format'
                          ;
              type ncd:ipv4-address ;
              mandatory true ;
            }
          }
          container max-metric {
            description 'Max metric'
                        ;
            presence metric ;
            container on-startup {
              description 'Set maximum metric temporarily after reboot'
                          ;
              choice on-startup {
                description 'Max metric'
                            ;
                case wait-for-bgp {
                  description 'BGP decide when to originate a normal router-LSA'
                              ;
                  container wait-for-bgp {
                    description 'BGP decide when to originate a normal router-L'
                              + 'SA'
                                ;
                    presence wait-for-bgp ;
                    leaf wait-for-bgp {
                      description 'BGP decide when to originate a normal router'
                                + '-LSA'
                                  ;
                      type enumeration {
                        enum config {
                          value 1 ;
                        }
                        enum no-config {
                          value 2 ;
                        }
                      }
                      mandatory true ;
                    }
                  }
                }
                case timeout {
                  description 'Secs,router-LSAs are originated with max-metric'
                              ;
                  container timeout {
                    description 'Secs,router-LSAs are originated with max-metric'
                                ;
                    presence timeout ;
                    leaf timeout {
                      description 'Secs,router-LSAs are originated with max-met'
                                + 'ric'
                                  ;
                      type uint32 {
                        range 5..86400 {
                          description 'Secs,router-LSAs are originated with max'
                                    + '-metric'
                                      ;
                        }
                      }
                      mandatory true ;
                    }
                  }
                }
              }
            }
            leaf router-lsa {
              description 'router lsa'
                          ;
              type empty ;
              mandatory true ;
            }
          }
          container distance {
            description 'Ospf distance'
                        ;
            leaf distance-inter {
              description 'Internal route distance value'
                          ;
              type uint32 {
                range 1..255 {
                  description 'Internal route distance value'
                              ;
                }
              }
              default 110 ;
            }
            leaf distance-ext1 {
              description 'The first kind of external route distance value'
                          ;
              type uint32 {
                range 1..255 {
                  description 'The first kind of external route distance value'
                              ;
                }
              }
              default 110 ;
            }
            leaf distance-ext2 {
              description 'The second kind of external distance value'
                          ;
              type uint32 {
                range 1..255 {
                  description 'The second kind of external distance value'
                              ;
                }
              }
              default 110 ;
            }
          }
          container lsa-limit {
            description 'Limit number of LSAs Ospf process can receive'
                        ;
            presence lsa-limit ;
            leaf lsa-num {
              description 'Max number of non self-generated LSAs can receive'
                          ;
              type uint32 {
                range 1..4294967294 {
                  description 'Max number of non self-generated LSAs can receive'
                              ;
                }
              }
              mandatory true ;
            }
            leaf threshold {
              description 'Threshold value(%) at which to give a warning'
                          ;
              type uint32 {
                range 1..100 {
                  description 'Threshold value(%) at which to give a warning'
                              ;
                }
              }
            }
            container lsa-choice {
              description 'Lsa choice'
                          ;
              choice lsa-choice {
                description 'Lsa choice'
                            ;
                case warning {
                  description 'Only give a warning when threshold is exceeded'
                              ;
                  container warning {
                    description 'Only give a warning when threshold is exceeded'
                                ;
                    leaf warning {
                      description 'Only give a warning when threshold is exceed'
                                + 'ed'
                                  ;
                      type empty ;
                    }
                  }
                }
                case limit-config {
                  description 'Limit config'
                              ;
                  container limit-config {
                    description 'Limit config'
                                ;
                    leaf limit-time {
                      description 'Mins,time during which limit-state continue'
                                  ;
                      type uint32 {
                        range 1..65535 {
                          description 'Mins,time during which limit-state conti'
                                    + 'nue'
                                      ;
                        }
                      }
                      units minute ;
                    }
                    leaf limit-cnt {
                      description 'Maximum times OSPF can enter limit-state'
                                  ;
                      type uint32 {
                        range 1..65535 {
                          description 'Maximum times OSPF can enter limit-state'
                                      ;
                        }
                      }
                    }
                    leaf refresh-time {
                      description 'Mins after which limit-count can be refreshed'
                                  ;
                      type uint32 {
                        range 1..65535 {
                          description 'Mins after which limit-count can be refr'
                                    + 'eshed'
                                      ;
                        }
                      }
                      units minute ;
                    }
                  }
                }
              }
            }
          }
          container thr-timer {
            description 'Ospf throttle timers'
                        ;
            presence thr-timer ;
            container spf {
              description 'Ospf spf throttle timers'
                          ;
              presence spf ;
              leaf hold-time {
                description 'Hold time for SPF calculation in milliseconds'
                            ;
                type uint32 {
                  range 1..600000 {
                    description 'Hold time for SPF calculation in milliseconds'
                                ;
                  }
                }
                units millisecond ;
                mandatory true ;
              }
              leaf delay-time {
                description 'Min delay for SPF calculation in milliseconds'
                            ;
                type uint32 {
                  range 1..600000 {
                    description 'Min delay for SPF calculation in milliseconds'
                                ;
                  }
                }
                units millisecond ;
                mandatory true ;
              }
              leaf max-delay-time {
                description 'Max delay for SPF calculation in milliseconds'
                            ;
                type uint32 {
                  range 1..600000 {
                    description 'Max delay for SPF calculation in milliseconds'
                                ;
                  }
                }
                units millisecond ;
                mandatory true ;
              }
            }
            container lsa {
              description 'Ospf lsa throttle timers'
                          ;
              presence lsa ;
              leaf hold-time {
                description 'Hold time for LSA update in milliseconds'
                            ;
                type uint32 {
                  range 1..600000 {
                    description 'Hold time for LSA update in milliseconds'
                                ;
                  }
                }
                units millisecond ;
                mandatory true ;
              }
              leaf delay-time {
                description 'Min delay for LSA update in milliseconds'
                            ;
                type uint32 {
                  range 1..600000 {
                    description 'Min delay for LSA update in milliseconds'
                                ;
                  }
                }
                units millisecond ;
                mandatory true ;
              }
              leaf max-delay-time {
                description 'Max delay for LSA update in milliseconds'
                            ;
                type uint32 {
                  range 1..600000 {
                    description 'Max delay for LSA update in milliseconds'
                                ;
                  }
                }
                units millisecond ;
                mandatory true ;
              }
            }
            container lsa-arrival {
              description 'Ospf lsa arrival throttle timers'
                          ;
              presence lsa-arrival ;
              leaf hold-time {
                description 'Hold time for LSA arrival in milliseconds'
                            ;
                type uint32 {
                  range 0..600000 {
                    description 'Hold time for LSA arrival in milliseconds'
                                ;
                  }
                }
                units millisecond ;
                mandatory true ;
              }
              leaf delay-time {
                description 'Min delay for LSA arrival in milliseconds'
                            ;
                type uint32 {
                  range 0..600000 {
                    description 'Min delay for LSA arrival in milliseconds'
                                ;
                  }
                }
                units millisecond ;
                mandatory true ;
              }
              leaf max-delay-time {
                description 'Max delay for LSA arrival in milliseconds'
                            ;
                type uint32 {
                  range 0..600000 {
                    description 'Max delay for LSA update in milliseconds'
                                ;
                  }
                }
                units millisecond ;
                mandatory true ;
              }
            }
          }
          container prefix-priority {
            description 'Prefix priority'
                        ;
            container prefix-prioritys {
              description 'Prefix priority'
                          ;
              list prefix-priority {
                description 'Prefix priority'
                            ;
                key priority ;
                leaf priority {
                  description Priority ;
                  type enumeration {
                    enum critical {
                      value 0 ;
                    }
                    enum high {
                      value 1 ;
                    }
                    enum medium {
                      value 2 ;
                    }
                  }
                }
                leaf prefix-list {
                  description 'Name of the prefix_list,characters from 1 to 169'
                              ;
                  type string {
                    length 1..169 {
                      description 'Name of the prefix_list,characters from 1 to'
                                + ' 169'
                                  ;
                    }
                  }
                  mandatory true ;
                }
              }
            }
            container prefix-priority-tags {
              description 'Prefix priority'
                          ;
              list prefix-priority-tag {
                description 'Prefix priority'
                            ;
                key 'priority tag-value'
                    ;
                leaf priority {
                  description Priority ;
                  type enumeration {
                    enum critical {
                      value 0 ;
                    }
                    enum high {
                      value 1 ;
                    }
                    enum medium {
                      value 2 ;
                    }
                  }
                }
                leaf tag-value {
                  description 'Tag value'
                              ;
                  type uint32;
                  //type uint32 {
                  //  range 0..4294967295 {
                  //    description 'Tag value'
                  //                ;
                  //  }
                  //}
                }
              }
            }
          }
          container adv-intf-to-stubs {
            description 'Advertise loopback to stub'
                        ;
            list adv-intf-to-stub {
              description 'Advertise loopback to stub'
                          ;
              key intf-name ;
              leaf intf-name {
                description 'Interface name'
                            ;
                type ncd:ifname {
                  length 1..31 {
                    description 'Interface name'
                                ;
                  }
                }
              }
            }
          }
          container ospf-te-areas {
            status obsolete {
              ncd:revise-date 2016-03-14 ;
            }
            description 'Configure an ospf area to run MPLS traffic engineering'
                        ;
            list ospf-te-area {
              description 'Configure an ospf area to run MPLS traffic engineeri'
                        + 'ng'
                          ;
              key area-ip ;
              leaf area-ip {
                description 'Area ip'
                            ;
                type ncd:ipv4-address ;
              }
            }
          }
          container dynamic-remote-lfa {
            description 'Configure dynamic remote lfa for ospf'
                        ;
            leaf capability {
              description 'Enable ospf dynamic remote lfa'
                          ;
              type enumeration {
                enum enable {
                  value 1 ;
                  description Enable ;
                }
                enum disable {
                  value 2 ;
                  description Disable ;
                }
              }
              default disable ;
            }
            leaf maximum-cost {
              description 'Configure dynamic remote lfa maximum cost'
                          ;
              type uint32 {
                range 1..16777214 {
                  description 'Maximum cost'
                              ;
                }
              }
            }
            ncd:revise-date 2015-09-10 ;
          }
          container frr-priority {
            description 'Configure fast-reroute priority for ospf'
                        ;
            leaf lfa {
              description 'Configure lfa priority for ospf'
                          ;
              type uint8 {
                range 1..255 ;
              }
              default 110 ;
            }
            leaf dynamic-remote-lfa {
              description 'Configure dynamic remote lfa priority for ospf'
                          ;
              type uint8 {
                range 1..255 ;
              }
              default 110 ;
            }
            leaf static-remote-lfa {
              description 'Configure static remote lfa priority for ospf'
                          ;
              type uint8 {
                range 1..255 ;
              }
              default 110 ;
            }
            leaf ti-lfa {
              // if-feature ti-lfa ;
              description 'Configure ti-lfa priority for ospf.'
                          ;
              type uint8 ;
              default 110 ;
              ncd:revise-date 2018-05-23 ;
            }
            ncd:revise-date 2015-09-10 ;
          }
          container microloop-prevention {
            description 'Configure microloop prevention priority for ospf'
                        ;
            container remote-lfa {
              description 'Configure microloop prevention priority for ospf rem'
                        + 'ote lfa'
                          ;
              leaf capability {
                description 'Enable ospf microloop prevention'
                            ;
                type enumeration {
                  enum enable {
                    value 1 ;
                    description Enable ;
                  }
                  enum disable {
                    value 2 ;
                    description Disable ;
                  }
                }
                default enable ;
              }
              leaf delay-time {
                description 'Delay time for microloop prevention in milliseconds'
                            ;
                type uint32 {
                  range 1..300000 {
                    description 'delay time'
                                ;
                  }
                }
                units millisecond ;
                default 3000 ;
              }
            }
            container segment-routing {
              // if-feature segment-routing ;
              description 'Configure microloop prevention priority for segment-'
                        + 'routing'
                          ;
              container mpls {
                description 'Configure microloop prevention priority for segmen'
                          + 't-routing mpls'
                            ;
                leaf capability {
                  description 'Enable ospf microloop prevention'
                              ;
                  type enumeration {
                    enum enable {
                      value 1 ;
                      description Enable ;
                    }
                    enum disable {
                      value 2 ;
                      description Disable ;
                    }
                  }
                  default disable ;
                }
                leaf delay-time {
                  description 'Delay time for microloop prevention in milliseco'
                            + 'nds'
                              ;
                  type uint32 {
                    range 1..300000 {
                      description 'delay time'
                                  ;
                    }
                  }
                  units millisecond ;
                  default 3000 ;
                }
              }
              ncd:revise-date 2019-08-07 ;
            }
            ncd:revise-date 2016-09-20 ;
          }
          container bgp-ls {
            description 'Distribute link-state data using BGP.'
                        ;
            presence bgp-ls ;
            leaf instance-id {
              description 'Link-state data instance identifier.'
                          ;
              type uint32 {
                range 0..65535 ;
              }
              default 0 ;
            }
            ncd:revise-date 2017-02-27 ;
          }
          container segment-routing {
            // if-feature segment-routing ;
            description 'Configure segment-routing parameters'
                        ;
            container mpls {
              description 'Configure segment-routing mpls parameters'
                          ;
              leaf capability {
                description 'Configure segment-routing mpls capability'
                            ;
                type enumeration {
                  enum enable {
                    value 1 ;
                    description Enable ;
                  }
                  enum disable {
                    value 2 ;
                    description Disable ;
                  }
                }
                default disable ;
              }
              container adj-sid {
                description 'Set segment routing MPLS adj-sid type.'
                            ;
                leaf type {
                  description 'Configure segment routing MPLS adj-sid type.'
                              ;
                  type enumeration {
                    enum hybrid {
                      value 1 ;
                      description hybrid ;
                    }
                    enum static {
                      value 2 ;
                      description static ;
                    }
                  }
                  default hybrid ;
                }
                ncd:revise-date 2020-03-27 ;
              }
              container entropy-label {
                description 'Configure segment routing mpls entropy label.'
                            ;
                leaf capability {
                  description 'Configure segment routing mpls entropy label.'
                              ;
                  type enumeration {
                    enum enable {
                      value 1 ;
                      description Enable ;
                    }
                    enum disable {
                      value 2 ;
                      description Disable ;
                    }
                  }
                  default disable ;
                }
                ncd:revise-date 2019-11-12 ;
              }
            }
            ncd:revise-date 2018-03-06 ;
          }
          container ti-lfa {
            // if-feature ti-lfa ;
            description 'Configure TI-LFA for ospf.'
                        ;
            leaf capability {
              description 'Configure TI-LFA capability for ospf.'
                          ;
              type enumeration {
                enum enable {
                  value 1 ;
                  description 'Enable TI-LFA.'
                              ;
                }
                enum disable {
                  value 2 ;
                  description 'Disable TI-LFA.'
                              ;
                }
              }
              default disable ;
            }
            choice protection-type {
              description 'Specify TI-LFA protection type.'
                          ;
              case node-protecting {
                description 'Specify TI-LFA protection type.'
                            ;
                leaf node-protecting {
                  description 'Specify TI-LFA note protection.'
                              ;
                  type enumeration {
                    enum node-protecting {
                      value 1 ;
                      description 'TI-LFA node protection'
                                  ;
                    }
                  }
                }
              }
              case node-protecting-choice-clear {
                description 'Remove value of any entities which belong to any c'
                          + 'ase within this choice.'
                            ;
                container node-protecting-all-clear {
                  description 'Remove this entitiy means to remove value of any'
                            + ' entities which belong to any case within this c'
                            + 'hoice.'
                              ;
                  presence node-protecting-all-clear ;
                }
                ncd:revise-date 2020-08-25 ;
              }
              ncd:revise-date 2019-08-21 ;
            }
            ncd:revise-date 2018-05-23 ;
          }
          container distance-policy {
            // if-feature distance-policy ;
            description 'Distance policy.'
                        ;
            leaf policy-type {
              description 'The type of policy.'
                          ;
              type enumeration {
                enum route-policy {
                  value 1 ;
                  description 'route-type is route-policy.'
                              ;
                }
                enum route-map {
                  value 2 ;
                  description 'route-type is route-map.'
                              ;
                }
              }
            }
            leaf policy-name {
              description 'Name of policy,characters from 1 to 200.'
                          ;
              type string {
                length 1..200 {
                  description 'Name of policy,characters from 1 to 200.'
                              ;
                }
              }
            }
            ncd:revise-date 2018-11-28 ;
          }
          container suppress-flapping {
            description 'Suppress flapping.'
                        ;
            container adjacency {
              description 'Suppress flapping for adjacency.'
                          ;
              leaf capability {
                description 'Capability of suppress flapping for adjacency.'
                            ;
                type enumeration {
                  enum enable {
                    value 1 ;
                    description 'Enable suppress flapping.'
                                ;
                  }
                  enum disable {
                    value 2 ;
                    description 'Disable suppress flapping.'
                                ;
                  }
                }
                default enable ;
              }
            }
            ncd:revise-date 2020-07-23 ;
          }
          container flex-algorithms {
            description 'Configure Flex-Algorithms'
                        ;
            list flex-algorithm {
              description 'Configure Flex-Algorithms'
                          ;
              key number ;
              leaf number {
                description 'Flex-algos number'
                            ;
                type uint8 {
                  range 128..255 ;
                }
              }
            }
            ncd:revise-date 2020-10-22 ;
          }
        }
      }
    }
  }
  container state {
    config false ;
    description 'State of OSPFv2.'
                ;
    container ospfv2 {
      description 'State of OSPFv2.'
                  ;
      container processes {
        description 'OSPFv2 process.'
                    ;
        list process {
          description 'OSPFv2 process.'
                      ;
          key process-id ;
          leaf process-id {
            description 'Ospf process ID.'
                        ;
            type uint32 {
              range 1..65535 ;
            }
          }
          leaf router-id {
            description 'Ospf router id.'
                        ;
            type ncd:ipv4-address ;
          }
          leaf vrf-name {
            description 'Vrf name.'
                        ;
            type string {
              length 1..32 ;
            }
          }
          leaf state {
            description 'Process state.'
                        ;
            type enumeration {
              enum enable {
                value 1 ;
              }
              enum disable {
                value 2 ;
              }
              enum restarting-for-lsa-limit {
                value 3 ;
              }
              enum disabling {
                value 4 ;
              }
            }
          }
          leaf domain-id-type {
            description 'Domain ID type.'
                        ;
            type uint8 ;
          }
          leaf domain-id {
            description 'Domain ID.'
                        ;
            type ncd:ipv4-address ;
          }
          leaf enable-time {
            description 'Process enable time.'
                        ;
            type string ;
          }
          leaf interface-count {
            description 'Interface count of the process.'
                        ;
            type uint32;
            //type uint32 {
            //  range 0..4294967295 ;
            //}
          }
          leaf neighbor-count {
            description 'Neighbor count of the process.'
                        ;
            type uint32;
            //type uint32 {
            //  range 0..4294967295 ;
            //}
          }
          leaf full-neighbor-count {
            description 'Full neighbor count of the process.'
                        ;
            type uint32;
            //type uint32 {
            //  range 0..4294967295 ;
            //}
          }
          leaf virtual-link-count {
            description 'Virtual link count of the process.'
                        ;
            type uint32;
            //type uint32 {
            //  range 0..4294967295 ;
            //}
          }
          leaf ttl-security-state {
            description 'TTL security check state.'
                        ;
            type enumeration {
              enum enable {
                value 1 ;
                description 'TTL security enable.'
                            ;
              }
              enum disable {
                value 2 ;
                description 'TTL security disable.'
                            ;
              }
            }
          }
          leaf ttl-security-hops {
            description 'TTL security check hops.'
                        ;
            type uint8 {
              range 1..254 ;
            }
          }
          container area-count {
            description 'Area count.'
                        ;
            leaf total-count {
              description 'Total area count.'
                          ;
              type uint32;
              //type uint32 {
              //  range 0..4294967295 ;
              //}
            }
            leaf normal-count {
              description 'Normal area count.'
                          ;
              type uint32;
              //type uint32 {
              //  range 0..4294967295 ;
              //}
            }
            leaf stub-count {
              description 'STUB area count.'
                          ;
              type uint32;
              //type uint32 {
              //  range 0..4294967295 ;
              //}
            }
            leaf nssa-count {
              description 'NSSA area count.'
                          ;
              type uint32;
              //type uint32 {
              //  range 0..4294967295 ;
              //}
            }
          }
          container lsa-count {
            description 'LSA count.'
                        ;
            leaf total-count {
              description 'Total LSA count.'
                          ;
              type uint32;
              //type uint32 {
              //  range 0..4294967295 ;
              //}
            }
            leaf ase-count {
              description 'Ase LSA count.'
                          ;
              type uint32;
              //type uint32 {
              //  range 0..4294967295 ;
              //}
            }
            leaf gr-count {
              description 'Gr LSA count.'
                          ;
              type uint32;
              //type uint32 {
              //  range 0..4294967295 ;
              //}
            }
            leaf received-new-count {
              description 'Received new LSA count.Not only include the LSAs in '
                        + 'current LSDB,but also include the LSAs that had been'
                        + ' flushed previously.'
                          ;
              type uint32;
              //type uint32 {
              //  range 0..4294967295 ;
              //}
            }
            leaf self-originated-count {
              description 'Self-originated LSA count.Not only include the LSAs '
                        + 'in current LSDB,but also include the LSAs that had b'
                        + 'een flushed previously.'
                          ;
              type uint32;
              //type uint32 {
              //  range 0..4294967295 ;
              //}
            }
            leaf non-self-originated-count {
              description 'non-self-originated LSA count.Not only include the L'
                        + 'SAs in current LSDB,but also include the LSAs that h'
                        + 'ad been flushed previously.'
                          ;
              type uint32;
              //type uint32 {
              //  range 0..4294967295 ;
              //}
            }
          }
          container lsa-limit {
            description 'Limit number of non-self originated LSAs that Ospf pro'
                      + 'cess can receive.'
                        ;
            leaf max-lsa-count {
              description 'Max number of non self-generated LSAs can receive.'
                          ;
              type uint32;
              //type uint32 {
              //  range 0..4294967295 ;
              //}
            }
            leaf current-lsa-count {
              description 'Current number of non self-generated LSAs can receiv'
                        + 'e.'
                          ;
              type uint32;
              //type uint32 {
              //  range 0..4294967294 ;
              //}
            }
            leaf warning-threshold {
              description 'Threshold value(%) at which to give a warning'
                          ;
              type uint8 {
                range 1..100 ;
              }
              units percent ;
            }
            leaf only-send-warning {
              description 'Only give a warning when threshold is exceeded.'
                          ;
              type empty ;
            }
            leaf limit-time {
              description 'Time during which limit-state continue.'
                          ;
              type uint32 {
                range 1..65535 ;
              }
              units minute ;
            }
            leaf refresh-time {
              description 'Mins after which limit-count can be refreshed.'
                          ;
              type uint32 {
                range 1..65535 ;
              }
              units minute ;
            }
            leaf limit-count {
              description 'Maximum times OSPF can enter limit-state.'
                          ;
              type uint32 {
                range 1..65535 ;
              }
            }
            leaf current-limit-count {
              description 'Current times OSPF can enter limit-state.'
                          ;
              type uint32 {
                range 0..65535 ;
              }
            }
            leaf permanently-ignore-all-neighbors {
              description 'Permanently ignoring all neighbors for lsa limit.'
                          ;
              type empty ;
            }
            container time-remaining {
              description 'Time remaining.'
                          ;
              leaf enter-limit-state {
                description 'Time remaining to enter limit state.'
                            ;
                type string ;
              }
              leaf refresh-limit-count {
                description 'Time remaining to refresh limit count.'
                            ;
                type string ;
              }
              leaf ignore-all-neighbors {
                description 'Time remaining to ignore all neighbors.'
                            ;
                type string ;
              }
            }
          }
          container nsf {
            description 'Non stop forwarding.'
                        ;
            leaf state {
              description 'NSF state.'
                          ;
              type enumeration {
                enum enable {
                  value 1 ;
                  description 'NSF enable.'
                              ;
                }
                enum disable {
                  value 2 ;
                  description 'NSF disable.'
                              ;
                }
              }
            }
            leaf last-nsf-restart-time {
              description 'Last nsf restart happened how long ago.'
                          ;
              type string ;
            }
            leaf last-nsf-restart-use-time {
              description 'Last nsf restart use time.'
                          ;
              type uint32 {
                range 0..1800 ;
              }
              units second ;
            }
          }
          container max-metric {
            description 'Maximum metric of router LSA.'
                        ;
            leaf take-effect-time {
              description 'The time at which max-metric router LSA took effect.'
                          ;
              type string ;
            }
            leaf disable-time {
              description 'The time at which max-metric router LSA disable.'
                          ;
              type string ;
            }
            leaf originate-router-lsas-with-max-metric {
              description 'Originate router LSAs with max metric.'
                          ;
              type empty ;
            }
            leaf time-remaining {
              description 'time remaining for originating router LSAs with maxi'
                        + 'mum metric.'
                          ;
              type string ;
            }
            leaf state {
              description 'Max metric state.'
                          ;
              type enumeration {
                enum active {
                  value 1 ;
                  description 'max-metric state is active.'
                              ;
                }
                enum inactive {
                  value 2 ;
                  description 'max-metric state is inactive.'
                              ;
                }
              }
            }
            container condition {
              description 'Condition of originating router LSAs with maximum me'
                        + 'tric.'
                          ;
              choice condition {
                description 'Condition of originating router LSAs with maximum '
                          + 'metric.'
                            ;
                case always {
                  description Always. ;
                  leaf always {
                    description Always. ;
                    type empty ;
                  }
                }
                case on-startup-wait-for-bgp {
                  description 'On startup while BGP is converging.'
                              ;
                  leaf on-startup-wait-for-bgp {
                    description 'On startup while BGP is converging.'
                                ;
                    type empty ;
                  }
                }
                case on-startup-wait-for-timeout {
                  description 'On startup for a time.'
                              ;
                  leaf on-startup-wait-for-timeout {
                    description 'On startup for a time.'
                                ;
                    type empty ;
                  }
                  leaf timeout {
                    description 'The time after startup to originate max metric'
                              + ' router LSA.'
                                ;
                    type uint32 {
                      range 5..86400 ;
                    }
                    units second ;
                  }
                }
              }
            }
          }
          container areas {
            description Area. ;
            list area {
              description Area. ;
              key area-id ;
              leaf area-id {
                description 'Area ID.'
                            ;
                type ncd:ipv4-address ;
              }
              leaf state {
                description 'Area state.'
                            ;
                type enumeration {
                  enum enable {
                    value 1 ;
                    description 'area is enable.'
                                ;
                  }
                  enum disable {
                    value 2 ;
                    description 'area is disable.'
                                ;
                  }
                }
              }
              leaf demand-circuit-available {
                description 'Demand circuit available.'
                            ;
                type empty ;
              }
              leaf enable-time {
                description 'Area enable time.'
                            ;
                type string ;
              }
              leaf area-type {
                description 'Area type.'
                            ;
                type enumeration {
                  enum stub {
                    value 1 ;
                    description 'Stub area.'
                                ;
                  }
                  enum nssa {
                    value 2 ;
                    description 'Nssa area.'
                                ;
                  }
                  enum normal {
                    value 3 ;
                    description 'Normal area.'
                                ;
                  }
                }
              }
              leaf stub-no-summary {
                description 'Do not send summary LSA into stub area.'
                            ;
                type empty ;
              }
              leaf stub-default-cost {
                description 'Default cost of stub area.'
                            ;
                type uint32 {
                  range 1..65535 ;
                }
              }
              leaf nssa-default-metric {
                description 'Default metric of nssa area.'
                            ;
                type uint32 {
                  range 1..16777214 ;
                }
              }
              leaf authentication-type {
                description 'Authentication type.'
                            ;
                type enumeration {
                  enum null {
                    value 1 ;
                    description 'No authentication.'
                                ;
                  }
                  enum simple-password {
                    value 2 ;
                    description 'Simple password authentication.'
                                ;
                  }
                  enum message-digest {
                    value 3 ;
                    description 'Message-digest authentication.'
                                ;
                  }
                  enum keychain {
                    value 4 ;
                    description 'Keychain authentication.'
                                ;
                  }
                }
              }
              container sending-sa {
                description 'Sending SA.'
                            ;
                leaf authen-keyid {
                  description 'Authentication keyid.'
                              ;
                  type uint8 {
                    range 0..255 {
                      description 'Authentication keyid, from 0 to 255'
                                  ;
                    }
                  }
                }
                leaf authen-algorithm {
                  description 'Authentication algorithm.'
                              ;
                  type enumeration {
                    enum md5 {
                      value 1 ;
                      description 'Authentication algorithm is md5.'
                                  ;
                    }
                    enum hmac-md5 {
                      value 2 ;
                      description 'Authentication algorithm is hmac-md5.'
                                  ;
                    }
                    enum sm3 {
                      value 3 ;
                      description 'Authentication algorithm is sm3.'
                                  ;
                    }
                    enum hmac-sm3 {
                      value 4 ;
                      description 'Authentication algorithm is hmac-sm3.'
                                  ;
                    }
                    enum sha256 {
                      value 5 ;
                      description 'Authentication algorithm is sha256.'
                                  ;
                    }
                    enum hmac-sha256 {
                      value 6 ;
                      description 'Authentication algorithm is hmac-sha256.'
                                  ;
                    }
                    enum sha1 {
                      value 7 ;
                      description 'Authentication algorithm is sha1.'
                                  ;
                    }
                    enum hmac-sha1-12 {
                      value 8 ;
                      description 'Authentication algorithm is hmac-sha1-12.'
                                  ;
                    }
                    enum hmac-sha1-20 {
                      value 9 ;
                      description 'Authentication algorithm is hmac-sha1-20.'
                                  ;
                    }
                  }
                }
                leaf authen-keychain {
                  description 'Authentication keychain.'
                              ;
                  type string {
                    length 1..31 {
                      description 'Name of keychain,characters from 1 to 31'
                                  ;
                    }
                  }
                }
                ncd:revise-date 2016-01-18 ;
              }
              leaf spf-calculation-times {
                description 'SPF calculation times.'
                            ;
                type uint32;
                //type uint32 {
                //  range 0..4294967295 ;
                //}
              }
              leaf ispf-calculation-times {
                description 'ISPF calculation times.'
                            ;
                type uint32;
                //type uint32 {
                //  range 0..4294967295 ;
                //}
              }
              leaf interface-count {
                description 'Interface count of the area.'
                            ;
                type uint32;
                //type uint32 {
                //  range 0..4294967295 ;
                //}
              }
              leaf up-interface-count {
                description 'Up interface count of the area.'
                            ;
                type uint32;
                //type uint32 {
                //  range 0..4294967295 ;
                //}
              }
              leaf intra-inter-lsa-count {
                description 'Intra/inter LSA count of the area.'
                            ;
                type uint32;
                //type uint32 {
                //  range 0..4294967295 ;
                //}
              }
              leaf area-filter-out {
                description 'Policy name that filter networks sent from this ar'
                          + 'ea.'
                            ;
                type string {
                  length 1..32 ;
                }
              }
              leaf area-filter-in {
                description 'Policy name that filter networks sent to this area.'
                            ;
                type string ;
              }
              leaf summary-range-count {
                description 'Summary range count.'
                            ;
                type uint32;
                //type uint32 {
                //  range 0..4294967295 ;
                //}
              }
              container summary-ranges {
                description 'Summary range of the area.'
                            ;
                list summary-range {
                  description 'Summary range of the area.'
                              ;
                  key 'ip-address subnet-mask'
                      ;
                  leaf ip-address {
                    description 'IP address of the range.'
                                ;
                    type ncd:ipv4-address ;
                  }
                  leaf subnet-mask {
                    description 'Subnet mask of the range.'
                                ;
                    type ncd:ipv4-mask ;
                  }
                  leaf advertise-state {
                    description 'Advertise state of the range.'
                                ;
                    type enumeration {
                      enum advertise {
                        value 1 ;
                      }
                      enum not-advertise {
                        value 2 ;
                      }
                    }
                  }
                  ncd:select 'ip-address subnet-mask'
                             ;
                }
              }
            }
          }
          ncd:select process-id ;
        }
      }
      container interfaces {
        description 'OSPFv2 interfaces.'
                    ;
        container normal-interfaces {
          description 'OSPFv2 interface.'
                      ;
          list normal-interface {
            description 'OSPFv2 interface.'
                        ;
            key 'process-id area-id interface-name'
                ;
            leaf process-id {
              description 'OSPF process ID.'
                          ;
              type uint32 {
                range 1..65535 {
                  description 'Ospf process ID from 1 to 65535'
                              ;
                }
              }
            }
            leaf area-id {
              description 'Area ID.'
                          ;
              type ncd:ipv4-address;
              //type ncd:ipv4-address {
              //  length 0..4294967295 ;
              //}
            }
            leaf interface-name {
              description 'Interface name.'
                          ;
              type ncd:ifname {
                length 1..31 {
                  description 'Interface name'
                              ;
                }
              }
            }
            leaf admin-state {
              description 'Admin state.'
                          ;
              type enumeration {
                enum down {
                  value 0 ;
                  description 'Admin state is down.'
                              ;
                }
                enum up {
                  value 1 ;
                  description 'Admin state is up.'
                              ;
                }
              }
            }
            leaf protocol-state {
              description 'Protocol state of the interface.'
                          ;
              type enumeration {
                enum disable {
                  value 0 ;
                  description 'Protocol state is disable.'
                              ;
                }
                enum enable-SD-down {
                  value 1 ;
                  description 'Protocol state is enable-SD-down.'
                              ;
                }
                enum enable {
                  value 2 ;
                  description 'Protocol state is enable.'
                              ;
                }
              }
            }
            leaf track-state {
              description 'Track state.'
                          ;
              type enumeration {
                enum down {
                  value 0 ;
                  description 'Track state is down.'
                              ;
                }
                enum up {
                  value 1 ;
                  description 'Track state is up.'
                              ;
                }
                enum unknown {
                  value 2 ;
                  description 'Track state is unknown.'
                              ;
                }
              }
            }
            leaf ip-address {
              description 'IP address of the interface.'
                          ;
              type ncd:ipv4-address ;
            }
            leaf ip-mask {
              description 'IP mask of the interface.'
                          ;
              type ncd:ipv4-mask ;
            }
            leaf up-time {
              description 'Up time of the interface.'
                          ;
              type string {
                length 1..15 {
                  description 'Up time of the interface'
                              ;
                }
              }
            }
            leaf demand-circuit {
              description 'Demand circuit.'
                          ;
              type empty ;
            }
            leaf suppress-hello {
              description 'Suppress hello.'
                          ;
              type empty ;
            }
            leaf interface-state {
              description 'Interface state.'
                          ;
              type enumeration {
                enum Down {
                  value 0 ;
                  description 'Down state.'
                              ;
                }
                enum Loopback {
                  value 1 ;
                  description 'Loopback state.'
                              ;
                }
                enum Waiting {
                  value 2 ;
                  description 'Waiting state.'
                              ;
                }
                enum Point-to-point {
                  value 3 ;
                  description 'Point-to-point state.'
                              ;
                }
                enum DR {
                  value 4 ;
                  description 'DR state.'
                              ;
                }
                enum Backup {
                  value 5 ;
                  description 'Backup state.'
                              ;
                }
                enum DROther {
                  value 6 ;
                  description 'DROther state.'
                              ;
                }
              }
            }
            leaf cost {
              description 'Cost value of the interface.'
                          ;
              type uint32 {
                range 0..65535 {
                  description 'Interface cost'
                              ;
                }
              }
            }
            leaf priority {
              description 'Interface priority.'
                          ;
              type uint32 {
                range 0..255 {
                  description 'Router priority'
                              ;
                }
              }
            }
            leaf network-type {
              description 'Network type of the interface.'
                          ;
              type enumeration {
                enum Broadcast {
                  value 1 ;
                  description 'Network type is Broadcast.'
                              ;
                }
                enum Nbma {
                  value 2 ;
                  description 'Network type is Nbma.'
                              ;
                }
                enum Point-to-point {
                  value 3 ;
                  description 'Network type is Point-to-point.'
                              ;
                }
                enum Point-to-multipoint {
                  value 4 ;
                  description 'Network type is Point-to-multipoint.'
                              ;
                }
                enum P-to-mp-nb {
                  value 5 ;
                  description 'Network type is P-to-mp-nb.'
                              ;
                }
                enum Loopback {
                  value 7 ;
                  description 'Network type is Loopback.'
                              ;
                }
              }
            }
            leaf transmit-delay {
              description 'Link state transmit delay.'
                          ;
              type uint32 {
                range 1..65535 {
                  description 'Link state transmit delay,Seconds'
                              ;
                }
              }
              units second ;
            }
            leaf authentication-type {
              description 'Authentication Type.'
                          ;
              type enumeration {
                enum null {
                  value 0 ;
                  description 'Authentication type is null.'
                              ;
                }
                enum simple-password {
                  value 1 ;
                  description 'Authentication type is simple-password.'
                              ;
                }
                enum message-digest {
                  value 2 ;
                  description 'Authentication type is message-digest.'
                              ;
                }
                enum keychain {
                  value 3 ;
                  description 'Authentication type is keychain.'
                              ;
                }
              }
            }
            container sending-sa {
              leaf authen-keyid {
                description 'Authentication keyid.'
                            ;
                type uint8 {
                  range 0..255 {
                    description 'Authentication keyid, from 0 to 255'
                                ;
                  }
                }
              }
              leaf authen-algorithm {
                description 'Authentication algorithm.'
                            ;
                type enumeration {
                  enum md5 {
                    value 1 ;
                    description 'Authentication algorithm is md5.'
                                ;
                  }
                  enum hmac-md5 {
                    value 2 ;
                    description 'Authentication algorithm is hmac-md5.'
                                ;
                  }
                  enum sm3 {
                    value 3 ;
                    description 'Authentication algorithm is sm3.'
                                ;
                  }
                  enum hmac-sm3 {
                    value 4 ;
                    description 'Authentication algorithm is hmac-sm3.'
                                ;
                  }
                  enum sha256 {
                    value 5 ;
                    description 'Authentication algorithm is sha256.'
                                ;
                  }
                  enum hmac-sha256 {
                    value 6 ;
                    description 'Authentication algorithm is hmac-sha256.'
                                ;
                  }
                  enum sha1 {
                    value 7 ;
                    description 'Authentication algorithm is sha1.'
                                ;
                  }
                  enum hmac-sha1-12 {
                    value 8 ;
                    description 'Authentication algorithm is hmac-sha1-12.'
                                ;
                  }
                  enum hmac-sha1-20 {
                    value 9 ;
                    description 'Authentication algorithm is hmac-sha1-20.'
                                ;
                  }
                }
              }
              leaf authen-keychain {
                description 'Authentication keychain.'
                            ;
                type string {
                  length 1..31 {
                    description 'Name of keychain,characters from 1 to 31'
                                ;
                  }
                }
              }
              ncd:revise-date 2016-01-18 ;
            }
            leaf ttl-security-state {
              description 'OSPF ttl-security.'
                          ;
              type enumeration {
                enum disable {
                  value 0 ;
                  description 'TTL security disable.'
                              ;
                }
                enum enable {
                  value 1 ;
                  description 'TTL security enable.'
                              ;
                }
              }
              units hop ;
            }
            leaf ttl-security-hops {
              description 'OSPF ttl-security hop count.'
                          ;
              type uint8 {
                range 1..254 {
                  description 'Ttl-security hops'
                              ;
                }
              }
            }
            leaf ldp-sync {
              description 'MPLS LDP IGP sync.'
                          ;
              type enumeration {
                enum disable {
                  value 0 ;
                  description 'LDP sync disable.'
                              ;
                }
                enum enable {
                  value 1 ;
                  description 'LDP sync enable.'
                              ;
                }
              }
            }
            leaf ldp-sync-state {
              description 'LDP sync of the interface.'
                          ;
              type enumeration {
                enum unachieve {
                  value 0 ;
                  description 'The LDP sync-state is unachieved.'
                              ;
                }
                enum achieve {
                  value 1 ;
                  description 'The LDP sync-state is achieved.'
                              ;
                }
                enum unknown {
                  value 2 ;
                  description 'The LDP sync-state is unknown.'
                              ;
                }
              }
            }
            leaf ldp-autoconfig {
              description 'MPLS LDP IGP autoconfig function.'
                          ;
              type enumeration {
                enum disable {
                  value 0 ;
                  description 'LDP autoconfig disable.'
                              ;
                }
                enum enable {
                  value 1 ;
                  description 'LDP autoconfig enable.'
                              ;
                }
              }
            }
            leaf ldp-link-state {
              description 'LDP link state.'
                          ;
              type enumeration {
                enum send-normal-metric {
                  value 0 ;
                  description 'Router lsa link state is sending normal metric.'
                              ;
                }
                enum send-max-metric {
                  value 1 ;
                  description 'Router lsa link state is sending max metric.'
                              ;
                }
                enum unreachable {
                  value 2 ;
                  description 'Router lsa link state is unreachable.'
                              ;
                }
              }
              ncd:revise-date 2015-12-24 ;
            }
            leaf no-cut-edge {
              description 'There is alternate path for the directly connected n'
                        + 'etwork.'
                          ;
              type empty ;
              ncd:revise-date 2015-12-24 ;
            }
            leaf sd-status {
              description 'SD status.'
                          ;
              type enumeration {
                enum appear {
                  value 1 ;
                  description 'SD status appears.'
                              ;
                }
                enum disappear {
                  value 2 ;
                  description 'SD status disappears.'
                              ;
                }
              }
              ncd:revise-date 2015-06-01 ;
            }
            leaf cost-link-sd {
              description 'The cost for interface in sd status'
                          ;
              type uint16 ;
              ncd:revise-date 2015-06-01 ;
            }
            leaf damp-state {
              description 'Link damp state of the interface.'
                          ;
              type enumeration {
                enum inactive {
                  value 0 ;
                  description 'Link Damp state of this interface is inactive.'
                              ;
                }
                enum active {
                  value 1 ;
                  description 'Link Damp state of this interface is active.'
                              ;
                }
              }
              ncd:revise-date 2017-04-05 ;
            }
            leaf damp-remain {
              description 'Link damp remaining time.'
                          ;
              type uint32 {
                range 0..3600000 {
                  description 'Link damp remaining time.'
                              ;
                }
              }
              ncd:revise-date 2017-04-05 ;
            }
            leaf hello-interval {
              description 'Time between hello packets.'
                          ;
              type uint32 {
                range 1..65535 {
                  description 'Time between hello packets,Seconds'
                              ;
                }
              }
              units second ;
            }
            leaf dead-interval {
              description 'Interval after which a neighbor is declared dead.'
                          ;
              type uint32 {
                range 1..65535 {
                  description 'Interval after which a neighbor is declared dead'
                            + ',Seconds'
                              ;
                }
              }
              units second ;
            }
            leaf retransmit-interval {
              description 'Time between retransmitting lost link state advertis'
                        + 'ements.'
                          ;
              type uint32 {
                range 1..65535 {
                  description 'Time between retransmitting lost link state adve'
                            + 'rtisements,Seconds'
                              ;
                }
              }
              units second ;
            }
            leaf dr {
              description 'Designated Router.'
                          ;
              type ncd:ipv4-address ;
            }
            leaf dr-ip-address {
              description 'IP address of Designated Router.'
                          ;
              type ncd:ipv4-address ;
            }
            leaf bdr {
              description 'Backup Designated Router.'
                          ;
              type ncd:ipv4-address ;
            }
            leaf bdr-ip-address {
              description 'IP address of Backup Designated Router.'
                          ;
              type ncd:ipv4-address ;
            }
            leaf neighbor-count {
              description 'Neighbor count.'
                          ;
              type uint32 {
                range 0..65536 ;
              }
            }
            leaf full-neighbor-count {
              description 'Number of full neighbors.'
                          ;
              type uint32 {
                range 0..65536 ;
              }
            }
            container neighbors {
              description 'OSPF neighbor.'
                          ;
              list neighbor {
                description 'OSPF neighbor.'
                            ;
                key neighbor-id ;
                leaf neighbor-id {
                  description 'The router-id of neighbor route.'
                              ;
                  type ncd:ipv4-address ;
                }
                leaf neighbor-role {
                  description 'The role of neighbor route.'
                              ;
                  type enumeration {
                    enum DR {
                      value 1 ;
                      description 'The role of the neighbor is DR.'
                                  ;
                    }
                    enum Backup {
                      value 2 ;
                      description 'The role of the neighbor is Backup.'
                                  ;
                    }
                    enum DROther {
                      value 3 ;
                      description 'The role of the neighbor is DROther.'
                                  ;
                    }
                  }
                }
              }
            }
            ncd:select process-id ;
            ncd:select interface-name ;
            ncd:select 'process-id interface-name'
                       ;
          }
        }
        container virtual-interfaces {
          description 'OSPFv2 virtual-links.'
                      ;
          list virtual-interface {
            description 'OSPFv2 virtual-link.'
                        ;
            key 'process-id transmit-area-id neighbor-id'
                ;
            leaf process-id {
              description 'Ospf process ID.'
                          ;
              type uint32 {
                range 1..65535 {
                  description 'Ospf process ID.'
                              ;
                }
              }
            }
            leaf transmit-area-id {
              description 'Transmit area ID of virtual-link.'
                          ;
              type ncd:ipv4-address ;
            }
            leaf neighbor-id {
              description 'ID associated with virtual link neighbor.'
                          ;
              type ncd:ipv4-address ;
            }
            leaf state {
              description 'State of virtual-link.'
                          ;
              type enumeration {
                enum down {
                  value 0 ;
                  description 'The virtual-link is down.'
                              ;
                }
                enum up {
                  value 1 ;
                  description 'The virtual-link is up.'
                              ;
                }
              }
            }
            leaf up-time {
              description 'Up time of interface.'
                          ;
              type string {
                length 1..15 ;
              }
            }
            leaf demand-circuit {
              description 'Interface is demand circuit.'
                          ;
              type empty ;
            }
            leaf suppress-hello {
              description 'Interface suppress hello sending.'
                          ;
              type empty ;
            }
            leaf out-interface-name {
              description 'The out interface name of virtual-link.'
                          ;
              type ncd:ifname {
                length 1..31 {
                  description 'The string length of interface is from 1 to 31.'
                              ;
                }
              }
            }
            leaf out-interface-ip-address {
              description 'The out ip address of virtual-link.'
                          ;
              type ncd:ipv4-address ;
            }
            leaf interface-state {
              description 'State machine of interface.'
                          ;
              type enumeration {
                enum Down {
                  value 0 ;
                  description 'This is the initial interface state.'
                              ;
                }
                enum Point-to-point {
                  value 3 ;
                  description 'In this state, the interface is operational, and'
                            + ' connects either to a physical point-to-point ne'
                            + 'twork or to a virtual link.'
                              ;
                }
              }
            }
            leaf transit-delay {
              description 'Link transmit delay,Seconds'
                          ;
              type uint32 {
                range 1..8192 {
                  description 'Link transmit delay,Seconds'
                              ;
                }
              }
              units second ;
            }
            leaf cost {
              description 'Interface cost.'
                          ;
              type uint32 {
                range 1..65535 {
                  description 'Interface cost.'
                              ;
                }
              }
            }
            leaf authentication-type {
              description 'Authentication type.'
                          ;
              type enumeration {
                enum null {
                  value 0 ;
                  description 'No authentication.'
                              ;
                }
                enum simple-password {
                  value 1 ;
                  description 'Simple password authentication.'
                              ;
                }
                enum message-digest {
                  value 2 ;
                  description 'Message-digest authentication.'
                              ;
                }
                enum keychain {
                  value 3 ;
                  description 'Keychain authentication.'
                              ;
                }
              }
            }
            container sending-sa {
              leaf authen-keyid {
                description 'Authentication keyid.'
                            ;
                type uint8 {
                  range 0..255 {
                    description 'Authentication keyid, from 0 to 255'
                                ;
                  }
                }
              }
              leaf authen-algorithm {
                description 'Authentication algorithm.'
                            ;
                type enumeration {
                  enum md5 {
                    value 1 ;
                    description 'Authentication algorithm is md5.'
                                ;
                  }
                  enum hmac-md5 {
                    value 2 ;
                    description 'Authentication algorithm is hmac-md5.'
                                ;
                  }
                  enum sm3 {
                    value 3 ;
                    description 'Authentication algorithm is sm3.'
                                ;
                  }
                  enum hmac-sm3 {
                    value 4 ;
                    description 'Authentication algorithm is hmac-sm3.'
                                ;
                  }
                  enum sha256 {
                    value 5 ;
                    description 'Authentication algorithm is sha256.'
                                ;
                  }
                  enum hmac-sha256 {
                    value 6 ;
                    description 'Authentication algorithm is hmac-sha256.'
                                ;
                  }
                  enum sha1 {
                    value 7 ;
                    description 'Authentication algorithm is sha1.'
                                ;
                  }
                  enum hmac-sha1-12 {
                    value 8 ;
                    description 'Authentication algorithm is hmac-sha1-12.'
                                ;
                  }
                  enum hmac-sha1-20 {
                    value 9 ;
                    description 'Authentication algorithm is hmac-sha1-20.'
                                ;
                  }
                }
              }
              leaf authen-keychain {
                description 'Authentication keychain.'
                            ;
                type string {
                  length 1..31 {
                    description 'Name of keychain,characters from 1 to 31'
                                ;
                  }
                }
              }
              ncd:revise-date 2016-01-18 ;
            }
            leaf hello-interval {
              description 'Time between hello packets,seconds'
                          ;
              type uint32 {
                range 1..8192 {
                  description 'Time between hello packets,seconds.'
                              ;
                }
              }
              units second ;
            }
            leaf dead-interval {
              description 'Interval after which a neighbor is declared dead,Sec'
                        + 'onds.'
                          ;
              type uint32 {
                range 1..8192 {
                  description 'Interval after which a neighbor is declared dead'
                            + ',Seconds.'
                              ;
                }
              }
              units second ;
            }
            leaf retransmit-interval {
              description 'Time between retransmitting lost link state advertis'
                        + 'ements,Seconds.'
                          ;
              type uint32 {
                range 1..8192 {
                  description 'Time between retransmitting lost link state adve'
                            + 'rtisements,Seconds.'
                              ;
                }
              }
              units second ;
            }
            leaf neighbor-state {
              description 'State machine of neighbor.'
                          ;
              type enumeration {
                enum Down {
                  value 0 ;
                  description 'This is the initial state of a neighbor conversa'
                            + 'tion.'
                              ;
                }
                enum Init {
                  value 2 ;
                  description 'In this state, an Hello packet has recently been'
                            + ' seen from the neighbor.'
                              ;
                }
                enum 2-Way {
                  value 3 ;
                  description 'In this state, communication between the two rou'
                            + 'ters is bidirectional.'
                              ;
                }
                enum ExStart {
                  value 4 ;
                  description 'This is the first step in creating an adjacency '
                            + 'between the two neighboring routers.'
                              ;
                }
                enum Exchange {
                  value 5 ;
                  description 'In this state the router is describing its entir'
                            + 'e link state database by sending Database Descri'
                            + 'ption packets to the neighbor.'
                              ;
                }
                enum Loading {
                  value 6 ;
                  description 'In this state, Link State Request packets are se'
                            + 'nt to the neighbor asking for the more recent LS'
                            + 'As that have been discovered (but not yet receiv'
                            + 'ed) in the Exchange state.'
                              ;
                }
                enum Full {
                  value 7 ;
                  description 'In this state, the neighboring routers are fully'
                            + ' adjacent.'
                              ;
                }
              }
            }
            leaf dead-time {
              description 'Remain time for neighbor.'
                          ;
              type string {
                length 1..15 ;
              }
            }
            leaf full-time {
              description 'Full time of neighbor.'
                          ;
              type string {
                length 1..15 ;
              }
            }
            leaf options-field {
              description 'Option of neighbor.'
                          ;
              type uint8 ;
              ncd:revise-date 2015-06-17 ;
            }
            container options {
              description 'The options field.'
                          ;
              leaf tos-bit {
                description "This bit describes the router's surportting of tos."
                            ;
                type empty ;
              }
              leaf e-bit {
                description 'The area of router is transit area.'
                            ;
                type empty ;
              }
              leaf mc-bit {
                description 'This bit describes whether IP multicast datagrams '
                          + 'are forwarded.'
                            ;
                type empty ;
              }
              leaf n-bit {
                description 'The area of router is NSSA area.'
                            ;
                type empty ;
              }
              leaf ea-bit {
                description "This bit describes the router's willingness to rec"
                          + "eive and forward External-Attributes-LSAs."
                            ;
                type empty ;
              }
              leaf dc-bit {
                description "This bit describes the router's handling of demand"
                          + " circuits."
                            ;
                type empty ;
              }
              leaf o-bit {
                description "This bit describes the router's willingness to rec"
                          + "eive and forward opaque-LSAS."
                            ;
                type empty ;
              }
              leaf dn-bit {
                description 'When a type 3 LSA is sent from a PE router to a CE'
                          + ' router, the DN bit in the LSA Options field MUST '
                          + 'be set.'
                            ;
                type empty ;
              }
              ncd:revise-date 2015-06-17 ;
            }
            ncd:select process-id ;
          }
        }
        container shamlink-interfaces {
          description 'OSPFv2 sham-link interface.'
                      ;
          list shamlink-interface {
            description 'OSPFv2 sham-link interface.'
                        ;
            key 'process-id area-id local-ip-addr neighbor-ip-address'
                ;
            leaf process-id {
              description 'OSPF process ID.'
                          ;
              type uint32 {
                range 1..65535 {
                  description 'Ospf process ID from 1 to 65535'
                              ;
                }
              }
            }
            leaf area-id {
              description 'Area ID.'
                          ;
              type ncd:ipv4-address ;
            }
            leaf local-ip-addr {
              description 'Local ip address of sham-link.'
                          ;
              type ncd:ipv4-address ;
            }
            leaf neighbor-ip-address {
              description 'IP address of the neighbor.'
                          ;
              type ncd:ipv4-address ;
            }
            leaf demand-circuit {
              description 'Demand circuit.'
                          ;
              type empty ;
            }
            leaf suppress-hello {
              description 'Suppress hello.'
                          ;
              type empty ;
            }
            leaf interface-state {
              description 'Interface state.'
                          ;
              type enumeration {
                enum Down {
                  value 0 ;
                  description 'Down state.'
                              ;
                }
                enum Point-to-point {
                  value 3 ;
                  description 'Point-to-point state.'
                              ;
                }
              }
            }
            leaf cost {
              description 'Cost value of the interface.'
                          ;
              type uint32 {
                range 1..65535 {
                  description 'Interface cost'
                              ;
                }
              }
            }
            leaf priority {
              description 'Interface priority.'
                          ;
              type uint32 {
                range 0..255 {
                  description 'Router priority'
                              ;
                }
              }
            }
            leaf transmit-delay {
              description 'Link state transmit delay.'
                          ;
              type uint32 {
                range 1..65535 {
                  description 'Link state transmit delay,Seconds'
                              ;
                }
              }
            }
            leaf authentication-type {
              description 'Authentication Type.'
                          ;
              type enumeration {
                enum null {
                  value 0 ;
                  description 'Authentication type is null.'
                              ;
                }
                enum simple-password {
                  value 1 ;
                  description 'Authentication type is simple-password.'
                              ;
                }
                enum message-digest {
                  value 2 ;
                  description 'Authentication type is message-digest.'
                              ;
                }
              }
            }
            leaf ttl-security-state {
              description 'OSPF ttl-security.'
                          ;
              type enumeration {
                enum disable {
                  value 0 ;
                  description 'TTL security disable.'
                              ;
                }
                enum enable {
                  value 1 ;
                  description 'TTL security enable.'
                              ;
                }
              }
            }
            leaf ttl-security-hops {
              description 'OSPF ttl-security hop count.'
                          ;
              type uint8 {
                range 1..254 {
                  description 'Ttl-security hops'
                              ;
                }
              }
            }
            leaf ldp-sync {
              description 'MPLS LDP IGP sync.'
                          ;
              type enumeration {
                enum disable {
                  value 0 ;
                  description 'LDP sync disable.'
                              ;
                }
                enum enable {
                  value 1 ;
                  description 'LDP sync enable.'
                              ;
                }
              }
            }
            leaf ldp-sync-state {
              description 'LDP sync of the interface.'
                          ;
              type enumeration {
                enum unachieve {
                  value 0 ;
                  description 'The LDP sync-state is unachieved.'
                              ;
                }
                enum achieve {
                  value 1 ;
                  description 'The LDP sync-state is achieved.'
                              ;
                }
                enum unknown {
                  value 2 ;
                  description 'The LDP sync-state is unknown.'
                              ;
                }
              }
            }
            leaf ldp-autoconfig {
              description 'MPLS LDP IGP autoconfig function.'
                          ;
              type enumeration {
                enum disable {
                  value 0 ;
                  description 'LDP autoconfig disable.'
                              ;
                }
                enum enable {
                  value 1 ;
                  description 'LDP autoconfig enable.'
                              ;
                }
              }
            }
            leaf hello-interval {
              description 'Time between hello packets.'
                          ;
              type uint32 {
                range 1..65535 {
                  description 'Time between hello packets,Seconds'
                              ;
                }
              }
              units second ;
            }
            leaf dead-interval {
              description 'Interval after which a neighbor is declared dead.'
                          ;
              type uint32 {
                range 1..65535 {
                  description 'Interval after which a neighbor is declared dead'
                            + ',Seconds'
                              ;
                }
              }
              units second ;
            }
            leaf retransmit-interval {
              description 'Time between retransmitting lost link state advertis'
                        + 'ements.'
                          ;
              type uint32 {
                range 1..65535 {
                  description 'Time between retransmitting lost link state adve'
                            + 'rtisements,Seconds'
                              ;
                }
              }
              units second ;
            }
            leaf neighbor-count {
              description 'Neighbor count.'
                          ;
              type uint32 {
                range 0..1 ;
              }
            }
            leaf full-neighbor-count {
              description 'Number of full neighbors.'
                          ;
              type uint32 {
                range 0..65536 ;
              }
            }
            leaf neighbor-id {
              description 'Router ID of the neighbor.'
                          ;
              type ncd:ipv4-address ;
            }
            leaf neighbor-state {
              description 'State machine of neighbor.'
                          ;
              type enumeration {
                enum Down {
                  value 0 ;
                  description 'The state of OSPF neighbor is DOWN.'
                              ;
                }
                enum Init {
                  value 2 ;
                  description 'The state of OSPF neighbor is INIT.'
                              ;
                }
                enum 2-Way {
                  value 3 ;
                  description 'The state of OSPF neighbor is 2WAY.'
                              ;
                }
                enum ExStart {
                  value 4 ;
                  description 'The state of OSPF neighbor is EXSTART.'
                              ;
                }
                enum Exchange {
                  value 5 ;
                  description 'The state of OSPF neighbor is EXCHANGE.'
                              ;
                }
                enum Loading {
                  value 6 ;
                  description 'The state of OSPF neighbor is LOADING.'
                              ;
                }
                enum Full {
                  value 7 ;
                  description 'The state of OSPF neighbor is FULL.'
                              ;
                }
              }
            }
            leaf dead-time {
              description 'Interval after which a neighbor is declared dead.'
                          ;
              type string ;
            }
            leaf options-field {
              description 'Option of neighbor.'
                          ;
              type uint8 ;
            }
            container options {
              description 'The options field.'
                          ;
              leaf tos-bit {
                description 'This bit describes whether use the type of service.'
                            ;
                type empty ;
              }
              leaf e-bit {
                description 'This bit describes the way AS-external-LSAs are fl'
                          + 'ooded.'
                            ;
                type empty ;
              }
              leaf mc-bit {
                description 'This bit describes whether IP multicast datagrams '
                          + 'are forwarded according to the specifications.'
                            ;
                type empty ;
              }
              leaf n-bit {
                description 'The area of router is NSSA area.'
                            ;
                type empty ;
                ncd:revise-date 2015-06-17 ;
              }
              leaf ea-bit {
                description "This bit describes the router's willingness to rec"
                          + "eive and forward External-Attributes-LSAs."
                            ;
                type empty ;
              }
              leaf dc-bit {
                description "This bit describes the router's handling of demand"
                          + " circuits."
                            ;
                type empty ;
              }
              leaf o-bit {
                description "This bit describes the router's willingness to rec"
                          + "eive and forward Opaque-LSAs as specified."
                            ;
                type empty ;
              }
              leaf dn-bit {
                description 'This bit is used to ensure that if any CE router s'
                          + 'ends this type 3 LSA to a PE router, the PE router'
                          + ' will not redistribute it further.'
                            ;
                type empty ;
              }
            }
            leaf full-time {
              description 'The during time that neighbor is in the full state.'
                          ;
              type string ;
            }
            ncd:select process-id ;
          }
        }
      }
      container neighbors {
        description 'OSPFv2 neighbor.'
                    ;
        container normal-neighbors {
          description 'OSPFv2 normal neighbor.'
                      ;
          list normal-neighbor {
            description 'OSPFv2 normal neighbor.'
                        ;
            key 'process-id area-id interface-name neighbor-id'
                ;
            leaf process-id {
              description 'OSPF process ID.'
                          ;
              type uint32 {
                range 1..65535 ;
              }
            }
            leaf area-id {
              description 'OSPF area ID.'
                          ;
              type ncd:ipv4-address ;
            }
            leaf interface-name {
              description 'Interface name.'
                          ;
              type ncd:ifname {
                length 1..31 ;
              }
            }
            leaf neighbor-id {
              description 'Router ID of the neighbor.'
                          ;
              type ncd:ipv4-address ;
            }
            leaf neighbor-ip-address {
              description 'IP address of the neighbor.'
                          ;
              type ncd:ipv4-address ;
            }
            leaf neighbor-role {
              description 'The role of OSPF neighbor.'
                          ;
              type enumeration {
                enum DR {
                  value 1 ;
                  description 'Designated Router.'
                              ;
                }
                enum Backup {
                  value 2 ;
                  description 'Backup Designated Router.'
                              ;
                }
                enum DROther {
                  value 3 ;
                  description 'Router that is not DR or BDR.'
                              ;
                }
              }
            }
            leaf neighbor-state {
              description 'The state of OSPF neighbor.'
                          ;
              type enumeration {
                enum Init {
                  value 2 ;
                  description 'The state of OSPF neighbor is Init.'
                              ;
                }
                enum 2-Way {
                  value 3 ;
                  description 'The state of OSPF neighbor is 2-Way.'
                              ;
                }
                enum ExStart {
                  value 4 ;
                  description 'The state of OSPF neighbor is ExStart.'
                              ;
                }
                enum Exchange {
                  value 5 ;
                  description 'The state of OSPF neighbor is Exchange.'
                              ;
                }
                enum Loading {
                  value 6 ;
                  description 'The state of OSPF neighbor is Loading.'
                              ;
                }
                enum Full {
                  value 7 ;
                  description 'The state of OSPF neighbor is Full.'
                              ;
                }
              }
            }
            leaf priority {
              description 'Interface priority of neighbor.'
                          ;
              type uint32 {
                range 0..255 ;
              }
            }
            leaf cost {
              description 'Cost value of interface.'
                          ;
              type uint32 {
                range 1..65535 {
                  description 'Interface cost.'
                              ;
                }
              }
            }
            leaf retransmit-list-count {
              description "Number of elements in neighbor's retransmit queue li"
                        + "st."
                          ;
              type uint32 ;
            }
            leaf dd-list-count {
              description "Number of elements in neighbor's DD list."
                          ;
              type uint32 ;
            }
            leaf request-list-count {
              description "Number of elements in neighbor's request list."
                          ;
              type uint32 ;
            }
            leaf dead-time {
              description 'Interval after which a neighbor is declared dead.'
                          ;
              type string {
                length 1..15 ;
              }
            }
            leaf options-field {
              description 'Option of neighbor.'
                          ;
              type uint8 ;
            }
            container options {
              description 'The options field.'
                          ;
              leaf tos-bit {
                description 'This bit describes whether use the type of service.'
                            ;
                type empty ;
              }
              leaf e-bit {
                description 'This bit describes the way AS-external-LSAs are fl'
                          + 'ooded.'
                            ;
                type empty ;
              }
              leaf mc-bit {
                description 'This bit describes whether IP multicast datagrams '
                          + 'are forwarded according to the specifications.'
                            ;
                type empty ;
              }
              leaf n-bit {
                description 'The area of router is NSSA area.'
                            ;
                type empty ;
                ncd:revise-date 2015-06-17 ;
              }
              leaf ea-bit {
                description "This bit describes the router's willingness to rec"
                          + "eive and forward External-Attributes-LSAs."
                            ;
                type empty ;
              }
              leaf dc-bit {
                description "This bit describes the router's handling of demand"
                          + " circuits."
                            ;
                type empty ;
              }
              leaf o-bit {
                description "This bit describes the router's willingness to rec"
                          + "eive and forward Opaque-LSAs as specified."
                            ;
                type empty ;
              }
              leaf dn-bit {
                description 'This bit is used to ensure that if any CE router s'
                          + 'ends this type 3 LSA to a PE router, the PE router'
                          + ' will not redistribute it further.'
                            ;
                type empty ;
              }
            }
            leaf full-time {
              description 'The during time that neighbor is in the full state.'
                          ;
              type string {
                length 1..15 ;
              }
            }
            leaf poll-interval {
              description 'Poll interval of non-broadcast neighbor.'
                          ;
              type uint32 {
                range 1..65535 ;
              }
              units second ;
            }
            ncd:select process-id ;
            ncd:select interface-name ;
            ncd:select 'interface-name neighbor-id'
                       ;
            ncd:select 'process-id interface-name'
                       ;
            ncd:select 'process-id interface-name neighbor-id'
                       ;
            ncd:select 'process-id neighbor-id'
                       ;
          }
        }
        container virtual-neighbors {
          description 'OSPFv2 virtual neighbor.'
                      ;
          list virtual-neighbor {
            description 'OSPFv2 virtual neighbor.'
                        ;
            key 'process-id transit-area-id neighbor-id'
                ;
            leaf process-id {
              description 'OSPF process ID.'
                          ;
              type uint32 {
                range 1..65535 ;
              }
            }
            leaf transit-area-id {
              description 'The transit area of virtual link.'
                          ;
              type ncd:ipv4-address ;
            }
            leaf neighbor-id {
              description 'Router ID of the neighbor.'
                          ;
              type ncd:ipv4-address ;
            }
            leaf out-interface-name {
              description 'The interface via which the vitual link connects to '
                        + 'neighbor.'
                          ;
              type ncd:ifname {
                length 1..31 ;
              }
            }
            leaf area-id {
              description "Virtual neighbor's area id."
                          ;
              type ncd:ipv4-address ;
            }
            leaf neighbor-ip-address {
              description 'IP address of the neighbor.'
                          ;
              type ncd:ipv4-address ;
            }
            leaf neighbor-state {
              description 'The state of OSPF neighbor.'
                          ;
              type enumeration {
                enum Down {
                  value 0 ;
                  description 'The state of OSPF neighbor is Down.'
                              ;
                }
                enum Init {
                  value 2 ;
                  description 'The state of OSPF neighbor is Init.'
                              ;
                }
                enum 2-Way {
                  value 3 ;
                  description 'The state of OSPF neighbor is 2-Way.'
                              ;
                }
                enum ExStart {
                  value 4 ;
                  description 'The state of OSPF neighbor is ExStart.'
                              ;
                }
                enum Exchange {
                  value 5 ;
                  description 'The state of OSPF neighbor is Exchange.'
                              ;
                }
                enum Loading {
                  value 6 ;
                  description 'The state of OSPF neighbor is Loading.'
                              ;
                }
                enum Full {
                  value 7 ;
                  description 'The state of OSPF neighbor is Full.'
                              ;
                }
              }
            }
            leaf priority {
              description 'Interface priority of neighbor.'
                          ;
              type uint32 {
                range 0..255 ;
              }
            }
            leaf cost {
              description 'Cost value of interface.'
                          ;
              type uint32 {
                range 1..65535 ;
              }
            }
            leaf retransmit-list-count {
              description "Number of elements in neighbor's retransmit queue li"
                        + "st."
                          ;
              type uint32 ;
            }
            leaf dd-list-count {
              description "Number of elements in neighbor's DD list."
                          ;
              type uint32 ;
            }
            leaf request-list-count {
              description "Number of elements in neighbor's request list."
                          ;
              type uint32 ;
            }
            leaf dead-time {
              description 'Interval after which a neighbor is declared dead.'
                          ;
              type string {
                length 1..15 ;
              }
            }
            leaf options-field {
              description 'Option of neighbor.'
                          ;
              type uint8 ;
            }
            container options {
              description 'The options field.'
                          ;
              leaf tos-bit {
                description 'This bit describes whether use the type of service.'
                            ;
                type empty ;
              }
              leaf e-bit {
                description 'This bit describes the way AS-external-LSAs are fl'
                          + 'ooded.'
                            ;
                type empty ;
              }
              leaf mc-bit {
                description 'This bit describes whether IP multicast datagrams '
                          + 'are forwarded according to the specifications.'
                            ;
                type empty ;
              }
              leaf n-bit {
                description 'The area of router is NSSA area.'
                            ;
                type empty ;
                ncd:revise-date 2015-06-17 ;
              }
              leaf ea-bit {
                description "This bit describes the router's willingness to rec"
                          + "eive and forward External-Attributes-LSAs."
                            ;
                type empty ;
              }
              leaf dc-bit {
                description "This bit describes the router's handling of demand"
                          + " circuits."
                            ;
                type empty ;
              }
              leaf o-bit {
                description "This bit describes the router's willingness to rec"
                          + "eive and forward Opaque-LSAs as specified."
                            ;
                type empty ;
              }
              leaf dn-bit {
                description 'This bit is used to ensure that if any CE router s'
                          + 'ends this type 3 LSA to a PE router, the PE router'
                          + ' will not redistribute it further.'
                            ;
                type empty ;
              }
            }
            leaf full-time {
              description 'The during time that neighbor is in the full state.'
                          ;
              type string {
                length 1..15 ;
              }
            }
            ncd:select neighbor-id ;
            ncd:select process-id ;
            ncd:select 'process-id neighbor-id'
                       ;
          }
        }
        container shamlink-neighbors {
          description 'OSPFv2 sham-link neighbor.'
                      ;
          list shamlink-neighbor {
            description 'OSPFv2 sham-link neighbor.'
                        ;
            key 'process-id area-id local-ip-address neighbor-ip-address'
                ;
            leaf process-id {
              description 'OSPF process ID.'
                          ;
              type uint32 {
                range 1..65535 ;
              }
            }
            leaf area-id {
              description 'OSPF area ID.'
                          ;
              type ncd:ipv4-address ;
            }
            leaf local-ip-address {
              description 'Local ip address of sham-link.'
                          ;
              type ncd:ipv4-address ;
            }
            leaf neighbor-ip-address {
              description 'IP address of the neighbor.'
                          ;
              type ncd:ipv4-address ;
            }
            leaf out-interface-name {
              description 'The interface via which the sham link connects to ne'
                        + 'ighbor.'
                          ;
              type ncd:ifname {
                length 1..31 ;
              }
            }
            leaf neighbor-id {
              description 'Router ID of the neighbor.'
                          ;
              type ncd:ipv4-address ;
            }
            leaf neighbor-state {
              description 'The state of OSPF neighbor.'
                          ;
              type enumeration {
                enum Down {
                  value 0 ;
                  description 'The state of OSPF neighbor is DOWN.'
                              ;
                }
                enum Init {
                  value 2 ;
                  description 'The state of OSPF neighbor is INIT.'
                              ;
                }
                enum 2-Way {
                  value 3 ;
                  description 'The state of OSPF neighbor is 2WAY.'
                              ;
                }
                enum ExStart {
                  value 4 ;
                  description 'The state of OSPF neighbor is EXSTART.'
                              ;
                }
                enum Exchange {
                  value 5 ;
                  description 'The state of OSPF neighbor is EXCHANGE.'
                              ;
                }
                enum Loading {
                  value 6 ;
                  description 'The state of OSPF neighbor is LOADING.'
                              ;
                }
                enum Full {
                  value 7 ;
                  description 'The state of OSPF neighbor is FULL.'
                              ;
                }
              }
            }
            leaf priority {
              description 'Interface priority of neighbor.'
                          ;
              type uint32 {
                range 0..255 ;
              }
            }
            leaf cost {
              description 'Cost value of interface.'
                          ;
              type uint32 {
                range 1..65535 ;
              }
            }
            leaf retransmit-list-count {
              description "Number of elements in neighbor's retransmit queue li"
                        + "st."
                          ;
              type uint32 ;
            }
            leaf dd-list-count {
              description "Number of elements in neighbor's DD list."
                          ;
              type uint32 ;
            }
            leaf request-list-count {
              description "Number of elements in neighbor's request list."
                          ;
              type uint32 ;
            }
            leaf dead-time {
              description 'Interval after which a neighbor is declared dead.'
                          ;
              type string {
                length 1..15 ;
              }
            }
            leaf options-field {
              description 'Option of neighbor.'
                          ;
              type uint8 ;
            }
            container options {
              description 'The options field.'
                          ;
              leaf tos-bit {
                description 'This bit describes whether use the type of service.'
                            ;
                type empty ;
              }
              leaf e-bit {
                description 'This bit describes the way AS-external-LSAs are fl'
                          + 'ooded.'
                            ;
                type empty ;
              }
              leaf mc-bit {
                description 'This bit describes whether IP multicast datagrams '
                          + 'are forwarded according to the specifications.'
                            ;
                type empty ;
              }
              leaf n-bit {
                description 'The area of router is NSSA area.'
                            ;
                type empty ;
                ncd:revise-date 2015-06-17 ;
              }
              leaf ea-bit {
                description "This bit describes the router's willingness to rec"
                          + "eive and forward External-Attributes-LSAs."
                            ;
                type empty ;
              }
              leaf dc-bit {
                description "This bit describes the router's handling of demand"
                          + " circuits."
                            ;
                type empty ;
              }
              leaf o-bit {
                description "This bit describes the router's willingness to rec"
                          + "eive and forward Opaque-LSAs as specified."
                            ;
                type empty ;
              }
              leaf dn-bit {
                description 'This bit is used to ensure that if any CE router s'
                          + 'ends this type 3 LSA to a PE router, the PE router'
                          + ' will not redistribute it further.'
                            ;
                type empty ;
              }
            }
            leaf full-time {
              description 'The during time that neighbor is in the full state.'
                          ;
              type string {
                length 1..15 ;
              }
            }
            ncd:select process-id ;
          }
        }
      }
      container vertexes {
        description 'OSPFv2 vertex.'
                    ;
        list vertex {
          description 'OSPFv2 vertex.'
                      ;
          key 'process-id area-id vertex-type advertising-router link-state-id'
              ;
          leaf process-id {
            description 'OSPF process ID.'
                        ;
            type uint32 {
              range 1..65535 ;
            }
          }
          leaf area-id {
            description 'Area ID.'
                        ;
            type ncd:ipv4-address ;
          }
          leaf vertex-type {
            description 'Vertex type.'
                        ;
            type enumeration {
              enum Router {
                value 0 ;
                description 'Router vertex.'
                            ;
              }
              enum Network {
                value 1 ;
                description 'Network vertex.'
                            ;
              }
            }
          }
          leaf advertising-router {
            description 'Advertising router.'
                        ;
            type ncd:ipv4-address ;
          }
          leaf link-state-id {
            description 'Link state ID'
                        ;
            type ncd:ipv4-address ;
          }
          leaf primary-nh-cost {
            description 'Primary nexthop cost of vertex.'
                        ;
            type uint32 {
              range 1..2147483647 ;
            }
          }
          container nexthops {
            description Nexthop. ;
            list nexthop {
              description Nexthop. ;
              key 'primary-nh-if-index primary-nh-type primary-nh-ip'
                  ;
              leaf primary-nh-if-index {
                description 'Interface index of primary nexthop.'
                            ;
                type uint32; 
                //type uint32 {
                //  range 1..4294967295 ;
                //}
              }
              leaf primary-nh-type {
                description 'Type of primary nexthop.'
                            ;
                type enumeration {
                  enum Nh-nbr {
                    value 1 ;
                    description 'Nexthop for neighbor.'
                                ;
                  }
                  enum Nh-tunnel {
                    value 2 ;
                    description 'Nexthop for tunnel.'
                                ;
                  }
                  enum Nh-virtual {
                    value 3 ;
                    description 'Nexthop for virtual.'
                                ;
                  }
                  enum Nh-local {
                    value 4 ;
                    description 'Nexthop for local.'
                                ;
                  }
                  enum Nh-shamlink {
                    value 5 ;
                    description 'Nexthop for shamlink.'
                                ;
                  }
                }
              }
              leaf primary-nh-ip {
                description 'Ip address of primary nexthop.'
                            ;
                type ncd:ipv4-address ;
              }
              leaf primary-nh-if-name {
                description 'Interface name of primary nexthop.'
                            ;
                type ncd:ifname {
                  length 1..31 ;
                }
              }
              container backup-nexthops {
                description 'Backup nexthop.'
                            ;
                container dynamic-remote-lfas {
                  description 'Dynamic remote LFA.'
                              ;
                  list dynamic-remote-lfa {
                    description 'Dynamic remote LFA.'
                                ;
                    key 'nh-if-index nh-type nh-ip'
                        ;
                    leaf nh-if-index {
                      description 'Interface index of drlfa nexthop.'
                                  ;
                      type uint32;
                      //type uint32 {
                      //  range 1..4294967295 ;
                      //}
                    }
                    leaf nh-type {
                      description 'Type of of drlfa nexthop.'
                                  ;
                      type enumeration {
                        enum Nh-nbr {
                          value 1 ;
                          description 'Nexthop for neighbor.'
                                      ;
                        }
                        enum Nh-tunnel {
                          value 2 ;
                          description 'Nexthop for tunnel.'
                                      ;
                        }
                        enum Nh-virtual {
                          value 3 ;
                          description 'Nexthop for virtual.'
                                      ;
                        }
                        enum Nh-local {
                          value 4 ;
                          description 'Nexthop for local.'
                                      ;
                        }
                        enum Nh-shamlink {
                          value 5 ;
                          description 'Nexthop for shamlink.'
                                      ;
                        }
                      }
                    }
                    leaf nh-ip {
                      description 'Ip address of drlfa nexthop .'
                                  ;
                      type ncd:ipv4-address ;
                    }
                    leaf nh-if-name {
                      description 'Interface name of drlfa nexthop.'
                                  ;
                      type ncd:ifname {
                        length 1..31 {
                          description 'Backup next hop interface name'
                                      ;
                        }
                      }
                    }
                    leaf nh-cost {
                      description 'Cost of drlfa nexthop.'
                                  ;
                      type uint32 {
                        range 1..65535 {
                          description 'Backup next hop cost'
                                      ;
                        }
                      }
                    }
                    leaf session-type {
                      description 'Session type.'
                                  ;
                      type enumeration {
                        enum mpls-ldp {
                          value 1 ;
                          description 'MPLS LDP.'
                                      ;
                        }
                      }
                    }
                    leaf peer-session-id {
                      description 'Peer session id.'
                                  ;
                      type ncd:ipv4-address ;
                    }
                    leaf peer-metric {
                      description 'Peer metric.'
                                  ;
                      type uint32 ;
                    }
                    leaf protect-type-s-pq {
                      description 'The protect type of S to PQ.'
                                  ;
                      type enumeration {
                        enum NULL {
                          value 0 ;
                          description 'Protect type is NULL.'
                                      ;
                        }
                        enum Link {
                          value 1 ;
                          description 'Link protection.'
                                      ;
                        }
                        enum Node {
                          value 2 ;
                          description 'Node protection.'
                                      ;
                        }
                        enum Link-node {
                          value 3 ;
                          description 'Link and node protection.'
                                      ;
                        }
                      }
                    }
                    leaf protect-type-pq-d {
                      description 'The protect type of PQ to D.'
                                  ;
                      type enumeration {
                        enum NULL {
                          value 0 ;
                          description NULL ;
                        }
                        enum Node {
                          value 1 ;
                          description 'Node protection.'
                                      ;
                        }
                        enum Downstream {
                          value 2 ;
                          description 'Downstream protection.'
                                      ;
                        }
                        enum Node-downstream {
                          value 3 ;
                          description 'Node and downstream protection.'
                                      ;
                        }
                      }
                    }
                    leaf update-time {
                      description 'Update time.'
                                  ;
                      type string ;
                    }
                    leaf session-status {
                      description 'Session status.'
                                  ;
                      type enumeration {
                        enum Down {
                          value 0 ;
                          description 'Session status is Down.'
                                      ;
                        }
                        enum Up {
                          value 1 ;
                          description 'Session status is Up.'
                                      ;
                        }
                      }
                    }
                  }
                }
              }
            }
          }
          ncd:select process-id ;
          ncd:select advertising-router ;
          ncd:select 'process-id advertising-router'
                     ;
        }
        ncd:revise-date 2015-10-20 ;
      }
    }
    ncd:revise-date 2015-03-26 ;
  }
  container operation {
    config false ;
    description 'Operation mode.'
                ;
    container ospfv2 {
      description 'Operation of OSPFv2.'
                  ;
      container clear {
        description 'Clear Operation.'
                    ;
        container process {
          description 'Reset an OSPF process based on the process ID.'
                      ;
          leaf process-id {
            description 'OSPF process ID.'
                        ;
            type uint32 {
              range 1..65535 ;
            }
          }
        }
        container redistribution {
          description 'Clear OSPF route redistribution based on the process ID.'
                      ;
          leaf process-id {
            description 'OSPF process ID.'
                        ;
            type uint32 {
              range 1..65535 ;
            }
          }
        }
      }
    }
    ncd:revise-date 2015-03-26 ;
  }
}
