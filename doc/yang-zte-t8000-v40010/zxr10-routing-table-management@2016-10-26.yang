module zxr10-routing-table-management {
  namespace 'http://www.zte.com.cn/zxr10/netconf/schema/rosng/rtm'
            ;
  prefix rtm ;
  yang-version 1 ;
  import zxr10-netconf-defs {
    prefix ncd ;
    revision-date 2013-11-22 ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe the routing table management(rtm).'
              ;
  revision 2016-10-26 {
    description 'This Netconf module provides IPv4/IPv6 routes statistics of gl'
              + 'obal and all VPN routes'+"\n"
              + 'this version add two nodes:'+"\n"
              + '1 state/rtm/route-summary-alls'+"\n"
              + '2 state/rtm6/route-summary-alls'
                ;
  }
  revision 2016-04-16 {
    description 'This Netconf module provides commonly used textual conventions'
              + ' for RTM.'+"\n"
              + 'This version add four nodes:'+"\n"
              + '1.state\rtm6\route6-statistics\route6-statistics\user-network;'
              + ''+"\n"
              + '2.state\rtm6\route6-statistics\route6-statistics\user-special;'
              + ''+"\n"
              + '3.state\rtm6\route6-path-statistics\route6-path-statistics\use'
              + 'r-network;'+"\n"
              + '4.state\rtm6\route6-path-statistics\route6-path-statistics\use'
              + 'r-special;'+"\n"
              + 'This version add two new values:user-network and user-special '
              + 'in choice ipv6-owner-type.'
                ;
  }
  revision 2015-05-18 {
    description 'This Netconf module provides commonly used textual conventions'
              + ' for RTM.'+"\n"
              + 'This version add two nodes:'+"\n"
              + '1.state\rtm6\route6-statistics\route6-statistics\ldp-area;'+"\n"
              + '2.state\rtm6\route6-path-statistics\route6-path-statistics\ldp'
              + '-area;'+"\n"
              + 'This version add a new value:ldp-area in choice ipv6-owner-typ'
              + 'e.'
                ;
  }
  revision 2015-05-07 {
    description "This Netconf module provides commonly used textual conventions"
              + " for RTM.
\nThis version change the MimDateType of iproute6's "
              + "route-owner."
                ;
  }
  revision 2015-04-15 {
    description "This Netconf module provides commonly used textual conventions"
              + " for RTM.
\nThis version change the MimDateType of iproute6's "
              + "route-owner."
                ;
  }
  revision 2015-02-10 {
    description 'This Netconf module provides commonly used textual conventions'
              + ' for RTM.'+"\n"
              + 'This version change spell of msp and lsp.'
                ;
  }
  revision 2015-02-02 {
    description "This Netconf module provides commonly used textual conventions"
              + " for RTM.
\nThis version change the MimDateType of iproute's r"
              + "oute-owner."
                ;
  }
  revision 2015-01-19 {
    description 'This Netconf module provides commonly used textual conventions'
              + ' for RTM.'+"\n"
              + 'This version change the valuemap of ipv6 on ldsh-hash-key-boar'
              + 'd and ldsh-hash-key-global.'
                ;
  }
  revision 2014-12-05 {
    description 'This Netconf module provides commonly used textual conventions'
              + ' for RTM.'+"\n"
              + 'This version add filter for ldsh-hash-key.'
                ;
  }
  revision 2014-09-16 {
    description 'This Netconf module provides commonly used textual conventions'
              + ' for RTM.'+"\n"
              + 'This version add route frr status for state iproute.'
                ;
  }
  revision 2014-07-09 {
    description 'This Netconf module provides commonly used textual conventions'
              + ' for RTM.'+"\n"
              + 'This version add state for statistics of fib.'
                ;
  }
  revision 2014-05-12 {
    description 'This Netconf module provides commonly used textual conventions'
              + ' for RTM.'+"\n"
              + 'This version add state for information of ipv6 route.'
                ;
  }
  revision 2014-04-30 {
    description 'This Netconf module provides commonly used textual conventions'
              + ' for RTM.'+"\n"
              + 'This version change mim action of ldsh-hash-fields,mpls-ldsh-h'
              + 'ash-fields and ldsh-hash-algorithm.'
                ;
  }
  revision 2014-04-11 {
    description 'This Netconf module provides commonly used textual conventions'
              + ' for RTM.'+"\n"
              + 'This version add state of route statistic.'
                ;
  }
  revision 2014-03-27 {
    description 'This Netconf module provides commonly used textual conventions'
              + ' for RTM.'+"\n"
              + 'This version add configuration about mpls ldsh hash configurat'
              + 'ion,hash scramble and bandwidth refresh.'
                ;
  }
  revision 2014-02-20 {
    description 'This Netconf module provides commonly used textual conventions'
              + ' for RTM.'+"\n"
              + 'This version deal spelling mistake of owner-type bgp-label and'
              + ' vpn-label.'
                ;
  }
  revision 2014-02-11 {
    description 'This Netconf module provides commonly used textual conventions'
              + ' for RTM.'+"\n"
              + 'This version deal spelling mistake of owner-type static-vrf-gl'
              + 'obal-nh.'
                ;
  }
  revision 2013-12-10 {
    description 'This Netconf module provides commonly used textual conventions'
              + ' for RTM.'+"\n"
              + 'This version select the leaf route-netxhop and route-ifname as'
              + ' key of ip-route.'
                ;
  }
  revision 2013-10-10 {
    description 'This Netconf module provides commonly used textual conventions'
              + ' for RTM.'+"\n"
              + 'This version add information about route for state, and add co'
              + 'nfiguration about ldsh.'
                ;
  }
  revision 2013-08-05 {
    description 'This Netconf module provides commonly used textual conventions'
              + ' for RTM.'+"\n"
              + 'This version changes the query condition.Adding objtype to ide'
              + 'ntify the frr in global routing tabel or vpn routing tabel.'
                ;
  }
  revision 2013-07-30 {
    description 'This Netconf module provides commonly used textual conventions'
              + ' for RTM.'+"\n"
              + 'This version changes the enumeration of forward-status.'
                ;
  }
  revision 2013-07-18 {
    description 'This Netconf module provides commonly used textual conventions'
              + ' for RTM.'+"\n"
              + 'This version changes the module name form zxr10-rtm to zxr10-r'
              + 'outing-table-management.'
                ;
  }
  revision 2013-06-13 {
    description 'This Netconf module provides commonly used textual conventions'
              + ' for RTM.'+"\n"
              + 'It is initial version.'
                ;
  }
  typedef owner-type {
    type enumeration {
      enum init {
        value 0 ;
        description 'This owner should not appear.'
                    ;
      }
      enum static {
        value 1 ;
        description 'Route owner is static.'
                    ;
      }
      enum direct {
        value 2 ;
        description 'Route owner is direct.'
                    ;
      }
      enum broadcast {
        value 3 ;
        description 'Route owner is broadcast.'
                    ;
      }
      enum multicast {
        value 4 ;
        description 'Route owner is multicast.'
                    ;
      }
      enum martian {
        value 5 ;
        description 'Route owner is martian.'
                    ;
      }
      enum address {
        value 6 ;
        description 'Route owner is address.'
                    ;
      }
      enum ospf {
        value 7 ;
        description 'Route owner is ospf.'
                    ;
      }
      enum bgp {
        value 8 ;
        description 'Route owner is bgp.'
                    ;
      }
      enum bgp-label {
        value 9 ;
        description 'Route owner is bgp-label.'
                    ;
      }
      enum rip {
        value 10 ;
        description 'Route owner is rip.'
                    ;
      }
      enum isis-l1 {
        value 11 ;
        description 'Route owner is isis-l1.'
                    ;
      }
      enum isis-l2 {
        value 12 ;
        description 'Route owner is isis-l2.'
                    ;
      }
      enum icmp {
        value 13 ;
        description 'Route owner is icmp.'
                    ;
      }
      enum snmp {
        value 14 ;
        description 'Route owner is snmp.'
                    ;
      }
      enum nat {
        value 15 ;
        description 'Route owner is nat.'
                    ;
      }
      enum natpt {
        value 16 ;
        description 'Route owner is natpt.'
                    ;
      }
      enum vrrp {
        value 17 ;
        description 'Route owner is vrrp.'
                    ;
      }
      enum ppp {
        value 18 ;
        description 'Route owner is ppp.'
                    ;
      }
      enum asbr-vpn {
        value 19 ;
        description 'Route owner is asbr-vpn.'
                    ;
      }
      enum rsvp-te {
        value 20 ;
        description 'Route owner is rsvp-te.'
                    ;
      }
      enum user-ipaddress {
        value 21 ;
        description 'Route owner is user-ipaddress.'
                    ;
      }
      enum user-network {
        value 22 ;
        description 'Route owner is user-network.'
                    ;
      }
      enum static-vrf-global-nh {
        value 23 ;
        description 'Route owner is static-vrf-global-nh.'
                    ;
      }
      enum IPSec {
        value 24 ;
        description 'Route owner is IPSec.'
                    ;
      }
      enum vpn-label {
        value 25 ;
        description 'Route owner is vpn-label.'
                    ;
      }
      enum psbusi-address {
        value 26 ;
        description 'Route owner is psbusi-address.'
                    ;
      }
      enum psuser-address {
        value 27 ;
        description 'Route owner is psuser-address.'
                    ;
      }
      enum ldp-area {
        value 28 ;
        description 'Route owner is ldp-area.'
                    ;
      }
      enum user-special {
        value 29 ;
        description 'Route owner is user-special.'
                    ;
      }
      enum dhcp-default {
        value 30 ;
        description 'Route owner is dhcp-default.'
                    ;
      }
      enum dhcp-static {
        value 31 ;
        description 'Route owner is dhcp-static.'
                    ;
      }
      enum slnat64 {
        value 32 ;
        description 'Route owner is slnat64.'
                    ;
      }
      enum ves {
        value 33 ;
        description 'Route owner is ves.'
                    ;
      }
    }
    description 'The owner type of nexthop.'
                ;
  }
  typedef forward-status {
    type enumeration {
      enum master {
        value 0 ;
        description 'The master nexthop of this frr is active.'
                    ;
      }
      enum slave {
        value 1 ;
        description 'The slave nexthop of this frr is active.'
                    ;
      }
      enum no-forwarding {
        value 2 ;
        description 'There is no active nexthop for this frr.'
                    ;
      }
      enum wtr {
        value 3 ;
        description 'This frr is waiting for cutback.'
                    ;
      }
    }
    description 'The forwarding status of frr.'
                ;
  }
  typedef select-module {
    type enumeration {
      enum global {
        value 1 ;
        description 'The frr in global routing tabel.'
                    ;
      }
      enum vpn {
        value 2 ;
        description 'The frr in vpn routing tabel.'
                    ;
      }
      enum global-vpn {
        value 3 ;
        description 'The frr in global routing tabel or vpn routing tabel.'
                    ;
      }
    }
    description 'The select module of frr.'
                ;
  }
  typedef ipv6-owner-type {
    type enumeration {
      enum init {
        value 0 ;
        description 'Route owner is init.'
                    ;
      }
      enum kernel {
        value 1 ;
        description 'Route owner is kernel.'
                    ;
      }
      enum direct {
        value 2 ;
        description 'Route owner is connect.'
                    ;
      }
      enum static {
        value 3 ;
        description 'Route owner is static.'
                    ;
      }
      enum rip {
        value 4 ;
        description 'Route owner is rip.'
                    ;
      }
      enum ripng {
        value 5 ;
        description 'Route owner is ripng.'
                    ;
      }
      enum ospfv2 {
        value 6 ;
        description 'Route owner is ospfv2.'
                    ;
      }
      enum ospfv3 {
        value 7 ;
        description 'Route owner is ospfv3.'
                    ;
      }
      enum bgp {
        value 8 ;
        description 'Route owner is bgp.'
                    ;
      }
      enum isis_l1 {
        value 9 ;
        description 'Route owner is isis_l1.'
                    ;
      }
      enum isis_l2 {
        value 10 ;
        description 'Route owner is isis_l2.'
                    ;
      }
      enum icmp {
        value 11 ;
        description 'Route owner is icmp.'
                    ;
      }
      enum multicast {
        value 12 ;
        description 'Route owner is multicast.'
                    ;
      }
      enum user_ipaddr {
        value 13 ;
        description 'Route owner is user_ipaddr.'
                    ;
      }
      enum vrrp {
        value 14 ;
        description 'Route owner is vrrp.'
                    ;
      }
      enum ppp {
        value 15 ;
        description 'Route owner is ppp.'
                    ;
      }
      enum nd {
        value 16 ;
        description 'Route owner is nd.'
                    ;
      }
      enum address {
        value 17 ;
        description 'Route owner is address.'
                    ;
      }
      enum dhcp {
        value 18 ;
        description 'Route owner is dhcp.'
                    ;
      }
      enum sf_nat64 {
        value 19 ;
        description 'Route owner is sf_nat64.'
                    ;
      }
      enum sl_nat64 {
        value 20 ;
        description 'Route owner is sl_nat64.'
                    ;
      }
      enum aftr {
        value 21 ;
        description 'Route owner is aftr.'
                    ;
      }
      enum bgp-label {
        value 22 ;
        description 'Route owner is bgp-label.'
                    ;
      }
      enum psbusi-address {
        value 23 ;
        description 'Route owner is psbusi-address.'
                    ;
      }
      enum psuser-address {
        value 24 ;
        description 'Route owner is psuser-address.'
                    ;
      }
      enum ldp-area {
        value 25 ;
        description 'Route owner is ldp-area.'
                    ;
      }
      enum user-network {
        value 26 ;
        description 'Route owner is user-network.'
                    ;
      }
      enum user-special {
        value 27 ;
        description 'Route owner is user-special.'
                    ;
      }
    }
  }
  container state {
    config false ;
    description 'This modul show the forwarding infor of routing table manageme'
              + 'nt.'
                ;
    container rtm {
      description 'This module show information about routing table management('
                + 'rtm).'
                  ;
      container frr {
        description 'This modul show the forwarding infor of frr.'
                    ;
        list ipfrr {
          description 'This modul show the forwarding infor of ip frr.'+"\n"
                    + 'For the frr of global,need select objtype(1),route-dest,'
                    + 'route-prefix.'+"\n"
                    + 'For all frr of global,need select objtype(1).'+"\n"
                    + 'For the frr of the vpn,need select objtype(2),route-vrfn'
                    + 'ame,route-dest,route-prefix.'+"\n"
                    + 'For all frr of the vpn,need select objtype(2),route-vrfn'
                    + 'ame.'+"\n"
                    + 'For all frr of global and all vpn,need select objtype(3)'
                    + '.'
                      ;
          key 'objtype route-vrfname route-dest route-prefix'
              ;
          leaf objtype {
            description 'The select module of ipfrr.'
                        ;
            type select-module ;
          }
          leaf route-vrfname {
            description 'VRF name of the route.'
                        ;
            type string {
              length 0..32 ;
            }
          }
          leaf route-dest {
            description 'The destination IP address of this route.'
                        ;
            type ncd:ipv4-address ;
          }
          leaf route-prefix {
            description 'The mask of this route.'
                        ;
            type ncd:ipv4-mask ;
          }
          leaf route-master-nexthop {
            description 'The nexthop of master route.'
                        ;
            type ncd:ipv4-address ;
            mandatory true ;
          }
          leaf route-master-ifname {
            description 'The local interface name through which the master next'
                      + ' hop of this route should be reached.'
                        ;
            type string {
              length 0..31 ;
            }
            mandatory true ;
          }
          leaf route-master-owner {
            description 'The protocol of master route.'
                        ;
            type owner-type ;
            mandatory true ;
          }
          leaf route-master-label {
            description 'The out label of master route.'
                        ;
            type uint32 {
              range 0..4294967295 ;
            }
            mandatory true ;
          }
          leaf route-master-priority {
            description 'The priority of master route.'
                        ;
            type uint8 {
              range 0..255 ;
            }
            mandatory true ;
          }
          leaf route-master-metric {
            description 'The metric of master route.'
                        ;
            type uint32 {
              range 0..4294967295 ;
            }
            mandatory true ;
          }
          leaf route-master-is-pe {
            description "Whether the next hop of master route is PE.
\nTure:It'"
                      + "s pe.\nFalse:It's not pe."
                        ;
            type boolean ;
            mandatory true ;
          }
          leaf route-slave-nexthop {
            description 'The nexthop of slave route.'
                        ;
            type ncd:ipv4-address ;
            mandatory true ;
          }
          leaf route-slave-ifname {
            description 'The local interface name through which the slave next '
                      + 'hop of this route should be reached.'
                        ;
            type string {
              length 0..31 ;
            }
            mandatory true ;
          }
          leaf route-slave-owner {
            description 'The protocol of slave route.'
                        ;
            type owner-type ;
            mandatory true ;
          }
          leaf route-slave-label {
            description 'The out label of slave route.'
                        ;
            type uint32 {
              range 0..4294967295 ;
            }
            mandatory true ;
          }
          leaf route-slave-priority {
            description 'The priority of slave route.'
                        ;
            type uint8 {
              range 0..255 ;
            }
            mandatory true ;
          }
          leaf route-slave-metric {
            description 'The metric of slave route.'
                        ;
            type uint32 {
              range 0..4294967295 ;
            }
            mandatory true ;
          }
          leaf route-slave-is-pe {
            description "Whether the next hop of slave route is PE.
\nTrue:It's"
                      + " pe.
\nFalse:It's not pe."
                        ;
            type boolean ;
            mandatory true ;
          }
          leaf route-forwarding-status {
            description 'Forwarding status of frr.'
                        ;
            type forward-status ;
            mandatory true ;
          }
          ncd:select 'objtype route-vrfname route-dest route-prefix'
                     ;
          ncd:select 'objtype route-dest route-prefix'
                     ;
          ncd:select 'objtype route-vrfname'
                     ;
          ncd:select objtype ;
        }
      }
      container route {
        description 'This modul show the forwarding infor of route.'
                    ;
        list iproute {
          description 'This modul show the forwarding infor of ip route.'+"\n"
                    + 'For all route of global,need select objtype(1).'+"\n"
                    + 'For the special protocol route of globle, need select ob'
                    + 'ject(1),route-owner.'+"\n"
                    + 'For exact match the route of global,need select objtype('
                    + '1),route-dest,route-prefix and route-match-type(true).'+"\n"
                    + 'For best match the route of global,need select objtype(1'
                    + '),route-dest and route-prefix.'+"\n"
                    + 'For all route of the vrf,need select objtype(2),route-vp'
                    + 'nname.'+"\n"
                    + 'For the special protocol route of the vrf, need select o'
                    + 'bject(2),route-owner.'+"\n"
                    + 'For exact match the route of the vrf,need select objtype'
                    + '(2),route-vpnname,route-dest,route-prefix and route-matc'
                    + 'h-type(true).'+"\n"
                    + 'For best match the route of the vrf,need select objtype('
                    + '2),route-vpnname,route-dest and route-prefix.'
                      ;
          key 'objtype route-vpnname route-owner route-dest route-prefix route-'
            + 'is-exact-match route-nexthop route-ifname'
              ;
          leaf objtype {
            description 'The select module of fib.'
                        ;
            type select-module ;
          }
          leaf route-vpnname {
            description 'VRF name of the route.'
                        ;
            type string {
              length 0..32 ;
            }
          }
          leaf route-owner {
            description 'The protocol of route.'
                        ;
            type owner-type ;
          }
          leaf route-dest {
            description 'The destination IP address of this route.'
                        ;
            type ncd:ipv4-address ;
          }
          leaf route-prefix {
            description 'The mask of this route.'
                        ;
            type ncd:ipv4-mask ;
          }
          leaf route-is-exact-match {
            description 'The match type of route.True is exact match,false is b'
                      + 'est match.'
                        ;
            type boolean ;
          }
          leaf route-nexthop {
            description 'The nexthop of route.'
                        ;
            type ncd:ipv4-address ;
          }
          leaf route-ifname {
            description 'The local interface name through which the next hop of'
                      + ' this route should be reached.'
                        ;
            type string {
              length 0..31 ;
            }
          }
          leaf route-priority {
            description 'The priority of route.'
                        ;
            type uint8 {
              range 0..255 ;
            }
            mandatory true ;
          }
          leaf route-metric {
            description 'The metric of route.'
                        ;
            type uint32 {
              range 0..4294967295 ;
            }
            mandatory true ;
          }
          leaf route-has-frr {
            description 'Route frr relation falg.'
                        ;
            type boolean ;
            mandatory true ;
          }
          leaf route-is-valid {
            description 'route valid flag.'
                        ;
            type boolean ;
            mandatory true ;
          }
          leaf route-is-backup {
            description 'Route is frr back path.'
                        ;
            type empty ;
          }
          ncd:select objtype ;
          ncd:select 'objtype route-owner'
                     ;
          ncd:select 'objtype route-dest route-prefix route-is-exact-match'
                     ;
          ncd:select 'objtype route-vpnname'
                     ;
          ncd:select 'objtype route-vpnname route-owner'
                     ;
          ncd:select 'objtype route-vpnname route-dest route-prefix route-is-ex'
                   + 'act-match'
                     ;
          ncd:select 'objtype route-vpnname route-dest route-prefix'
                     ;
          ncd:select 'objtype route-dest route-prefix'
                     ;
        }
      }
      container route-statistics {
        description 'This modul show the statistic infor of route.'
                    ;
        list route-statistic {
          description 'The statistic of routes.'+"\n"
                    + 'For statistic of global route,need select objtype(1).'+"\n"
                    + 'For statistic of the vpn route,need select objtype(2) an'
                    + 'd vpnname.'+"\n"
                    + 'For statistic of all route,need select objtype(3).'
                      ;
          key 'objtype vpnname'
              ;
          leaf objtype {
            description 'The select module of route statistic.'
                        ;
            type select-module ;
          }
          leaf vpnname {
            description 'VRF name of the route.'
                        ;
            type string {
              length 0..32 ;
            }
          }
          leaf static {
            description 'The statistic of static route.'
                        ;
            type uint32 ;
          }
          leaf direct {
            description 'The statistic of direct route.'
                        ;
            type uint32 ;
          }
          leaf broadcast {
            description 'The statistic of broadcast route.'
                        ;
            type uint32 ;
          }
          leaf multicast {
            description 'The statistic of multicast route.'
                        ;
            type uint32 ;
          }
          leaf martian {
            description 'The statistic of martian route.'
                        ;
            type uint32 ;
          }
          leaf address {
            description 'The statistic of address route.'
                        ;
            type uint32 ;
          }
          leaf ospf {
            description 'The statistic of ospf route.'
                        ;
            type uint32 ;
          }
          leaf bgp {
            description 'The statistic of bgp route.'
                        ;
            type uint32 ;
          }
          leaf rip {
            description 'The statistic of rip route.'
                        ;
            type uint32 ;
          }
          leaf isis-l1 {
            description 'The statistic of isis-l1 route.'
                        ;
            type uint32 ;
          }
          leaf isis-l2 {
            description 'The statistic of isis-l2 route.'
                        ;
            type uint32 ;
          }
          leaf icmp {
            description 'The statistic of icmp route.'
                        ;
            type uint32 ;
          }
          leaf snmp {
            description 'The statistic of snmp route.'
                        ;
            type uint32 ;
          }
          leaf nat {
            description 'The statistic of nat route.'
                        ;
            type uint32 ;
          }
          leaf pat {
            description 'The statistic of pat route.'
                        ;
            type uint32 ;
          }
          leaf vrrp {
            description 'The statistic of vrrp route.'
                        ;
            type uint32 ;
          }
          leaf ppp {
            description 'The statistic of ppp route.'
                        ;
            type uint32 ;
          }
          leaf asbrvpn {
            description 'The statistic of asbrvpn route.'
                        ;
            type uint32 ;
          }
          leaf rsvpte {
            description 'The statistic of rsvpte route.'
                        ;
            type uint32 ;
          }
          leaf user-ipaddr {
            description 'The statistic of dhcp-dtf route.'
                        ;
            type uint32 ;
          }
          leaf user-network {
            description 'The statistic of user-network route.'
                        ;
            type uint32 ;
          }
          leaf static-vrf {
            description 'The statistic of static-vrf route.'
                        ;
            type uint32 ;
          }
          leaf ipsec {
            description 'The statistic of ipsec route.'
                        ;
            type uint32 ;
          }
          leaf perVrf-label {
            description 'The statistic of perVrf-label route.'
                        ;
            type uint32 ;
          }
          leaf ps-busi {
            description 'The statistic of ps-busi route.'
                        ;
            type uint32 ;
          }
          leaf ps-user {
            description 'The statistic of ps-user route.'
                        ;
            type uint32 ;
          }
          leaf ldp-area {
            description 'The statistic of ldp-area route.'
                        ;
            type uint32 ;
          }
          leaf user-special {
            description 'The statistic of user-special route.'
                        ;
            type uint32 ;
          }
          leaf dhcp-dft {
            description 'The statistic of dhcp-dtf route.'
                        ;
            type uint32 ;
          }
          leaf dhcp-static {
            description 'The statistic of dhcp-static route.'
                        ;
            type uint32 ;
          }
          leaf nat64-sl {
            description 'The statistic of nat64-sl route.'
                        ;
            type uint32 ;
          }
          leaf ves {
            description 'The statistic of ves route.'
                        ;
            type uint32 ;
          }
          leaf total {
            description 'The statistic of all routes.'
                        ;
            type uint32 ;
          }
          ncd:select objtype ;
          ncd:select 'objtype vpnname'
                     ;
        }
      }
      container route-path-statistics {
        description 'This modul show the forwarding infor of route path.'
                    ;
        list route-path-statistic {
          description 'The statistic of all routes.'
                      ;
          key 'objtype vpnname'
              ;
          leaf objtype {
            description 'The statistic of all route path.'
                        ;
            type select-module ;
          }
          leaf vpnname {
            description 'VRF name of the route.'
                        ;
            type string {
              length 0..32 ;
            }
          }
          leaf static {
            description 'The statistic of static route path.'
                        ;
            type uint32 ;
          }
          leaf direct {
            description 'The statistic of direct route path.'
                        ;
            type uint32 ;
          }
          leaf broadcast {
            description 'The statistic of broadcast route path.'
                        ;
            type uint32 ;
          }
          leaf multicast {
            description 'The statistic of multicast route path.'
                        ;
            type uint32 ;
          }
          leaf martian {
            description 'The statistic of martian route path.'
                        ;
            type uint32 ;
          }
          leaf address {
            description 'The statistic of address route path.'
                        ;
            type uint32 ;
          }
          leaf ospf {
            description 'The statistic of ospf route path.'
                        ;
            type uint32 ;
          }
          leaf bgp {
            description 'The statistic of bgp route path.'
                        ;
            type uint32 ;
          }
          leaf rip {
            description 'The statistic of rip route path.'
                        ;
            type uint32 ;
          }
          leaf isis-l1 {
            description 'The statistic of isis-l1 route path.'
                        ;
            type uint32 ;
          }
          leaf isis-l2 {
            description 'The statistic of isis-l2 route path.'
                        ;
            type uint32 ;
          }
          leaf icmp {
            description 'The statistic of icmp route path.'
                        ;
            type uint32 ;
          }
          leaf snmp {
            description 'The statistic of snmp route path.'
                        ;
            type uint32 ;
          }
          leaf nat {
            description 'The statistic of nat route path.'
                        ;
            type uint32 ;
          }
          leaf pat {
            description 'The statistic of pat route path.'
                        ;
            type uint32 ;
          }
          leaf vrrp {
            description 'The statistic of vrrp route path.'
                        ;
            type uint32 ;
          }
          leaf ppp {
            description 'The statistic of ppp route path.'
                        ;
            type uint32 ;
          }
          leaf asbrvpn {
            description 'The statistic of asbrvpn route path.'
                        ;
            type uint32 ;
          }
          leaf rsvpte {
            description 'The statistic of rsvpte route path.'
                        ;
            type uint32 ;
          }
          leaf user-ipaddr {
            description 'The statistic of dhcp-dtf route path.'
                        ;
            type uint32 ;
          }
          leaf user-network {
            description 'The statistic of user-network route path.'
                        ;
            type uint32 ;
          }
          leaf static-vrf {
            description 'The statistic of static-vrf route path.'
                        ;
            type uint32 ;
          }
          leaf ipsec {
            description 'The statistic of ipsec route path.'
                        ;
            type uint32 ;
          }
          leaf perVrf-label {
            description 'The statistic of perVrf-label route path.'
                        ;
            type uint32 ;
          }
          leaf ps-busi {
            description 'The statistic of ps-busi route path.'
                        ;
            type uint32 ;
          }
          leaf ps-userCopy {
            description 'The statistic of ps-user route path.'
                        ;
            type uint32 ;
          }
          leaf ldp-area {
            description 'The statistic of ldp-area route path.'
                        ;
            type uint32 ;
          }
          leaf user-special {
            description 'The statistic of user-special route path.'
                        ;
            type uint32 ;
          }
          leaf dhcp-dft {
            description 'The statistic of dhcp-dtf route path.'
                        ;
            type uint32 ;
          }
          leaf dhcp-static {
            description 'The statistic of dhcp-static route path.'
                        ;
            type uint32 ;
          }
          leaf nat64-sl {
            description 'The statistic of nat64-sl route path.'
                        ;
            type uint32 ;
          }
          leaf ves {
            description 'The statistic of ves route path.'
                        ;
            type uint32 ;
          }
          leaf total {
            description 'The statistic of all route path.'
                        ;
            type uint32 ;
          }
        }
      }
      container fib-statistics {
        description 'The statistic of fib resource.'
                    ;
        leaf fib-used {
          description 'The statistic of used fib.'
                      ;
          type uint32 ;
        }
        leaf fib-free {
          description 'The statistic of unused fib.'
                      ;
          type uint32 ;
        }
      }
      container route-summary-alls {
        leaf capacity {
          description 'The performance parameters of IPv4 route'
                      ;
          type uint32 ;
        }
        leaf used-route-count {
          description 'The used count of IPv4 route'
                      ;
          type uint32 ;
          default 0 ;
        }
        list route-summary-all {
          description 'The count of IPv4 route for global and all VRF,but do no'
                    + 't support the query conditions'
                      ;
          key 'objtype route-vpnname'
              ;
          leaf objtype {
            description 'The select module of IPv4 route statistic for global a'
                      + 'nd all VRF.'
                        ;
            type select-module ;
          }
          leaf route-vpnname {
            description 'VRF name of the route.'
                        ;
            type string {
              length 0..32 ;
            }
          }
          leaf route-count {
            description 'The count of IPv4 route for global or VRF'
                        ;
            type uint32 ;
            default 0 ;
          }
        }
        ncd:revise-date 2016-10-26 ;
      }
    }
    container rtm6 {
      container route6-statistics {
        description 'This modul show the statistic infor of ipv6 route.'
                    ;
        list route6-statistic {
          description 'The statistic of routes.'+"\n"
                    + 'For statistic of global route,need select objtype(1).'+"\n"
                    + 'For statistic of the vpn route,need select objtype(2) an'
                    + 'd vpnname.'+"\n"
                    + 'For statistic of all route,need select objtype(3).'
                      ;
          key 'objtype vpnname'
              ;
          leaf objtype {
            description 'The select module of route statistic.'
                        ;
            type select-module ;
          }
          leaf vpnname {
            description 'The vpn name.'
                        ;
            type string {
              length 0..32 ;
            }
          }
          leaf kernel {
            description 'The statistic of kernel route.'
                        ;
            type uint32 ;
          }
          leaf connect {
            description 'The statistic of connect route.'
                        ;
            type uint32 ;
          }
          leaf static {
            description 'The statistic of static route.'
                        ;
            type uint32 ;
          }
          leaf ripng {
            description 'The statistic of ripng route.'
                        ;
            type uint32 ;
          }
          leaf ospfv3 {
            description 'The statistic of ospfv3 route.'
                        ;
            type uint32 ;
          }
          leaf bgp {
            description 'The statistic of bgp route.'
                        ;
            type uint32 ;
          }
          leaf isis_l1 {
            description 'The statistic of isis_l1 route.'
                        ;
            type uint32 ;
          }
          leaf isis_l2 {
            description 'The statistic of isis_l2 route.'
                        ;
            type uint32 ;
          }
          leaf icmp {
            description 'The statistic of icmp route.'
                        ;
            type uint32 ;
          }
          leaf multicast {
            description 'The statistic of multicast route.'
                        ;
            type uint32 ;
          }
          leaf user_ipaddr {
            description 'The statistic of user_ipaddr route.'
                        ;
            type uint32 ;
          }
          leaf vrrp {
            description 'The statistic of vrrp route.'
                        ;
            type uint32 ;
          }
          leaf ppp {
            description 'The statistic of ppp route.'
                        ;
            type uint32 ;
          }
          leaf nd {
            description 'The statistic of nd route.'
                        ;
            type uint32 ;
          }
          leaf address {
            description 'The statistic of address route.'
                        ;
            type uint32 ;
          }
          leaf dhcp {
            description 'The statistic of dhcp route.'
                        ;
            type uint32 ;
          }
          leaf sf_nat64 {
            description 'The statistic of sf_nat64 route.'
                        ;
            type uint32 ;
          }
          leaf sl_nat64 {
            description 'The statistic of sl_nat64 route.'
                        ;
            type uint32 ;
          }
          leaf aftr {
            description 'The statistic of aftr route.'
                        ;
            type uint32 ;
          }
          leaf ps-busi {
            description 'The statistic of ps-busi route.'
                        ;
            type uint32 ;
            ncd:revise-date 2015-04-15 ;
          }
          leaf ps-user {
            description 'The statistic of ps-user route.'
                        ;
            type uint32 ;
            ncd:revise-date 2015-04-15 ;
          }
          leaf ldp-area {
            description 'The statistic of ldp-area route.'
                        ;
            type uint32 ;
            ncd:revise-date 2015-05-18 ;
          }
          leaf user-network {
            description 'The statistic of user-network route.'
                        ;
            type uint32 ;
            ncd:revise-date 2016-04-16 ;
          }
          leaf user-special {
            description 'The statistic of user-special route.'
                        ;
            type uint32 ;
            ncd:revise-date 2016-04-16 ;
          }
          leaf total {
            description 'The statistic of total route.'
                        ;
            type uint32 ;
          }
          ncd:select objtype ;
          ncd:select 'objtype vpnname'
                     ;
        }
      }
      container route6-path-statistic {
        description 'This modul show the statistic infor of ipv6 route path.'
                    ;
        list route6-path-statistic {
          description 'The statistic of all route path.'
                      ;
          key 'objtype vpnname'
              ;
          leaf objtype {
            description 'The statistic of all route path.'
                        ;
            type select-module ;
          }
          leaf vpnname {
            description 'The vpn name.'
                        ;
            type string {
              length 0..32 ;
            }
          }
          leaf kernel {
            description 'The statistic of kernel route.'
                        ;
            type uint32 ;
          }
          leaf connect {
            description 'The statistic of connect route.'
                        ;
            type uint32 ;
          }
          leaf static {
            description 'The statistic of static route.'
                        ;
            type uint32 ;
          }
          leaf ripng {
            description 'The statistic of ripng route.'
                        ;
            type uint32 ;
          }
          leaf ospfv3 {
            description 'The statistic of ospfv3 route.'
                        ;
            type uint32 ;
          }
          leaf bgp {
            description 'The statistic of bgp route.'
                        ;
            type uint32 ;
          }
          leaf isis_l1 {
            description 'The statistic of isis_l1 route.'
                        ;
            type uint32 ;
          }
          leaf isis_l2 {
            description 'The statistic of isis_l2 route.'
                        ;
            type uint32 ;
          }
          leaf icmp {
            description 'The statistic of icmp route.'
                        ;
            type uint32 ;
          }
          leaf multicast {
            description 'The statistic of multicast route.'
                        ;
            type uint32 ;
          }
          leaf user_ipaddr {
            description 'The statistic of user_ipaddr route.'
                        ;
            type uint32 ;
          }
          leaf vrrp {
            description 'The statistic of vrrp route.'
                        ;
            type uint32 ;
          }
          leaf ppp {
            description 'The statistic of ppp route.'
                        ;
            type uint32 ;
          }
          leaf nd {
            description 'The statistic of nd route.'
                        ;
            type uint32 ;
          }
          leaf address {
            description 'The statistic of address route.'
                        ;
            type uint32 ;
          }
          leaf dhcp {
            description 'The statistic of dhcp route.'
                        ;
            type uint32 ;
          }
          leaf sf_nat64 {
            description 'The statistic of sf_nat64 route.'
                        ;
            type uint32 ;
          }
          leaf sl_nat64 {
            description 'The statistic of sl_nat64 route.'
                        ;
            type uint32 ;
          }
          leaf aftr {
            description 'The statistic of aftr route.'
                        ;
            type uint32 ;
          }
          leaf ps-busi {
            description 'The statistic of ps-busi route path.'
                        ;
            type uint32 ;
            ncd:revise-date 2015-04-15 ;
          }
          leaf ps-user {
            description 'The statistic of ps-user route path.'
                        ;
            type uint32 ;
            ncd:revise-date 2015-04-15 ;
          }
          leaf ldp-area {
            description 'The statistic of ldp-area route path.'
                        ;
            type uint32 ;
            ncd:revise-date 2015-05-18 ;
          }
          leaf user-network {
            description 'The statistic of user-network route path.'
                        ;
            type uint32 ;
            ncd:revise-date 2016-04-16 ;
          }
          leaf user-special {
            description 'The statistic of user-special route path.'
                        ;
            type uint32 ;
            ncd:revise-date 2016-04-16 ;
          }
          leaf total {
            description 'The statistic of total route.'
                        ;
            type uint32 ;
          }
        }
      }
      container route6 {
        description 'This modul show the forwarding infor of ipv6 route.'
                    ;
        list iproute6 {
          description 'This modul show the forwarding infor of ipv6 route.'
                      ;
          key 'objtype route6-vpnname route6-owner route6-dest route6-prefixlen'
            + ' route6-is-exact-match route6-nexthop route6-ifname'
              ;
          leaf objtype {
            description 'The select module of fib.'
                        ;
            type select-module ;
          }
          leaf route6-vpnname {
            description 'VRF name of the route.'
                        ;
            type string {
              length 0..32 ;
            }
          }
          leaf route6-owner {
            description 'The protocol of route.'
                        ;
            type ipv6-owner-type ;
          }
          leaf route6-dest {
            description 'The destination address of this route.'
                        ;
            type ncd:ipv6-address ;
          }
          leaf route6-prefixlen {
            description 'The mask length of this route.'
                        ;
            type uint32 {
              range 0..128 ;
            }
          }
          leaf route6-is-exact-match {
            description 'Whether exact match route.'
                        ;
            type boolean ;
          }
          leaf route6-nexthop {
            description 'The nexthop of route.'
                        ;
            type ncd:ipv6-address ;
          }
          leaf route6-ifname {
            description 'The local interface name through which the next hop of'
                      + ' this route should be reached.'
                        ;
            type string {
              length 0..32 ;
            }
          }
          leaf route6-priority {
            description 'The priority of route.'
                        ;
            type uint32 ;
          }
          leaf route6-metric {
            description 'The metric of route.'
                        ;
            type uint32 ;
          }
          leaf route6-has-frr {
            description 'Route frr relation falg.'
                        ;
            type boolean ;
          }
          leaf route6-is-valid {
            description 'route valid flag.'
                        ;
            type boolean ;
          }
          leaf route6-is-backup {
            description 'Route is frr back path.'
                        ;
            type empty ;
          }
          ncd:select objtype ;
          ncd:select 'objtype route6-vpnname'
                     ;
          ncd:select 'objtype route6-owner'
                     ;
          ncd:select 'objtype route6-vpnname route6-owner'
                     ;
          ncd:select 'objtype route6-dest route6-prefixlen route6-is-exact-match'
                     ;
          ncd:select 'objtype route6-vpnname route6-dest route6-prefixlen route'
                   + '6-is-exact-match'
                     ;
          ncd:select 'objtype route6-vpnname route6-dest route6-prefixlen'
                     ;
          ncd:select 'objtype route6-dest route6-prefixlen'
                     ;
        }
      }
      container frr6 {
        list ipfrr6 {
          description 'This modul show the forwarding infor of ipv6 frr.'+"\n"
                    + 'For the frr of global,need select objtype(1),route6-dest'
                    + ',route6-prefixlen.'+"\n"
                    + 'For the frr of the vpn,need select objtype(2),route6-vpn'
                    + 'name,route6-dest,route6-prefixlen.'+"\n"
                    + 'For all frr of global,need select objtype(1).'+"\n"
                    + 'For all frr of the vpn,need select objtype(2),route6-vpn'
                    + 'name.'+"\n"
                    + 'For all frr of global and all vpn,need select objtype(3)'
                    + '.'
                      ;
          key 'objtype route6-vpnname route6-dest route6-prefixlen'
              ;
          leaf objtype {
            description 'The select module of ipv6 frr.'
                        ;
            type select-module ;
          }
          leaf route6-vpnname {
            description 'VRF name of the route.'
                        ;
            type string {
              length 0..32 ;
            }
          }
          leaf route6-dest {
            description 'The destination IP address of this route.'
                        ;
            type ncd:ipv6-address ;
          }
          leaf route6-prefixlen {
            description 'The mask length of this route.'
                        ;
            type uint32 {
              range 0..128 ;
            }
          }
          leaf route6-master-nexthop {
            description 'The nexthop of master route.'
                        ;
            type ncd:ipv6-address ;
          }
          leaf route6-master-ifname {
            description 'The local interface name through which the master next'
                      + ' hop of this route should be reached.'
                        ;
            type string {
              length 0..32 ;
            }
          }
          leaf route6-master-priority {
            description 'The priority of master route.'
                        ;
            type uint32 ;
          }
          leaf route6-master-metric {
            description 'The metric of master route.'
                        ;
            type uint32 ;
          }
          leaf route6-master-owner {
            description 'The protocol of master route.'
                        ;
            type ipv6-owner-type ;
          }
          leaf route6-master-label {
            description 'The out label of master route.'
                        ;
            type uint32 ;
          }
          leaf route6-master-is-pe {
            description 'Whether the next hop of master route is PE.'
                        ;
            type boolean ;
          }
          leaf route6-slave-nexthop {
            description 'The nexthop of slave route.'
                        ;
            type ncd:ipv6-address ;
          }
          leaf route6-slave-ifname {
            description 'The local interface name through which the slave next '
                      + 'hop of this route should be reached.'
                        ;
            type string {
              length 0..32 ;
            }
          }
          leaf route6-slave-priority {
            description 'The priority of slave route.'
                        ;
            type uint32 ;
          }
          leaf route6-slave-metric {
            description 'The metric of slave route.'
                        ;
            type uint32 ;
          }
          leaf route6-slave-owner {
            description 'The protocol of slave route.'
                        ;
            type ipv6-owner-type ;
          }
          leaf route6-slave-label {
            description 'The out label of slave route.'
                        ;
            type uint32 ;
          }
          leaf route6-slave-is-pe {
            description 'Whether the next hop of slave route is PE.'
                        ;
            type boolean ;
          }
          leaf route6-frr-status {
            description 'Forwarding status of frr.'
                        ;
            type forward-status ;
          }
          ncd:select objtype ;
          ncd:select 'objtype route6-vpnname'
                     ;
          ncd:select 'objtype route6-dest route6-prefixlen'
                     ;
          ncd:select 'objtype route6-vpnname route6-dest route6-prefixlen'
                     ;
        }
      }
      container route-summary-alls {
        leaf capacity {
          description 'The performance parameters of IPv6 route'
                      ;
          type uint32 ;
        }
        leaf used-route-count {
          description 'The used count of IPv6 route'
                      ;
          type uint32 ;
          default 0 ;
        }
        list route-summary-all {
          description 'The count of IPv6 route for global and all VRF,but do no'
                    + 't support the query conditions'
                      ;
          key 'objtype route-vpnname'
              ;
          leaf objtype {
            description 'The select module of IPv6 route statistic for global a'
                      + 'nd all VRF.'
                        ;
            type select-module ;
          }
          leaf route-vpnname {
            description 'VRF name of the route.'
                        ;
            type string {
              length 0..32 ;
            }
          }
          leaf route-count {
            description 'The count of IPv6 route for global or VRF'
                        ;
            type uint32 ;
            default 0 ;
          }
        }
        ncd:revise-date 2016-10-26 ;
      }
    }
  }
  container configuration {
    description 'This modul config ldsh precision configuration.'
                ;
    container rtm {
      description 'This module config information about routing table managemen'
                + 't(rtm).'
                  ;
      container ldsh {
        description 'This module config information aboutldsh.'
                    ;
        container bandwidth {
          description 'Specifies ldsh response outer ldsh bandwidth changes.'
                      ;
          leaf unaware {
            description 'Specifies ldsh response outer ldsh bandwidth changes.'
                        ;
            type empty ;
          }
        }
        container wtr {
          description 'Config wtr time(1-12mim) of ldsh.'
                      ;
          presence 'ldsh wtr time'
                   ;
          leaf time {
            description 'Config wtr time of ldsh.'
                        ;
            type uint8 {
              range 1..12 {
                description 'Ecmp wtr time is 1 to 12 min.'
                            ;
              }
            }
            units min ;
            mandatory true ;
          }
        }
        container hash {
          description 'Config information about ldsh hash configuration.'
                      ;
          container ldsh-hash-scramble {
            description 'This module set hash scramble.'
                        ;
            leaf scramble-value {
              description 'This module set hash scramble.'
                          ;
              type uint32 {
                range 1..65535 ;
              }
              default 1 ;
            }
          }
          container ldsh-hash-fields {
            description 'This module config the hash configuration of ldsh.'
                        ;
            list ldsh-hash-fields {
              description 'This module config the hash configuration of ldsh.'+"\n"
                        + 'When config ipv4 enable,ipv6 need be configed false.'
                        + ''+"\n"
                        + 'When config ipv6 enable,ipv4 need be configed false.'
                          ;
              key 'ipv4 ipv6 board-name'
                  ;
              leaf ipv4 {
                description 'Config ipv4 address family.'
                            ;
                type boolean ;
              }
              leaf ipv6 {
                description 'Config ipv6 address family.'
                            ;
                type boolean ;
              }
              leaf board-name {
                description 'Config board name,and "global" meaning config all '
                          + 'boards.'
                            ;
                type string {
                  length 1..33 ;
                }
              }
              choice hash-element {
                description 'Config information participating hash operation.'
                            ;
                mandatory true ;
                case l3 {
                  description 'Config l3 information of upstream flow participa'
                            + 'ting hash operation.'
                              ;
                  leaf l3 {
                    description 'Config l3 information of upstream flow partici'
                              + 'pating hash operation.'
                                ;
                    type empty ;
                    mandatory true ;
                  }
                }
                case l4 {
                  description 'Config l4 information of upstream flow participa'
                            + 'ting hash operation.'
                              ;
                  leaf l4 {
                    description 'Config l4 information of upstream flow partici'
                              + 'pating hash operation.'
                                ;
                    type empty ;
                    mandatory true ;
                  }
                }
                case l3src {
                  description 'Config l3 original information of upstream flow '
                            + 'participating hash operation.'
                              ;
                  leaf l3src {
                    description 'Config l3 original information of upstream flo'
                              + 'w participating hash operation.'
                                ;
                    type empty ;
                    mandatory true ;
                  }
                }
              }
            }
          }
          container ldsh-hash-key-board {
            description 'This module config the hash precise configuration of l'
                      + 'dsh for the board.'
                        ;
            list ldsh-hash-key-board {
              description 'This module config the hash precise configuration of'
                        + ' ldsh for the board.'
                          ;
              key 'ipv6 board-name'
                  ;
              leaf ipv6 {
                description 'Config ipv6 address family.'+"\n"
                          + 'It must be selected temporarily.'
                            ;
                type boolean ;
              }
              leaf board-name {
                description 'Config board name.'
                            ;
                type string {
                  length 1..33 {
                    description "The board name can't be null."
                                ;
                  }
                }
              }
              leaf lsb {
                description 'Config low byte of ip address participating hash o'
                          + 'peration.'
                            ;
                type boolean ;
                mandatory true ;
              }
              leaf msb {
                description 'Config high byte of ip address participating hash '
                          + 'operation.'
                            ;
                type boolean ;
                mandatory true ;
              }
            }
          }
          container ldsh-hash-algorithm {
            description 'Config hash operation algorithm.'
                        ;
            list ldsh-hash-algorithm {
              description 'Config hash operation algorithm.'
                          ;
              key board-name ;
              leaf board-name {
                description 'Config board name,and "global" meaning config all '
                          + 'boards.'
                            ;
                type string {
                  length 1..33 ;
                }
              }
              choice algorithm {
                description 'Choiec crc configuration.'
                            ;
                mandatory true ;
                case crc16 {
                  description 'Config crc16 algorithm.'
                              ;
                  leaf crc16 {
                    description 'Config crc16 algorithm.'
                                ;
                    type empty ;
                    mandatory true ;
                  }
                }
                case crc32 {
                  description 'Config crc16 algorithm.'
                              ;
                  leaf crc32 {
                    description 'Config crc32 algorithm.'
                                ;
                    type empty ;
                    mandatory true ;
                  }
                }
              }
            }
          }
          container ldsh-hash-key-global {
            description 'This module config the hash precise configuration of l'
                      + 'dsh for all boards.'
                        ;
            list ldsh-hash-key-global {
              description 'This module config the hash precise configuration of'
                        + ' ldsh for all boards.'
                          ;
              key ipv6 ;
              leaf ipv6 {
                description 'Config ipv6 address family.'+"\n"
                          + 'It must be selected temporarily.'
                            ;
                type boolean ;
              }
              leaf lsb {
                description 'Config low byte of ip address participating hash o'
                          + 'peration.'
                            ;
                type boolean ;
                mandatory true ;
              }
              leaf msb {
                description 'Config high byte of ip address participating hash '
                          + 'operation.'
                            ;
                type boolean ;
                mandatory true ;
              }
            }
          }
          container mpls-ldsh-hash-fields {
            description 'This module config the hash configuration of mpls ldsh.'
                        ;
            list mpls-ldsh-hash-field {
              description 'This module config the hash configuration of mpls ld'
                        + 'sh.'
                          ;
              key board-name ;
              leaf board-name {
                description 'Config board name,and "global" meaning config all '
                          + 'boards.'
                            ;
                type string {
                  length 1..33 ;
                }
              }
              choice hash-element {
                description 'Config information participating hash operation.'
                            ;
                mandatory true ;
                case ip-l3 {
                  description 'Config the ip ternary group information as hash '
                            + 'factor.'
                              ;
                  leaf ip-l3 {
                    description 'Config the ip ternary group information as has'
                              + 'h factor.'
                                ;
                    type empty ;
                    mandatory true ;
                  }
                }
                case ip-l4 {
                  description 'Config the ip quintuple group information as has'
                            + 'h factor.'
                              ;
                  leaf ip-l4 {
                    description 'Config the ip quintuple group information as h'
                              + 'ash factor.'
                                ;
                    type empty ;
                    mandatory true ;
                  }
                }
                case label {
                  description 'Config label information as hash factor.'
                              ;
                  leaf label {
                    description 'Config label information as hash factor.'
                                ;
                    type empty ;
                    mandatory true ;
                  }
                }
              }
            }
          }
        }
      }
    }
  }
}
