module zxr10-pppoe-client {
  namespace 'http://www.zte.com.cn/zxr10/netconf/schema/rosng/pppoe-client'
            ;
  prefix pppoe-client ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe PPPoE Client(PPPoE-C)'
              ;
  revision 2015-07-28 {
    description 'Change config of state from true to false'
                ;
  }
  revision 2014-05-26 {
    description 'The initial version'
                ;
  }
  container configuration {
    description 'Describe the configuration of PPPoE-C'
                ;
    container pppoe-client {
      description 'Configuration data of PPPoE-C'
                  ;
      container padiattr {
        description 'Configure PADI packet parameters'
                    ;
        list padi {
          description 'Configure PADI packet parameters'
                      ;
          key ifname ;
          leaf ifname {
            description 'This value identifies the PPPoE interface name.This at'
                      + 'tribute is created by Interface Management'
                        ;
            type ncd:ifname ;
          }
          leaf timeout {
            description 'Base interval for PADI packet resending'
                        ;
            type uint32 {
              range 1..30 ;
            }
            units seconds ;
            default 5 ;
          }
          leaf repeat {
            description 'Maximum repetition for PADI packet resending'
                        ;
            type uint32 {
              range 3..10 ;
            }
            default 5 ;
          }
        }
      }
      container padrattr {
        description 'Configure PADR packet parameters'
                    ;
        list padr {
          description 'Configure PADR packet parameters'
                      ;
          key ifname ;
          leaf ifname {
            description 'This value identifies the PPPoE interface name.This at'
                      + 'tribute is created by Interface Management'
                        ;
            type ncd:ifname ;
          }
          leaf timeout {
            description 'Base interval for PADR packet resending'
                        ;
            type uint32 {
              range 1..30 ;
            }
            units seconds ;
            default 5 ;
          }
          leaf repeat {
            description 'Maximum repetition for PADR packet resending'
                        ;
            type uint32 {
              range 3..10 ;
            }
            default 5 ;
          }
        }
      }
      container padoattr {
        description 'Configure PADO packet parameters'
                    ;
        list pado {
          description 'Configure PADO packet parameters'
                      ;
          key ifname ;
          leaf ifname {
            description 'This value identifies the PPPoE interface name.This at'
                      + 'tribute is created by Interface Management'
                        ;
            type ncd:ifname ;
          }
          leaf timeout {
            description 'Maximum time for PADO packet collecting'
                        ;
            type uint32 {
              range 1..10 ;
            }
            units seconds ;
            default 2 ;
          }
        }
      }
    }
  }
  container state {
    config false ;
    description 'Describe the state of PPPoE-C'
                ;
    container pppoe-client {
      description 'State data of PPPoE-C'
                  ;
      container sessions {
        description 'Session information of PPPoE-C'
                    ;
        list session {
          description 'Session information'
                      ;
          key ifname ;
          leaf ifname {
            description 'This value identifies the PPPoE interface name.This at'
                      + 'tribute is created by Interface Management'
                        ;
            type ncd:ifname ;
          }
          leaf session-id {
            description 'session id'
                        ;
            type uint16 ;
          }
          leaf src-mac-address {
            description 'Source MAC address'
                        ;
            type ncd:mac-address ;
          }
          leaf dst-mac-address {
            description 'Destination MAC address'
                        ;
            type ncd:mac-address ;
          }
        }
      }
    }
  }
}
