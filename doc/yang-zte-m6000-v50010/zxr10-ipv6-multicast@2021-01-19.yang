module zxr10-ipv6-multicast {
  namespace 'http://www.zte.com.cn/zxr10/netconf/schema/rosng/ipv6-multicast'
            ;
  prefix ipv6-multicast ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module of describing IPv6 multicast.'
              ;
  revision 2021-01-19 {
    description '1.Add the leaf of ecmp-select-reference-bandwidth: /configurat'
              + 'ion/ipv6-multicast/v6-multicast/global/;'+"\n"
              + '2.Add the leaf of ecmp-select-reference-bandwidth: /configurat'
              + 'ion/ipv6-multicast/vrf-v6-multicasts/vrf-v6-multicast/;'
                ;
  }
  revision 2020-12-22 {
    description 'Add the leaf of bsl: /configuration/ipv6-multicast/v6-multicas'
              + 't/biers/bier;'
                ;
  }
  revision 2020-10-27 {
    description 'Add the containers /configuration/ipv6-multicast/v6-multicast/'
              + 'spmsi-bier-infos; /configuration/ipv6-multicast/vrf-v6-multica'
              + 'sts/vrf-v6-multicast/spmsi-bier-infos;'
                ;
  }
  revision 2020-09-21 {
    description '1.modify the range of the leaf: /configuration/ipv6-multicast/'
              + 'v6-multicast/global/multipath;'+"\n"
              + '2.modify the range of the leaf: /configuration/ipv6-multicast/'
              + 'vrf-v6-multicasts/vrf-v6-multicast/multipath;'+"\n"
              + '3.modify the name and description of enum item of the leaf: /c'
              + 'onfiguration/ipv6-multicast/v6-multicast/global/multipath;'+"\n"
              + '4.modify the name and description of enum item of the leaf: /c'
              + 'onfiguration/ipv6-multicast/vrf-v6-multicasts/vrf-v6-multicast'
              + '/multipath.'
                ;
  }
  revision 2020-06-20 {
    description 'Add the enumeration of the leafs: '+"\n"
              + '/configuration/ipv6-multicast/vrf-v6-multicasts/vrf-v6-multica'
              + 'st/mvpn/provider-tunnel;'+"\n"
              + '/state/ipv6-multicast/public/mvpn/mtunnels/mtunnel/tunnel-type'
              + ';'+"\n"
              + '/state/ipv6-multicast/private/mvpn/instances/instance/mtunnel-'
              + 'type;'+"\n"
              + '/state/ipv6-multicast/private/mvpn/mtibs/mtib/tunnel-type;'+"\n"
              + 'Add the leafs /configuration/ipv6-multicast/vrf-v6-multicasts/'
              + 'vrf-v6-multicast/mvpn/sub-domain-id;'+"\n"
              + '/configuration/ipv6-multicast/vrf-v6-multicasts/vrf-v6-multica'
              + 'st/mvpn/bfd-enable;'+"\n"
              + '/configuration/ipv6-multicast/vrf-v6-multicasts/vrf-v6-multica'
              + 'st/mvpn/bfd-template;'+"\n"
              + '/configuration/ipv6-multicast/v6-multicast/global/mvpn-frr-pol'
              + 'icy;'+"\n"
              + '/configuration/ipv6-multicast/v6-multicast/global/mvpn-frr-egr'
              + 'ess-wtr;'+"\n"
              + 'Add the list /state/ipv6-multicast/public/mroutes/mroute;'+"\n"
              + '/state/ipv6-multicast/private/mroutes/mroute/bier-info;'+"\n"
              + '/state/ipv6-multicast/private/mroutes/mroute/vpn-extranet;'+"\n"
              + 'Add the BIER description:/state/ipv6-multicast/private/mvpn/au'
              + 'to-discovery-routes;'+"\n"
              + 'Add the containers /configuration/ipv6-multicast/v6-multicast/'
              + 'biers;'+"\n"
              + '/configuration/ipv6-multicast/v6-multicast/mvpn;'+"\n"
              + '/state/ipv6-multicast/public/mvpn/instance;'+"\n"
              + '/state/ipv6-multicast/public/mvpn/auto-discovery-route;'+"\n"
              + '/state/ipv6-multicast/public/mvpn/public-auto-discovery-route;'
              + ''+"\n"
              + '/state/ipv6-multicast/public/mvpn/mribs;'+"\n"
              + '/state/ipv6-multicast/public/mvpn/ad-summary;'+"\n"
              + '/state/ipv6-multicast/public/mvpn/public-ad-summary;'+"\n"
              + '/state/ipv6-multicast/public/mvpn/protect-groups;'+"\n"
              + 'Modify the DerivedType to string-all of the leafs:'+"\n"
              + '/state/ipv6-multicast/public/mvpn/mtunnels/mtunnel/vrf-name;'+"\n"
              + '/state/ipv6-multicast/public/mvpn/mtunnels/mtunnel/mrts/mrt/su'
              + 'b-vrf-name;'
                ;
  }
  revision 2019-12-31 {
    description '1.modify the range and description of the leaf:/state/ipv6-mul'
              + 'ticast/public/mvpn/mtunnels/mtunnel/vrf-name.'
                ;
  }
  revision 2019-11-28 {
    description 'Add the enumeration of the leaf:/configuration/ipv6-multicast/'
              + 'vrf-v6-multicasts/vrf-v6-multicast/mvpn-upstream-pe-select'
                ;
  }
  revision 2019-11-06 {
    description 'Add the leafs of mvpn-spt-only/mvpn-send-site-only/mvpn-receiv'
              + 'e-site-only/mvpn-spmsi-tunnel: /configuration/ipv6-multicast/v'
              + 'rf-v6-multicasts/vrf-v6-multicast;'
                ;
  }
  revision 2019-09-29 {
    description '1,Add nexthop-path-lists and rpf-vector-path-lists containers '
              + 'to /configuration/ipv6-multicast/v6-multicast.'
                ;
  }
  revision 2019-08-29 {
    description 'Add router-id container to /configuration/ipv6-multicast/v6-mu'
              + 'lticast and /configuration/ipv6-multicast/vrf-v6-multicasts/vr'
              + 'f-v6-multicast.'
                ;
  }
  revision 2019-07-15 {
    description '1,Add longest-match,static-first,downstream-limit leaf nodes t'
              + 'o: /configuration/ipv6-multicast/v6-multicast/global;'+"\n"
              + '2,Add boundarys container to: /configuration/ipv6-multicast/v6'
              + '-multicast;'+"\n"
              + '3,Add mvpn-wildcards-spmsi,longest-match,static-first,mvpn-ups'
              + 'tream-pe-select leaf nodes to: /configuration/ipv6-multicast/v'
              + 'rf-v6-multicasts/vrf-v6-multicast;'+"\n"
              + '4,Add mvpn-spmsi-aggregation container to: /configuration/ipv6'
              + '-multicast/vrf-v6-multicasts/vrf-v6-multicast;'+"\n"
              + '5,Add mtunnels container to: /state/ipv6-multicast/public/mvpn'
              + ';'+"\n"
              + '6,Add mdts and mdt-tlvs containers to: /state/ipv6-multicast/p'
              + 'rivate/mvpn;'
                ;
  }
  revision 2019-04-12 {
    description 'Add the containers of p2mp-template and mvpn-frr-peer-bfd-ipv4'
              + 's: /configuration/ipv6-multicast/vrf-v6-multicasts/vrf-v6-mult'
              + 'icast;'+"\n"
              + 'Add the leafs of mvpn-frr-policy/mvpn-frr-detect-type/mvpn-frr'
              + '-ingress-wtr/mvpn-frr-egress-wtr: /configuration/ipv6-multicas'
              + 't/vrf-v6-multicasts/vrf-v6-multicast;'
                ;
  }
  revision 2019-02-25 {
    description '1.Add the leaf of ecmp-select-cost-first: /configuration/ipv6-'
              + 'multicast/v6-multicast/ecmp-select-cost-first;'+"\n"
              + '2.Add the leaf of ecmp-select-cost-first: /configuration/ipv6-'
              + 'multicast/vrf-v6-multicasts/vrf-v6-multicast/ecmp-select-cost-'
              + 'first;'+"\n"
              + '3.Add the container of mtunnel: /configuration/ipv6-multicast/'
              + 'vrf-v6-multicasts/vrf-v6-multicast/mtunnel;'+"\n"
              + '4.Add the container of mdt-default: /configuration/ipv6-multic'
              + 'ast/vrf-v6-multicasts/vrf-v6-multicast/mdt-default;'+"\n"
              + '5.Add the container of mdt-data: /configuration/ipv6-multicast'
              + '/vrf-v6-multicasts/vrf-v6-multicast/mdt-data;'
                ;
  }
  revision 2019-01-21 {
    description 'Add the leaf of mvpn-switchover-holdtime: /configuration/ipv6-'
              + 'multicast/vrf-v6-multicasts/vrf-v6-multicast;'
                ;
  }
  revision 2018-12-11 {
    description '1.add the leaf of multicast-address-rfc7371: /configuration/ip'
              + 'v6-multicast/v6-multicast/global;'
                ;
  }
  revision 2018-11-14 {
    description 'Add the container of smdms: /configuration/ipv6-multicast/mult'
              + 'icast/'
                ;
  }
  revision 2018-08-10 {
    description 'Add the enumeration of the leaf: /configuration/ipv6-multicast'
              + '/vrf-v6-multicasts/vrf-v6-multicast/mvpn/provider-tunnel;'
                ;
  }
  revision 2018-08-03 {
    description '1.modify the range of the leaf:/configuration/ipv6-multicast/v'
              + '6-multicast/global/mroute6-limit.'+"\n"
              + '2.modify the range of the leaf:/configuration/ipv6-multicast/v'
              + '6-multicast/global/mroute6-limit-p-instance.'+"\n"
              + '3.modify the range of the leaf:/configuration/ipv6-multicast/v'
              + 'rf-v6-multicasts/vrf-v6-multicast/mroute6-limit-c-instance.'
                ;
  }
  revision 2017-11-14 {
    description 'Add the labels of 6100 for the features of mvpn-cross-as and m'
              + 'vpn-switch-threshold;'
                ;
  }
  revision 2017-06-21 {
    description '1.Add the feature of mvpn-switch-threshold.'+"\n"
              + '2.Add If_Features of mvpn-switch-threshold for /configuration/'
              + 'ipv6-multicast/vrf-v6-multicasts/vrf-v6-multicast/mvpn-switcho'
              + 'ver-threshold;'
                ;
  }
  revision 2017-06-05 {
    description 'Add the leaf of mvpn-switchover-threshold-infinity: /configura'
              + 'tion/ipv6-multicast/vrf-v6-multicasts/vrf-v6-multicast;'+"\n"
              + 'Add the labels of 15K and M6000-S for the feature of mvpn-cros'
              + 's-as;'+"\n"
              + 'Delete the If_Features for the leaf of /configuration/ipv6-mul'
              + 'ticast/vrf-v6-multicasts/vrf-v6-multicast/mvpn-switchover-inte'
              + 'rval;'
                ;
  }
  revision 2017-02-21 {
    description 'Add the container of mvpn-switchover-threshold: /configuration'
              + '/ipv6-multicast/vrf-v6-multicasts/vrf-v6-multicast;'
                ;
  }
  revision 2016-11-29 {
    description '1.add the leaves of mvpn-switchover-interval: /configuration/i'
              + 'pv6-multicast/vrf-multicasts/vrf-multicast;'+"\n"
              + '2.obsolete the container of ad-routes and add the container of'
              + ' auto-discovery-routes: /state/ipv6-multicast/private/mvpn;'+"\n"
              + '3.add the description of tunnel-type: /state/ipv6-multicast/pr'
              + 'ivate/mvpn/mtibs/mtib;'+"\n"
              + '4.modify the description and type of sub-vrf-name, add the lea'
              + 'f of sub-tunnel-state and select: /state/ipv6-multicast/privat'
              + 'e/mvpn/mtibs/mtib/multi-imports/multi-import;'+"\n"
              + '5.obsolete the containers of spmsi-ads and leaf-ads:/state/mul'
              + 'ticast/private/mvpn/mribs/mrib/;'+"\n"
              + '6.add the containers of spmsi-auto-discoveries and leaf-auto-d'
              + 'iscoveries: /state/multicast/private/mvpn/mribs/mrib/;'+"\n"
              + '7.modify description of source-active, xg-join, sg-join: /stat'
              + 'e/ipv6-multicast/private/mvpn/mribs/mrib/source-actives/source'
              + '-active, /state/ipv6-multicast/private/mvpn/mribs/mrib/xg-join'
              + 's/xg-join and /state/ipv6-multicast/private/mvpn/mribs/mrib/sg'
              + '-joins/sg-join;'+"\n"
              + '8.add the container of ad-summarys: /state/ipv6-multicast/priv'
              + 'ate/mvpn/;'+"\n"
              + '9.add the feature of mvpn-cross-as.'
                ;
  }
  revision 2015-12-09 {
    description '1.add containers of nexthop-fallbacks: /configuration/ipv6-mul'
              + 'ticast/v6-multicast/ and /configuration/ipv6-multicast/vrf-v6-'
              + 'multicasts/vrf-v6-multicast/.'+"\n"
              + '2.add the leaf of fallback-vrf: /state/ipv6-multicast/public/m'
              + 'routes/mroute/, /state/ipv6-multicast/public/nexthops/nexthop/'
              + ', /state/ipv6-multicast/private/mroutes/mroute/ and /state/ipv'
              + '6-multicast/private/nexthops/nexthop/.'+"\n"
              + '3.add the list of fallback-extranet: /state/ipv6-multicast/pub'
              + 'lic/mroutes/mroute/ and  /state/ipv6-multicast/private/mroutes'
              + '/mroute/.'
                ;
  }
  revision 2015-11-26 {
    description '1.add mroute6-limit-p-instance leaf node to /configuration/ipv'
              + '6-multicast/v6-multicast/global/.'+"\n"
              + '2.add mroute6-limit-c-instance leaf node to /configuration/ipv'
              + '6-multicast/vrf-v6-multicasts/vrf-v6-multicast/.'+"\n"
              + '3.modify the description of the leaf node: /configuration/ipv6'
              + '-multicast/v6-multicast/global/mroute6-limit.'
                ;
  }
  revision 2015-08-28 {
    description '1:add the key of the list: /state/ipv6-multicast/public/nextho'
              + 'ps/nexthop;'+"\n"
              + '2:delete the key of the list: /state/ipv6-multicast/public/nex'
              + 'thops/nexthop/ecmp;'+"\n"
              + '3:delete the leaf of the list: /state/ipv6-multicast/public/ne'
              + 'xthops/nexthop/ecmp/type;'+"\n"
              + '4:add the key of the list: /state/ipv6-multicast/private/nexth'
              + 'ops/nexthop;'+"\n"
              + '5:delete the key of the list: /state/ipv6-multicast/private/ne'
              + 'xthops/nexthop/ecmp;'+"\n"
              + '6:delete the leaf of the list: /state/ipv6-multicast/private/n'
              + 'exthops/nexthop/ecmp/type;'+"\n"
              + '7:modify the description of the leaf: /state/ipv6-multicast/pu'
              + 'blic/mroutes/mroute/mrt-flag;'+"\n"
              + '8:modify the description of the leaf: /state/ipv6-multicast/pr'
              + 'ivate/mroutes/mroute/mrt-flag;'
                ;
  }
  revision 2015-08-12 {
    description '1.modify the description of the leaf: /state/ipv6-multicast/pu'
              + 'blic/mroutes/mroute/mrt-flag,iif-flag;'+"\n"
              + '2.modify the description of the leaf: /state/ipv6-multicast/pu'
              + 'blic/mroutes/mroute/oif-list/oif-flag;'+"\n"
              + '3.modify the description of the leaf: /state/ipv6-multicast/pr'
              + 'ivate/mroutes/mroute/mrt-flag,iif-flag;'+"\n"
              + '4.modify the description of the leaf: /state/ipv6-multicast/pr'
              + 'ivate/mroutes/mroute/oif-list/oif-flag;'+"\n"
              + '5:add the selects of the list: /state/ipv6-multicast/public/mr'
              + 'outes/mroute;'+"\n"
              + '6:add the selects of the list: /state/ipv6-multicast/private/m'
              + 'routes/mroute;'+"\n"
              + '7:add the selects of the list: /state/ipv6-multicast/public/br'
              + 'iefs/brief;'+"\n"
              + '8:add the selects of the list: /state/ipv6-multicast/private/b'
              + 'riefs/brief;'+"\n"
              + '9:add the selects of the list: /state/ipv6-multicast/private/n'
              + 'exthops/nexthop;'+"\n"
              + '10:delete the range of the leaf: /state/ipv6-multicast/private'
              + '/mvpn/mtibs/mtib/tunnel-id;'+"\n"
              + '11:delete the range of the leaf: /state/ipv6-multicast/private'
              + '/mvpn/mribs/mrib/rpf-tunnel-id;'+"\n"
              + '12:add the container: /state/ipv6-multicast/private/mvpn/ad-ro'
              + 'utes/ad-route/xg-joins;'+"\n"
              + '13:add the container: /state/ipv6-multicast/private/mvpn/mribs'
              + '/mrib/xg-joins;'
                ;
  }
  revision 2015-08-04 {
    description 'Remove the config of operation.'
                ;
  }
  revision 2015-05-08 {
    description '1.add the leaf of access-addr-scope: /configuration/ipv6-multi'
              + 'cast/v6-multicast/global;'+"\n"
              + '2.add the feature of access-addr-scope;'
                ;
  }
  revision 2015-03-31 {
    description 'Add state and operation of IPv6 MULTICAST.'
                ;
  }
  revision 2015-03-04 {
    description '1.modify the description of the container and leaf: /configura'
              + 'tion/ipv6-multicast/vrf-v6-multicasts/vrf-v6-multicast/vrf-nam'
              + 'e, forward-policy ;'+"\n"
              + '2.modify the description of the container and leaf: /configura'
              + 'tion/ipv6-multicast/v6-multicast/forward-policy ;'
                ;
  }
  revision 2015-02-11 {
    description '1.modify the length of the leaf: /configuration/ipv6-multicast'
              + '/vrf-v6-multicasts/vrf-v6-multicast/vrf-name ;'+"\n"
              + '2.modify the description of the leaf: /configuration/ipv6-mult'
              + 'icast/v6-multicast/global/mroute6-limit ;'
                ;
  }
  revision 2014-09-01 {
    description '1.modify the range of the leaf: /configuration/ipv6-multicast/'
              + 'v6-multicast/global/multipath;'+"\n"
              + '2.modify the range of the leaf: /configuration/ipv6-multicast/'
              + 'vrf-v6-multicasts/vrf-v6-multicast/multipath;'+"\n"
              + '3.modify the name and description of enum item of the leaf: /c'
              + 'onfiguration/ipv6-multicast/v6-multicast/global/multipath;'+"\n"
              + '4.modify the name and description of enum item of the leaf: /c'
              + 'onfiguration/ipv6-multicast/vrf-v6-multicasts/vrf-v6-multicast'
              + '/multipath.'
                ;
  }
  revision 2014-03-26 {
    description 'Change acl range of forward-policy under vrf-v6-multicast'+"\n"
              + 'change default value of dscp-tos'+"\n"
              + 'change miminfo of vrf-v6-multicast list'
                ;
  }
  revision 2013-09-30 {
    description 'Initial version'
                ;
  }
  feature access-addr-scope {
    description 'Access multicast address scope'
                ;
  }
  feature mvpn-cross-as {
    description 'Only for the use of HighEndPacket.15K,HighEndPacket.15K-GM,PC.'
              + 'MSE,6100 and MSE.M6000-S.'
                ;
  }
  feature mvpn-switch-threshold {
    description 'Only for the use of HighEndPacket.15K,HighEndPacket.15K-GM,610'
              + '0 and PC.MSE.'
                ;
  }
  container configuration {
    description 'Configuration model.'
                ;
    container ipv6-multicast {
      description 'IPv6 multicast'
                  ;
      container v6-multicast {
        description 'IPv6 Multicast routing'
                    ;
        presence multicast ;
        container global {
          description 'Global config'
                      ;
          leaf mroute6-limit {
            description "The max number of the IPv6 multicast routes. It's topl"
                      + "imit depends on ability of the device."
                        ;
            type uint32 {
              range 1..262144 {
                description 'The max number of the IPv6 multicast routes.'
                            ;
              }
            }
          }
          leaf nsf-time {
            description 'NSF lifetime'
                        ;
            type int32 {
              range 30..1800 {
                description 'NSF lifetime'
                            ;
              }
            }
            units second ;
            default 60 ;
          }
          leaf damping-threshold {
            description 'Mroute6 flap damping threshold'
                        ;
            type uint32 {
              range 2..100 {
                description 'Mroute6 flap damping threshold'
                            ;
              }
            }
            default 5 ;
          }
          leaf damping-enable {
            description 'Mroute6 flap damping enable'
                        ;
            type empty ;
          }
          leaf multipath {
            description Multipath ;
            type enumeration {
              enum s-hash-basic {
                value 1 ;
                description S-hash-basic ;
              }
              enum sg-hash-basic {
                value 2 ;
                description Sg-hash-basic ;
              }
              enum sg-hash-nexthop-based {
                value 3 ;
                description Sg-hash-nexthop-based ;
              }
              enum sg-hash-balance {
                value 4 ;
                description Sg-hash-balance ;
              }
              enum g-hash-basic {
                value 5 ;
                description G-hash-basic ;
              }
            }
          }
          leaf dscp-tos {
            description 'DSCP value'
                        ;
            type uint8 {
              range 0..63 {
                description 'DSCP value'
                            ;
              }
            }
          }
          leaf access-addr-scope {
            // if-feature access-addr-scope ;
            description 'Access multicast address scope'
                        ;
            type enumeration {
              enum FFx0 {
                value 1 ;
                description FFx0 ;
              }
            }
            ncd:revise-date 2015-05-08 ;
          }
          leaf mroute6-limit-p-instance {
            description "The max number of the IPv6 multicast routes attached t"
                      + "o theglobal instance. It's toplimit depends on ability"
                      + " of the device."
                        ;
            type uint32 {
              range 1..262144 {
                description 'The max number of the IPv6 multicast routes attach'
                          + 'ed to the global instance.'
                            ;
              }
            }
            ncd:revise-date 2015-11-26 ;
          }
          leaf multicast-address-rfc7371 {
            description 'Multicast address compatible with RFC7371.'
                        ;
            type empty ;
            ncd:revise-date 2018-12-11 ;
          }
          leaf ecmp-select-cost-first {
            description 'ECMP selecting of multicast route'
                        ;
            type empty ;
            ncd:revise-date 2019-02-25 ;
          }
          leaf longest-match {
            description 'Nexthop longest match'
                        ;
            type empty ;
            ncd:revise-date 2019-07-15 ;
          }
          leaf static-first {
            description 'Nexthop static first'
                        ;
            type empty ;
            ncd:revise-date 2019-07-15 ;
          }
          leaf downstream-limit {
            description "The max number of the multicast route forward table do"
                      + "wnstreams. It's toplimit depends on ability of the dev"
                      + "ice."
                        ;
            type int32 {
              range 1..1024 {
                description 'The max number of the multicast route forward tabl'
                          + 'e downstreams.'
                            ;
              }
            }
            ncd:revise-date 2019-07-15 ;
          }
          leaf mvpn-frr-policy {
            description 'MVPN FRR policy.
2:hot-root-standby'
                        ;
            type enumeration {
              enum hot-root-standby {
                value 2 ;
              }
            }
            ncd:revise-date 2020-06-20 ;
          }
          leaf mvpn-frr-egress-wtr {
            description 'Egress WTR delay time(second).'
                        ;
            type uint16 {
              range 1..600 ;
            }
            ncd:revise-date 2020-06-20 ;
          }
          leaf ecmp-select-reference-bandwidth {
            description 'Select multicast nexthop based on reference bandwidth '
                      + 'in terms of 10Gbps.'
                        ;
            type empty ;
            ncd:revise-date 2021-01-19 ;
          }
        }
        container forward-policy {
          description 'Forward policy'
                      ;
          presence forward ;
          leaf acl {
            description 'Access list name'
                        ;
            type string {
              length 1..31 ;
            }
          }
          leaf options {
            description 'Forward IPv6 multicast traffic option'
                        ;
            type enumeration {
              enum per-packet {
                value 1 ;
                description 'Forward IPv6 multicast traffic by packet'
                            ;
              }
              enum per-user {
                value 2 ;
                description 'Forward IPv6 multicast traffic by user'
                            ;
              }
              enum per-stream {
                value 3 ;
                description 'Forward IPv6 multicast traffic by stream'
                            ;
              }
            }
            mandatory true ;
          }
        }
        container biers {
          description 'Multicast BIER.'
                      ;
          list bier {
            description 'Bit index explicit replication.'
                        ;
            max-elements 256 ;
            key subdomain-id ;
            leaf subdomain-id {
              description 'Subdomain ID.'
                          ;
              type uint8 {
                range 0..255 ;
              }
            }
            leaf bsl {
              description 'Bitstring length.'
                          ;
              type enumeration {
                enum 256 {
                  value 3 ;
                }
                enum 512 {
                  value 4 ;
                }
              }
              ncd:revise-date 2020-12-22 ;
            }
            container bfer-indexs {
              description 'Bit forwarding egress routers index.'
                          ;
              list bfer-index {
                description 'BFER index.'
                            ;
                max-elements 65535 ;
                key 'index prefix'
                    ;
                leaf index {
                  description 'BFER index.'
                              ;
                  type uint32 {
                    range 1..100 ;
                  }
                }
                leaf prefix {
                  description 'BFER prefix.'
                              ;
                  type ncd:ipv6-address ;
                }
              }
            }
          }
          ncd:revise-date 2020-06-20 ;
        }
        container nexthops {
          description 'Multicast static nexthop.'
                      ;
          list nexthop {
            description 'Multicast static nexthop.'
                        ;
            key 'intf-name ipv6-addr prefix-length nexthop-addr'
                ;
            leaf intf-name {
              description 'Interface name.'
                          ;
              type ncd:ifname {
                length 1..31 ;
              }
            }
            leaf ipv6-addr {
              description 'Prefix of destination IPv6 address.'
                          ;
              type ncd:ipv6-address ;
            }
            leaf prefix-length {
              description 'Prefix length.'
                          ;
              type uint8 {
                range 1..128 ;
              }
            }
            leaf nexthop-addr {
              description 'Nexthop address.'
                          ;
              type ncd:ipv6-address ;
            }
            leaf slave {
              description 'Slave nexthop.'
                          ;
              type empty ;
            }
          }
          ncd:revise-date 2015-12-09 ;
        }
        container nexthop-fallbacks {
          description 'Alternate routing table for nexthop lookup.'
                      ;
          list nexthop-fallback {
            description 'Alternate routing table for nexthop lookup.'
                        ;
            key 'ipv6-addr prefix-length'
                ;
            leaf ipv6-addr {
              description 'Prefix of destination IPv6 address.'
                          ;
              type ncd:ipv6-address ;
            }
            leaf prefix-length {
              description 'Prefix length.'
                          ;
              type uint8 {
                range 1..128 ;
              }
            }
            leaf vrf-name {
              description 'VRF name.'
                          ;
              type string {
                length 1..32 ;
              }
              mandatory true ;
            }
          }
          ncd:revise-date 2015-12-09 ;
        }
        container nexthop-path-lists {
          description 'Multicast static nexthop for RPF vector path list.'
                      ;
          list nexthop-path-list {
            description 'Multicast static nexthop for RPF vector path list.'
                        ;
            key 'ipv6-addr prefix-length'
                ;
            leaf ipv6-addr {
              description 'Prefix of destination IPv6 address.'
                          ;
              type ncd:ipv6-address ;
            }
            leaf prefix-length {
              description 'Prefix length.'
                          ;
              type uint8 {
                range 1..128 ;
              }
            }
            leaf rpf-path-name {
              description 'RPF path name.'
                          ;
              type string {
                length 1..31 ;
              }
              mandatory true ;
            }
          }
          ncd:revise-date 2019-09-29 ;
        }
        container smdms {
          description 'configure L2 oif mapping mode'
                      ;
          list smdm {
            description 'configure L2 oif mapping mode'
                        ;
            key intf-name ;
            leaf intf-name {
              description 'Interface name'
                          ;
              type ncd:ifname ;
            }
          }
          ncd:revise-date 2018-11-14 ;
        }
        container boundarys {
          description 'Multicast forwarding boundary'
                      ;
          list boundary {
            description 'Multicast forwarding boundary'
                        ;
            max-elements 64 ;
            key intf-name ;
            leaf intf-name {
              description 'Interface name'
                          ;
              type ncd:ifname {
                length 1..31 ;
              }
            }
            leaf aclname {
              description 'Access list name for group  prefix'
                          ;
              type string {
                length 1..31 ;
              }
              mandatory true ;
            }
          }
          ncd:revise-date 2019-07-15 ;
        }
        container router-id {
          description 'Multicast router ID.'
                      ;
          presence router-id ;
          leaf router-id {
            description 'Multicast router ID.'
                        ;
            type ncd:ipv4-address ;
            mandatory true ;
          }
          ncd:revise-date 2019-08-29 ;
        }
        container rpf-vector-path-lists {
          description 'RPF proxy vector for path list.'
                      ;
          list rpf-vector-path-list {
            description 'RPF proxy vector for path list.'
                        ;
            key 'rpf-path-name rpf-path-index'
                ;
            leaf rpf-path-name {
              description 'RPF path name.'
                          ;
              type string {
                length 1..31 ;
              }
            }
            leaf rpf-path-index {
              description 'RPF path index.'
                          ;
              type uint32 {
                range 1..65535 ;
              }
            }
            leaf vector-address {
              description 'RPF vector address.'
                          ;
              type ncd:ipv6-address ;
              mandatory true ;
            }
            leaf vector-type {
              description 'RPF vector type.'
                          ;
              type enumeration {
                enum loose {
                  value 0 ;
                }
                enum strict {
                  value 4 ;
                }
              }
              mandatory true ;
            }
          }
          ncd:revise-date 2019-09-29 ;
        }
        container mvpn {
          description Mvpn ;
          presence mvpn ;
          leaf provider-tunnel {
            description Provider-tunnel ;
            type enumeration {
              enum rsvp-te {
                value 1 ;
                description rsvp-te ;
              }
              enum mldp-p2mp {
                value 2 ;
                description mldp-p2mp ;
              }
              enum bier {
                value 11 ;
                description bier ;
              }
            }
            mandatory true ;
          }
          leaf sub-domain-id {
            description 'BIER sub-domain-id.'
                        ;
            type uint8 {
              range 0..255 ;
            }
          }
          leaf bfd-enable {
            description 'BFD enable.'
                        ;
            type empty ;
          }
          leaf bfd-template {
            description 'BFD template name.'
                        ;
            type string {
              length 1..31 ;
            }
          }
          ncd:revise-date 2020-06-20 ;
        }
        container spmsi-bier-infos {
          description 'MVPN S-PMSI BIER information.'
                      ;
          list spmsi-bier-info {
            description 'MVPN S-PMSI BIER information.'
                        ;
            key subdomain-id ;
            leaf subdomain-id {
              description 'Subdomain ID.'
                          ;
              type uint8 {
                range 0..255 ;
              }
            }
            leaf acl-name {
              description 'ACL name.'
                          ;
              type string {
                length 1..31 ;
              }
              mandatory true ;
            }
          }
          ncd:revise-date 2020-10-27 ;
        }
      }
      container vrf-v6-multicasts {
        description 'VRF instance'
                    ;
        list vrf-v6-multicast {
          description 'VRF instance'
                      ;
          key vrf-name ;
          leaf vrf-name {
            description 'VRF name'
                        ;
            type string {
              length 1..32 ;
            }
          }
          leaf multipath {
            description Multipath ;
            type enumeration {
              enum s-hash-basic {
                value 1 ;
                description S-hash-basic ;
              }
              enum sg-hash-basic {
                value 2 ;
                description Sg-hash-basic ;
              }
              enum sg-hash-nexthop-based {
                value 3 ;
                description Sg-hash-nexthop-based ;
              }
              enum sg-hash-balance {
                value 4 ;
                description Sg-hash-balance ;
              }
              enum g-hash-basic {
                value 5 ;
                description G-hash-basic ;
              }
            }
          }
          leaf mroute6-limit-c-instance {
            description "The max number of the IPv6 multicast routes attached t"
                      + "o theVRF instance. It's toplimit depends on ability of"
                      + " the device."
                        ;
            type uint32 {
              range 1..262144 {
                description 'The max number of the IPv6 multicast routes attach'
                          + 'ed to the VRF instance.'
                            ;
              }
            }
            ncd:revise-date 2015-11-26 ;
          }
          leaf mvpn-switchover-holdtime {
            description 'Holdtime which data tree switch back to default tree'
                        ;
            type uint16 {
              range 30..600 ;
            }
            ncd:revise-date 2019-01-21 ;
          }
          leaf mvpn-switchover-interval {
            description 'Delay time which default tree switch to data tree'
                        ;
            type uint16 {
              range 3..65535 ;
            }
            ncd:revise-date 2016-11-29 ;
          }
          leaf mvpn-switchover-threshold-infinity {
            description 'ACL for MVPN tunnel never switch to data tree.'
                        ;
            type string {
              length 1..31 ;
            }
            ncd:revise-date 2017-06-05 ;
          }
          leaf ecmp-select-cost-first {
            description 'ECMP selecting of multicast route'
                        ;
            type empty ;
            ncd:revise-date 2019-02-25 ;
          }
          leaf mvpn-upstream-pe-select {
            description 'MVPN upstream PE select policy '+"\n"
                      + '1:lowest-addr-first'+"\n"
                      + '2:bgp-route-policy'
                        ;
            type enumeration {
              enum lowest-addr-first {
                value 1 ;
              }
              enum bgp-route-policy {
                value 2 ;
              }
            }
            ncd:revise-date 2019-07-15 ;
          }
          leaf mvpn-frr-policy {
            description 'MVPN FRR policy.'+"\n"
                      + '1:warm-root-standby'+"\n"
                      + '2:hot-root-standby'
                        ;
            type enumeration {
              enum warm-root-standby {
                value 1 ;
              }
              enum hot-root-standby {
                value 2 ;
              }
            }
            ncd:revise-date 2019-04-12 ;
          }
          leaf mvpn-frr-detect-type {
            description 'MVPN FRR detect type.'+"\n"
                      + '1:stream detect'+"\n"
                      + '2:peer BFD detect'
                        ;
            type enumeration {
              enum stream {
                value 1 ;
              }
              enum peer-bfd {
                value 2 ;
              }
            }
            ncd:revise-date 2019-04-12 ;
          }
          leaf mvpn-frr-ingress-wtr {
            description 'Ingress WTR delay time(second).'
                        ;
            type uint16 {
              range 1..600 ;
            }
            ncd:revise-date 2019-04-12 ;
          }
          leaf mvpn-frr-egress-wtr {
            description 'Egress WTR delay time(second).'
                        ;
            type uint16 {
              range 1..600 ;
            }
            ncd:revise-date 2019-04-12 ;
          }
          leaf mvpn-wildcards-spmsi {
            description 'MVPN wildcards SPMSI.'
                        ;
            type empty ;
            ncd:revise-date 2019-07-15 ;
          }
          leaf mvpn-spt-only {
            description 'MVPN spt only mode'
                        ;
            type empty ;
            ncd:revise-date 2019-11-06 ;
          }
          leaf mvpn-send-site-only {
            description 'MVPN send site only mode'
                        ;
            type empty ;
            ncd:revise-date 2019-11-06 ;
          }
          leaf mvpn-receive-site-only {
            description 'MVPN receive site only mode'
                        ;
            type empty ;
            ncd:revise-date 2019-11-06 ;
          }
          leaf mvpn-spmsi-tunnel {
            description 'MVPN spmsi tunnel'
                        ;
            type enumeration {
              enum rsvp-te {
                value 1 ;
                description rsvp-te ;
              }
              enum mldp-p2mp {
                value 2 ;
                description mldp-p2mp ;
              }
              enum ingress-replication {
                value 6 ;
                description ingress-replication ;
              }
            }
            ncd:revise-date 2019-11-06 ;
          }
          leaf longest-match {
            description 'Nexthop longest match'
                        ;
            type empty ;
            ncd:revise-date 2019-07-15 ;
          }
          leaf static-first {
            description 'Nexthop static first'
                        ;
            type empty ;
            ncd:revise-date 2019-07-15 ;
          }
          leaf ecmp-select-reference-bandwidth {
            description 'Select multicast nexthop based on reference bandwidth '
                      + 'in terms of 10Gbps.'
                        ;
            type empty ;
            ncd:revise-date 2021-01-19 ;
          }
          container mvpn-switchover-threshold {
            // if-feature mvpn-switch-threshold ;
            description 'MVPN tunnel switchover threshold.'
                        ;
            presence mvpn-switchover-threshold ;
            leaf threshold {
              description 'MVPN tunnel switchover threshold(Kbps).'
                          ;
              type uint32 {
                range 1..4294967295 ;
              }
              mandatory true ;
            }
            leaf acl {
              description 'ACL for MVPN tunnel switchover.'
                          ;
              type string {
                length 1..31 ;
              }
              mandatory true ;
            }
            ncd:revise-date 2017-02-21 ;
          }
          container mvpn {
            description Mvpn ;
            presence mvpn ;
            leaf provider-tunnel {
              description Provider-tunnel ;
              type enumeration {
                enum rsvp-te {
                  value 1 ;
                  description rsvp-te ;
                }
                enum mldp-p2mp {
                  value 2 ;
                  description mldp-p2mp ;
                }
                enum ingress-replication {
                  value 6 ;
                  description ingress-replication ;
                }
                enum bier {
                  value 11 ;
                  description bier ;
                }
              }
              mandatory true ;
            }
            leaf sub-domain-id {
              description 'BIER sub-domain-id.'
                          ;
              type uint8 {
                range 0..255 ;
              }
              ncd:revise-date 2020-06-20 ;
            }
            leaf bfd-enable {
              description 'BFD enable.'
                          ;
              type empty ;
              ncd:revise-date 2020-06-20 ;
            }
            leaf bfd-template {
              description 'BFD template name.'
                          ;
              type string {
                length 1..31 ;
              }
              ncd:revise-date 2020-06-20 ;
            }
          }
          container forward-policy {
            description 'Forward policy'
                        ;
            presence forward ;
            leaf acl {
              description 'Access list name'
                          ;
              type string {
                length 1..31 ;
              }
            }
            leaf options {
              description 'Forward IPv6 multicast traffic option'
                          ;
              type enumeration {
                enum per-packet {
                  value 1 ;
                  description 'Forward IPv6 multicast traffic by packet'
                              ;
                }
                enum per-user {
                  value 2 ;
                  description 'Forward IPv6 multicast traffic by user'
                              ;
                }
                enum per-stream {
                  value 3 ;
                  description 'Forward IPv6 multicast traffic by stream'
                              ;
                }
              }
              mandatory true ;
            }
          }
          container nexthops {
            description 'Multicast static nexthop.'
                        ;
            list nexthop {
              description 'Multicast static nexthop.'
                          ;
              key 'intf-name ipv6-addr prefix-length nexthop-addr'
                  ;
              leaf intf-name {
                description 'Interface name.'
                            ;
                type ncd:ifname {
                  length 1..31 ;
                }
              }
              leaf ipv6-addr {
                description 'Prefix of destination IPv6 address.'
                            ;
                type ncd:ipv6-address ;
              }
              leaf prefix-length {
                description 'Prefix length.'
                            ;
                type uint8 ;
              }
              leaf nexthop-addr {
                description 'Nexthop address.'
                            ;
                type ncd:ipv6-address ;
              }
              leaf slave {
                description 'Slave nexthop.'
                            ;
                type empty ;
              }
            }
            ncd:revise-date 2015-12-09 ;
          }
          container nexthop-fallbacks {
            description 'Alternate routing table for nexthop lookup.'
                        ;
            list nexthop-fallback {
              description 'Alternate routing table for nexthop lookup.'
                          ;
              key 'ipv6-addr prefix-length'
                  ;
              leaf ipv6-addr {
                description 'Prefix of destination IPv6 address.'
                            ;
                type ncd:ipv6-address ;
              }
              leaf prefix-length {
                description 'Prefix length.'
                            ;
                type uint8 {
                  range 1..128 ;
                }
              }
              container instance {
                description 'Fallback instance.'
                            ;
                choice instance {
                  description 'Fallback instance.'
                              ;
                  mandatory true ;
                  case p-instance {
                    description 'Public instance.'
                                ;
                    leaf global {
                      description 'Public instance.'
                                  ;
                      type empty ;
                    }
                  }
                  case c-instance {
                    description 'Customer instance.'
                                ;
                    leaf vrf-name {
                      description 'VRF name.'
                                  ;
                      type string {
                        length 1..32 ;
                      }
                    }
                  }
                }
              }
            }
            ncd:revise-date 2015-12-09 ;
          }
          container mtunnel {
            description 'Interface used to set MDT source address'
                        ;
            presence mtunnel ;
            leaf intf-name {
              description 'Interface name'
                          ;
              type ncd:ifname {
                length 1..31 ;
              }
              mandatory true ;
            }
            ncd:revise-date 2019-02-25 ;
          }
          container mdt-default {
            description 'Default MDT'
                        ;
            choice mdt-default {
              description 'Default MDT'
                          ;
              case mdt-default-group {
                description 'MDT default group'
                            ;
                leaf group {
                  description 'IP multicast group address'
                              ;
                  type ncd:ipv4-address-none-zero ;
                  mandatory true ;
                }
              }
              case mpls-mldp {
                description 'MDT P2MP mLDP default distribution tree'
                            ;
                container mdt-defaults {
                  description 'Default MDT'
                              ;
                  list mdt-default {
                    description 'Default MDT'
                                ;
                    max-elements 3200 ;
                    key root-addr ;
                    leaf root-addr {
                      description 'Remote root address'
                                  ;
                      type ncd:ipv4-address-none-zero ;
                    }
                  }
                }
              }
            }
            ncd:revise-date 2019-02-25 ;
          }
          container mdt-data {
            description 'Data MDT'
                        ;
            choice mdt-data {
              description 'Data MDT'
                          ;
              case mdt-data-group {
                description 'MDT data group'
                            ;
                leaf acl {
                  description 'Access list name'
                              ;
                  type string {
                    length 1..31 ;
                  }
                }
                leaf group {
                  description 'IP multicast group address'
                              ;
                  type ncd:ipv4-address-none-zero ;
                  mandatory true ;
                }
                leaf mask {
                  description 'Wildcard bits'
                              ;
                  type ncd:ipv4-imask ;
                  mandatory true ;
                }
              }
              case mpls-mldp {
                description 'MDT P2MP mLDP data distribution tree'
                            ;
                leaf num-tree {
                  description 'Data tree number'
                              ;
                  type uint32 {
                    range 1..5000 {
                      description 'MDT data num tree'
                                  ;
                    }
                  }
                  mandatory true ;
                }
              }
            }
            ncd:revise-date 2019-02-25 ;
          }
          container p2mp-template {
            description 'MVPN TE P2MP template'
                        ;
            presence p2mp-template ;
            leaf name {
              description 'Template name(1-32 characters)'
                          ;
              type string {
                length 1..32 {
                  description 'Template name'
                              ;
                }
              }
              mandatory true ;
            }
            ncd:revise-date 2019-04-12 ;
          }
          container mvpn-frr-peer-bfd-ipv4s {
            description 'MVPN frr peer-bfd config information'
                        ;
            list mvpn-frr-peer-bfd-ipv4 {
              description 'MVPN frr peer-bfd config information'
                          ;
              key 'local-addr remote-addr'
                  ;
              leaf local-addr {
                description 'Specify local IPv4 address'
                            ;
                type ncd:ipv4-address-none-zero ;
              }
              leaf remote-addr {
                description 'Specify remote IPv4 address'
                            ;
                type ncd:ipv4-address-none-zero ;
              }
            }
            ncd:revise-date 2019-04-12 ;
          }
          container mvpn-spmsi-aggregation {
            description 'MVPN SPMSI aggregation config information.'
                        ;
            choice mvpn-spmsi-aggregation {
              description 'MVPN SPMSI aggregation config information.'
                          ;
              case type {
                description 'MVPN SPMSI aggregation source-based.'
                            ;
                leaf type {
                  description 'MVPN SPMSI aggregation type.'
                              ;
                  type enumeration {
                    enum source-based {
                      value 1 ;
                    }
                  }
                  mandatory true ;
                }
              }
              case count {
                description 'MVPN SPMSI aggregation count.'
                            ;
                leaf count {
                  description 'MVPN SPMSI aggregation count.'
                              ;
                  type uint32 {
                    range 1..131072 ;
                  }
                  mandatory true ;
                }
              }
            }
            ncd:revise-date 2019-07-15 ;
          }
          container router-id {
            description 'Multicast router ID.'
                        ;
            presence router-id ;
            leaf router-id {
              description 'Multicast router ID.'
                          ;
              type ncd:ipv4-address ;
              mandatory true ;
            }
            ncd:revise-date 2019-08-29 ;
          }
          container spmsi-bier-infos {
            description 'MVPN S-PMSI BIER information.'
                        ;
            list spmsi-bier-info {
              description 'MVPN S-PMSI BIER information.'
                          ;
              key subdomain-id ;
              leaf subdomain-id {
                description 'Subdomain ID.'
                            ;
                type uint8 {
                  range 0..255 ;
                }
              }
              leaf acl-name {
                description 'ACL name.'
                            ;
                type string {
                  length 1..31 ;
                }
                mandatory true ;
              }
            }
            ncd:revise-date 2020-10-27 ;
          }
        }
      }
    }
  }
  container state {
    config false ;
    description 'State module.'
                ;
    container ipv6-multicast {
      description 'IPv6 multicast show info.'
                  ;
      container public {
        description 'Public mode of IPv6 multicast.'
                    ;
        container mroutes {
          description 'Multicast route information.'
                      ;
          list mroute {
            description 'Multicast route information.'
                        ;
            key 'group-addr source-addr'
                ;
            leaf group-addr {
              description 'Group address'
                          ;
              type ncd:ipv6-address ;
            }
            leaf source-addr {
              description 'Source address'
                          ;
              type ncd:ipv6-address ;
            }
            leaf rp-addr {
              description 'RP address'
                          ;
              type ncd:ipv6-address ;
            }
            leaf iif-name {
              description 'Incoming interface name'
                          ;
              type ncd:string-all {
                length 0..31 ;
              }
            }
            leaf secondary-rpf-intf {
              description 'Secondary RPF interface name'
                          ;
              type ncd:string-all {
                length 0..31 ;
              }
            }
            leaf mrt-flag {
              description 'Mroute flag.'+"\n"
                        + 'NS:SPT upsend,RT:Reg upsend,MT:Tunnel,NTP:NTP join,D'
                        + 'PU:Damping enable,DPD:Damping del,B:Bidir,SU:Slave i'
                        + 'n use.'
                          ;
              type ncd:string-all {
                length 0..31 ;
              }
            }
            leaf mrt-type {
              description 'Mroute type:"STATIC","DYNAMIC".'
                          ;
              type ncd:string-all {
                length 0..20 ;
              }
            }
            leaf iif-flag {
              description 'Incoming interface flag.
NS:SPT upsend.'
                          ;
              type ncd:string-all {
                length 0..31 ;
              }
            }
            leaf fallback-vrf {
              description 'The upstream VRF name of mroute.'
                          ;
              type string {
                length 0..32 ;
              }
              ncd:revise-date 2015-12-09 ;
            }
            list oif-list {
              description 'Downstream interface list'
                          ;
              key oif-name ;
              leaf oif-name {
                description 'Downstream interface name'
                            ;
                type ncd:string-all {
                  length 0..31 ;
                }
              }
              leaf oif-flag {
                description 'Downstream interface flag.'+"\n"
                          + 'F:Forward,RT:Reg upsend,MT:Tunnel,DF:DF.'
                            ;
                type ncd:string-all {
                  length 0..31 ;
                }
              }
              ncd:select oif-name ;
            }
            list fallback-extranet {
              description 'Fallback extranet receiver info.'
                          ;
              key vrf-name ;
              leaf vrf-name {
                description 'VRF name.'
                            ;
                type string {
                  length 1..32 ;
                }
              }
              ncd:revise-date 2015-12-09 ;
            }
            list bier-info {
              description 'Bit index explicit replication information.'
                          ;
              key 'subdomain-id bfer-prefix'
                  ;
              leaf subdomain-id {
                description 'Subdomain ID.'
                            ;
                type uint8 {
                  range 0..255 ;
                }
              }
              leaf bfer-prefix {
                description 'BFER prefix.'
                            ;
                type string {
                  length 1..39 ;
                }
              }
              leaf bfr-id {
                description 'BFR ID.'
                            ;
                type uint16 {
                  range 0..65535 ;
                }
              }
              ncd:select bfer-prefix ;
              ncd:revise-date 2020-06-20 ;
            }
            ncd:select 'group-addr source-addr'
                       ;
            ncd:select source-addr ;
            ncd:select group-addr ;
          }
        }
        container summary {
          description 'The summary information of mroute.'
                      ;
          leaf xg-count {
            description 'XG summary'
                        ;
            type uint32 ;
          }
          leaf sg-count {
            description 'SG summary'
                        ;
            type uint32 ;
          }
          leaf mroute-count {
            description 'XG and SG mroute summary'
                        ;
            type uint32 ;
          }
        }
        container briefs {
          description 'The brief information of mroute'
                      ;
          list brief {
            description 'The brief information of mroute'
                        ;
            key 'group source'
                ;
            leaf group {
              description 'Group address'
                          ;
              type ncd:ipv6-address ;
            }
            leaf source {
              description 'Source address'
                          ;
              type ncd:ipv6-address ;
            }
            leaf type {
              description 'Mroute type:"STATIC","DYNAMIC".'
                          ;
              type string {
                length 1..11 ;
              }
            }
            ncd:select group ;
            ncd:select source ;
            ncd:select 'group source'
                       ;
          }
        }
        container nexthops {
          description 'The nexthop information of mroute'
                      ;
          list nexthop {
            description 'The nexthop information of mroute'
                        ;
            key 'dest-addr type'
                ;
            leaf dest-addr {
              description 'Destination address'
                          ;
              type ncd:ipv6-address ;
            }
            leaf type {
              description 'Type:"Mstatic nexthop","Mdt nexthop","Mbgp nexthop",'
                        + '"Migp nexthop","Rtm nexthop"'
                          ;
              type ncd:string-all {
                length 0..31 ;
              }
              ncd:revise-date 2015-08-28 ;
            }
            leaf time {
              description 'Nexthop create time'
                          ;
              type ncd:string-all {
                length 0..31 ;
              }
            }
            leaf user {
              description 'Nexthop user:"PIM","DM","MSDP","MSN","MVPN"'
                          ;
              type ncd:string-all {
                length 0..31 ;
              }
            }
            leaf metric {
              description Metric ;
              type uint32 ;
            }
            leaf preference {
              description Preference ;
              type uint32 ;
            }
            leaf mask-len {
              description 'Mask length'
                          ;
              type uint16 ;
            }
            leaf flag {
              description 'Flag.'+"\n"
                        + 'L:Local,C:Connect,UNR:Unreachable unicast,CTOP:Acros'
                        + 's the backbone'
                          ;
              type ncd:string-all {
                length 0..31 ;
              }
            }
            leaf fallback-vrf {
              description 'The VRF name of fallback nexthop.'
                          ;
              type string {
                length 0..32 ;
              }
              ncd:revise-date 2015-12-09 ;
            }
            list ecmp {
              description 'ECMP information'
                          ;
              key 'nexthop oif-name'
                  ;
              leaf nexthop {
                description 'Nexthop address'
                            ;
                type ncd:ipv6-address ;
              }
              leaf oif-name {
                description 'Downstream interface name'
                            ;
                type ncd:string-all {
                  length 0..31 ;
                }
              }
              leaf oif-flag {
                description 'Downstream interface flag.'+"\n"
                          + 'Mdt:Mdt nexthop'+"\n"
                          + 'Down:Interface down'+"\n"
                          + 'S:Slave '+"\n"
                          + 'M:Maste'
                            ;
                type ncd:string-all {
                  length 0..31 ;
                }
              }
              leaf real-nexthop {
                description 'Real nexthop address.'
                            ;
                type ncd:ipv6-address ;
              }
              ncd:select 'nexthop oif-name'
                         ;
            }
            ncd:select dest-addr ;
          }
        }
        container mvpn {
          description 'MVPN show info.'
                      ;
          container mtunnels {
            description 'MVPN tunnel information.'
                        ;
            list mtunnel {
              description 'MVPN tunnel information.'
                          ;
              key 'tunnel-id tunnel-type'
                  ;
              leaf tunnel-id {
                description 'Tunnel ID.'
                            ;
                type uint32 ;
              }
              leaf tunnel-type {
                description 'Tunnel type.'+"\n"
                          + '0:No-Tunnel'+"\n"
                          + '1:TE-P2MP'+"\n"
                          + '2:mLDP-P2MP'+"\n"
                          + '3:PIM-SSM'+"\n"
                          + '4:PIM-SM'+"\n"
                          + '5:PIM-BIDIR'+"\n"
                          + '6:INGRESS-RPL'+"\n"
                          + '7:mLDP-MP2MP'+"\n"
                          + '11:BIER'
                            ;
                type enumeration {
                  enum No-Tunnel {
                    value 0 ;
                  }
                  enum TE-P2MP {
                    value 1 ;
                  }
                  enum mLDP-P2MP {
                    value 2 ;
                  }
                  enum PIM-SSM {
                    value 3 ;
                  }
                  enum PIM-SM {
                    value 4 ;
                  }
                  enum PIM-BIDIR {
                    value 5 ;
                  }
                  enum INGRESS-RPL {
                    value 6 ;
                  }
                  enum mLDP-MP2MP {
                    value 7 ;
                  }
                  enum BIER {
                    value 11 ;
                  }
                }
              }
              leaf tunnel-state {
                description 'Tunnel state.
0:Root
1:Leaf'
                            ;
                type enumeration {
                  enum Root {
                    value 0 ;
                  }
                  enum Leaf {
                    value 1 ;
                  }
                }
              }
              leaf vrf-name {
                description 'The VRF name of MVPN mtunnel.If the instance of MV'
                          + 'PN is public, the value of the node is "", else is'
                          + ' VRF name.'
                            ;
                type ncd:string-all {
                  length 0..32 ;
                }
              }
              container mrts {
                description 'Attach mroute information.'
                            ;
                list mrt {
                  description 'Attach mroute information.'
                              ;
                  key 'sub-vrf-name source group'
                      ;
                  leaf sub-vrf-name {
                    description 'VPN Routing/Forwarding instance name.'
                                ;
                    type ncd:string-all {
                      length 1..32 ;
                    }
                  }
                  leaf source {
                    description 'Source address.'
                                ;
                    type ncd:ipv6-address ;
                  }
                  leaf group {
                    description 'Group address.'
                                ;
                    type ncd:ipv6-address ;
                  }
                  ncd:select sub-vrf-name ;
                }
              }
              ncd:select tunnel-type ;
              ncd:select 'tunnel-id tunnel-type'
                         ;
            }
          }
          container protect-groups {
            description 'MVPN protect group information.'
                        ;
            list protect-group {
              description 'MVPN protect group information.'
                          ;
              key 'protect-group-id m-subdomain-id m-bfir-id m-vpn-label s-subd'
                + 'omain-id s-bfir-id s-vpn-label'
                  ;
              leaf protect-group-id {
                description 'MVPN protect group ID.'
                            ;
                type uint32 ;
              }
              leaf m-subdomain-id {
                description 'Master subdomain ID.'
                            ;
                type uint8 {
                  range 0..255 ;
                }
              }
              leaf m-bfir-id {
                description 'Master BFIR ID.'
                            ;
                type uint16 {
                  range 1..65535 ;
                }
              }
              leaf m-vpn-label {
                description 'Master VPN Label.'
                            ;
                type uint32 ;
              }
              leaf s-subdomain-id {
                description 'Slave subdomain ID.'
                            ;
                type uint8 {
                  range 0..255 ;
                }
              }
              leaf s-bfir-id {
                description 'Slave BFIR ID.'
                            ;
                type uint16 {
                  range 1..65535 ;
                }
              }
              leaf s-vpn-label {
                description 'Slave VPN label.'
                            ;
                type uint32 ;
              }
              leaf master-state {
                description 'Master tunnel state.'
                            ;
                type ncd:string-all {
                  length 0..23 ;
                }
              }
              leaf egress-wtr {
                description 'Egress WTR delay.'
                            ;
                type ncd:string-all {
                  length 0..15 ;
                }
              }
              leaf vrf-name {
                description 'VRF name.'
                            ;
                type ncd:string-all {
                  length 0..32 ;
                }
              }
              container mrts {
                description 'Attach mroute information.'
                            ;
                list mrt {
                  description 'Attach mroute information.'
                              ;
                  key 'source group'
                      ;
                  leaf source {
                    description 'Source address.'
                                ;
                    type ncd:ipv6-address ;
                  }
                  leaf group {
                    description 'Group address.'
                                ;
                    type ncd:ipv6-address ;
                  }
                  ncd:select 'source group'
                             ;
                }
              }
              ncd:select protect-group-id ;
            }
            ncd:revise-date 2020-06-20 ;
          }
          container instance {
            description 'MVPN instance information.'
                        ;
            leaf rd {
              description RD. ;
              type string {
                length 0..23 ;
              }
            }
            leaf import-rt {
              description 'MVPN import RT.'
                          ;
              type string {
                length 0..23 ;
              }
            }
            leaf origin-ip {
              description 'Origin IP address.'
                          ;
              type ncd:ipv4-address ;
            }
            leaf te-id {
              description 'TE root ID.'
                          ;
              type ncd:ipv4-address ;
            }
            leaf origin-state {
              description 'Origin state.'+"\n"
                        + '"Un-routable"'+"\n"
                        + '"Routable,Local"'+"\n"
                        + '"Routable,Not Local"'
                          ;
              type ncd:string-all {
                length 0..23 ;
              }
            }
            leaf te-state {
              description 'TE state.
"in-use"
"Not in-use"'
                          ;
              type ncd:string-all {
                length 0..15 ;
              }
            }
            leaf mtunnel-type {
              description 'Mtunnel type.'+"\n"
                        + '0:No-Tunnel'+"\n"
                        + '1:TE-P2MP'+"\n"
                        + '2:mLDP-P2MP'+"\n"
                        + '3:PIM-SSM'+"\n"
                        + '4:PIM-SM'+"\n"
                        + '5:PIM-BIDIR'+"\n"
                        + '6:INGRESS-RPL'+"\n"
                        + '7:mLDP-MP2MP'+"\n"
                        + '8:PIM-MDT'+"\n"
                        + '11:BIER'
                          ;
              type enumeration {
                enum No-Tunnel {
                  value 0 ;
                }
                enum TE-P2MP {
                  value 1 ;
                }
                enum mLDP-P2MP {
                  value 2 ;
                }
                enum PIM-SSM {
                  value 3 ;
                }
                enum PIM-SM {
                  value 4 ;
                }
                enum PIM-BIDIR {
                  value 5 ;
                }
                enum INGRESS-RPL {
                  value 6 ;
                }
                enum mLDP-MP2MP {
                  value 7 ;
                }
                enum PIM-MDT {
                  value 8 ;
                }
                enum BIER {
                  value 11 ;
                }
              }
            }
            leaf route-state {
              description 'Route state.
0: Disable
1: Enable'
                          ;
              type enumeration {
                enum Disable {
                  value 0 ;
                }
                enum Enable {
                  value 1 ;
                }
              }
            }
            leaf mldp-state {
              description 'MLDP state.
0: Disable
1: Enable'
                          ;
              type enumeration {
                enum Disable {
                  value 0 ;
                }
                enum Enable {
                  value 1 ;
                }
              }
            }
            leaf p-pim-state {
              description 'P-PIM state.
0: Disable
1: Enable'
                          ;
              type enumeration {
                enum Disable {
                  value 0 ;
                }
                enum Enable {
                  value 1 ;
                }
              }
            }
            leaf c-pim-state {
              description 'C-PIM state.
0: Disable
1: Enable'
                          ;
              type enumeration {
                enum Disable {
                  value 0 ;
                }
                enum Enable {
                  value 1 ;
                }
              }
            }
            leaf us-protocol {
              description 'Upstream Protocol.
0: Unknown
1: BGP
2: PIM'
                          ;
              type enumeration {
                enum Unknown {
                  value 0 ;
                }
                enum BGP {
                  value 1 ;
                }
                enum PIM {
                  value 2 ;
                }
              }
            }
            leaf mtunnel-name {
              description 'Mtunnel name.'
                          ;
              type ncd:ifname {
                length 0..31 ;
              }
            }
            leaf mtunnel-state {
              description 'Mtunnel state.'+"\n"
                        + '"up / PIM enable"'+"\n"
                        + '"down / PIM enable"'+"\n"
                        + '"up / PIM disable"'+"\n"
                        + '"down / PIM disable"'
                          ;
              type ncd:string-all {
                length 0..23 ;
              }
            }
            leaf mtunnel-addr {
              description 'Mtunnel address.'
                          ;
              type ncd:ipv4-address ;
            }
            leaf default-group {
              description 'MDT default group address.'
                          ;
              type ncd:ipv4-address ;
            }
            leaf data-group {
              description 'MDT data group address.'
                          ;
              type ncd:ipv4-address ;
            }
            leaf data-group-mask-len {
              description 'MDT data group mask length.'
                          ;
              type uint8 {
                range 24..32 ;
              }
            }
            leaf data-acl-name {
              description 'MDT data ACL name.'
                          ;
              type string {
                length 0..31 ;
              }
            }
            ncd:revise-date 2020-06-20 ;
          }
          container auto-discovery-route {
            description 'MVPN auto discovery route information.'
                        ;
            container intra-ases {
              description 'Intra-AS auto dicovery route.'
                          ;
              list intra-as {
                description 'Intra-AS auto dicovery route.'
                            ;
                key 'rd origin-ip'
                    ;
                leaf rd {
                  description RD. ;
                  type string {
                    length 0..23 ;
                  }
                }
                leaf origin-ip {
                  description 'Origin IP address.'
                              ;
                  type ncd:ipv4-address ;
                }
                leaf root-tunnel {
                  description 'Root Tunnel.'+"\n"
                            + 'Flags: L- Local,R- Remote,J- Join Ptnl,S- Start '
                            + 'Ptnl,T0- No Ptnl '+"\n"
                            + '       T1- RSVP-TE,T2- mLDP-P2MP,T3- PIM-SSM,T4-'
                            + ' PIM-SM,T5- PIM-Bidir'+"\n"
                            + '       T6- Ingress-Replication,T7- mLDP-MP2MP,T1'
                            + '1- BIER'+"\n"
                            + '(flags:type:label:id)/Flags'
                              ;
                  type ncd:string-all {
                    length 0..119 ;
                  }
                }
                leaf leaf-tunnel {
                  description 'Leaf Tunnel.'+"\n"
                            + 'Flags: L- Local,R- Remote,J- Join Ptnl,S- Start '
                            + 'Ptnl,T0- No Ptnl '+"\n"
                            + '       T1- RSVP-TE,T2- mLDP-P2MP,T3- PIM-SSM,T4-'
                            + ' PIM-SM,T5- PIM-Bidir'+"\n"
                            + '       T6- Ingress-Replication,T7- mLDP-MP2MP,T1'
                            + '1- BIER'+"\n"
                            + '(flags:type:label:id)/Flags'
                              ;
                  type ncd:string-all {
                    length 0..119 ;
                  }
                }
                leaf ir-tunnel {
                  description 'Ingress replication tunnel.'+"\n"
                            + 'Flags: L- Local,R- Remote,J- Join Ptnl,S- Start '
                            + 'Ptnl,T0- No Ptnl '+"\n"
                            + '       T1- RSVP-TE,T2- mLDP-P2MP,T3- PIM-SSM,T4-'
                            + ' PIM-SM,T5- PIM-Bidir'+"\n"
                            + '       T6- Ingress-Replication,T7- mLDP-MP2MP,T1'
                            + '1- BIER'+"\n"
                            + '(flags:type:label:id)/Flags'
                              ;
                  type ncd:string-all {
                    length 0..119 ;
                  }
                }
                ncd:select origin-ip ;
              }
            }
            container inter-ases {
              description 'Inter-AS auto dicovery route.'
                          ;
              list inter-as {
                description 'Inter-AS auto dicovery route.'
                            ;
                key 'rd source-as'
                    ;
                leaf rd {
                  description RD. ;
                  type string {
                    length 0..23 ;
                  }
                }
                leaf source-as {
                  description 'Source autonomous system number.'
                              ;
                  type uint32 ;
                }
                leaf root-tunnel {
                  description 'Root Tunnel.'+"\n"
                            + 'Flags: L- Local,R- Remote,J- Join Ptnl,S- Start '
                            + 'Ptnl,T0- No Ptnl '+"\n"
                            + '       T1- RSVP-TE,T2- mLDP-P2MP,T3- PIM-SSM,T4-'
                            + ' PIM-SM,T5- PIM-Bidir'+"\n"
                            + '       T6- Ingress-Replication,T7- mLDP-MP2MP,T1'
                            + '1- BIER'+"\n"
                            + '(flags:type:label:id)/Flags'
                              ;
                  type ncd:string-all {
                    length 0..119 ;
                  }
                }
                leaf leaf-tunnel {
                  description 'Leaf Tunnel.'+"\n"
                            + 'Flags: L- Local,R- Remote,J- Join Ptnl,S- Start '
                            + 'Ptnl,T0- No Ptnl '+"\n"
                            + '       T1- RSVP-TE,T2- mLDP-P2MP,T3- PIM-SSM,T4-'
                            + ' PIM-SM,T5- PIM-Bidir'+"\n"
                            + '       T6- Ingress-Replication,T7- mLDP-MP2MP,T1'
                            + '1- BIER'+"\n"
                            + '(flags:type:label:id)/Flags'
                              ;
                  type ncd:string-all {
                    length 0..119 ;
                  }
                }
                leaf ir-tunnel {
                  description 'Ingress replication tunnel.'+"\n"
                            + 'Flags: L- Local,R- Remote,J- Join Ptnl,S- Start '
                            + 'Ptnl,T0- No Ptnl '+"\n"
                            + '       T1- RSVP-TE,T2- mLDP-P2MP,T3- PIM-SSM,T4-'
                            + ' PIM-SM,T5- PIM-Bidir'+"\n"
                            + '       T6- Ingress-Replication,T7- mLDP-MP2MP,T1'
                            + '1- BIER'+"\n"
                            + '(flags:type:label:id)/Flags'
                              ;
                  type ncd:string-all {
                    length 0..119 ;
                  }
                }
                ncd:select source-as ;
              }
            }
            container spmsi-ads {
              description 'Spmsi-AD auto dicovery route.'
                          ;
              list spmsi-ad {
                description 'Spmsi-AD auto dicovery route.'
                            ;
                key 'rd source group origin-ip'
                    ;
                leaf rd {
                  description RD. ;
                  type string {
                    length 0..23 ;
                  }
                }
                leaf source {
                  description 'Source address.'
                              ;
                  type ncd:ipv6-address ;
                }
                leaf group {
                  description 'Group address.'
                              ;
                  type ncd:ipv6-address ;
                }
                leaf origin-ip {
                  description 'Origin IP address.'
                              ;
                  type ncd:ipv4-address ;
                }
                leaf root-tunnel {
                  description 'Root Tunnel.'+"\n"
                            + 'Flags: L- Local,R- Remote,J- Join Ptnl,S- Start '
                            + 'Ptnl,T0- No Ptnl '+"\n"
                            + '       T1- RSVP-TE,T2- mLDP-P2MP,T3- PIM-SSM,T4-'
                            + ' PIM-SM,T5- PIM-Bidir'+"\n"
                            + '       T6- Ingress-Replication,T7- mLDP-MP2MP,T1'
                            + '1- BIER'+"\n"
                            + '(flags:type:label:id)/Flags'
                              ;
                  type ncd:string-all {
                    length 0..119 ;
                  }
                }
                leaf leaf-tunnel {
                  description 'Leaf Tunnel.'+"\n"
                            + 'Flags: L- Local,R- Remote,J- Join Ptnl,S- Start '
                            + 'Ptnl,T0- No Ptnl '+"\n"
                            + '       T1- RSVP-TE,T2- mLDP-P2MP,T3- PIM-SSM,T4-'
                            + ' PIM-SM,T5- PIM-Bidir'+"\n"
                            + '       T6- Ingress-Replication,T7- mLDP-MP2MP,T1'
                            + '1- BIER'+"\n"
                            + '(flags:type:label:id)/Flags'
                              ;
                  type ncd:string-all {
                    length 0..119 ;
                  }
                }
                leaf ir-tunnel {
                  description 'Ingress replication tunnel.'+"\n"
                            + 'Flags: L- Local,R- Remote,J- Join Ptnl,S- Start '
                            + 'Ptnl,T0- No Ptnl '+"\n"
                            + '       T1- RSVP-TE,T2- mLDP-P2MP,T3- PIM-SSM,T4-'
                            + ' PIM-SM,T5- PIM-Bidir'+"\n"
                            + '       T6- Ingress-Replication,T7- mLDP-MP2MP,T1'
                            + '1- BIER'+"\n"
                            + '(flags:type:label:id)/Flags'
                              ;
                  type ncd:string-all {
                    length 0..119 ;
                  }
                }
                ncd:select source ;
                ncd:select group ;
                ncd:select origin-ip ;
                ncd:select 'source group'
                           ;
                ncd:select 'source origin-ip'
                           ;
                ncd:select 'group origin-ip'
                           ;
                ncd:select 'source group origin-ip'
                           ;
              }
            }
            container leaf-ads {
              description 'Leaf-AD auto dicovery route.'
                          ;
              list leaf-ad {
                description 'Leaf-AD auto dicovery route.'
                            ;
                key 'type sub-rd sub-source sub-group sub-origin-ip sub-source-'
                  + 'as origin-ip'
                    ;
                leaf type {
                  description 'AD route type.'+"\n"
                            + '1:Intra-AS'+"\n"
                            + '2:Inter-AS'+"\n"
                            + '3:Spmsi-AD'
                              ;
                  type enumeration {
                    enum Intra-AS {
                      value 1 ;
                    }
                    enum Inter-AS {
                      value 2 ;
                    }
                    enum Spmsi-AD {
                      value 3 ;
                    }
                  }
                }
                leaf sub-rd {
                  description 'Sub RD.'
                              ;
                  type string {
                    length 0..23 ;
                  }
                }
                leaf sub-source {
                  description 'Sub source address.'
                              ;
                  type ncd:ipv6-address ;
                }
                leaf sub-group {
                  description 'Sub group address.'
                              ;
                  type ncd:ipv6-address ;
                }
                leaf sub-origin-ip {
                  description 'Sub origin IP address.'
                              ;
                  type ncd:ipv4-address ;
                }
                leaf sub-source-as {
                  description 'Sub source autonomous system number.'
                              ;
                  type uint32 ;
                }
                leaf origin-ip {
                  description 'Origin IP address.'
                              ;
                  type ncd:ipv4-address ;
                }
                leaf p-tunnel {
                  description 'Public tunnel.'+"\n"
                            + 'Flags: L- Local,R- Remote,J- Join Ptnl,S- Start '
                            + 'Ptnl,T0- No Ptnl '+"\n"
                            + '       T1- RSVP-TE,T2- mLDP-P2MP,T3- PIM-SSM,T4-'
                            + ' PIM-SM,T5- PIM-Bidir'+"\n"
                            + '       T6- Ingress-Replication,T7- mLDP-MP2MP,T1'
                            + '1- BIER'+"\n"
                            + '(flags:type:label:id)/Flags'
                              ;
                  type ncd:string-all {
                    length 0..119 ;
                  }
                }
                ncd:select origin-ip ;
              }
            }
            ncd:revise-date 2020-06-20 ;
          }
          container public-auto-discovery-route {
            description 'MVPN auto discovery route information of public instan'
                      + 'ce.'
                        ;
            container intra-ases {
              description 'Intra-AS auto dicovery route.'
                          ;
              list intra-as {
                description 'Intra-AS auto dicovery route.'
                            ;
                key 'rd origin-ip'
                    ;
                leaf rd {
                  description RD. ;
                  type string {
                    length 0..23 ;
                  }
                }
                leaf origin-ip {
                  description 'Origin IP address.'
                              ;
                  type ncd:ipv4-address ;
                }
                leaf root-tunnel {
                  description 'Root Tunnel.'+"\n"
                            + 'Flags: L- Local,R- Remote,J- Join Ptnl,S- Start '
                            + 'Ptnl,T0- No Ptnl '+"\n"
                            + '       T1- RSVP-TE,T2- mLDP-P2MP,T3- PIM-SSM,T4-'
                            + ' PIM-SM,T5- PIM-Bidir'+"\n"
                            + '       T6- Ingress-Replication,T7- mLDP-MP2MP,T1'
                            + '1- BIER'+"\n"
                            + '(flags:type:label:id)/Flags'
                              ;
                  type ncd:string-all {
                    length 0..119 ;
                  }
                }
                leaf leaf-tunnel {
                  description 'Leaf Tunnel.'+"\n"
                            + 'Flags: L- Local,R- Remote,J- Join Ptnl,S- Start '
                            + 'Ptnl,T0- No Ptnl '+"\n"
                            + '       T1- RSVP-TE,T2- mLDP-P2MP,T3- PIM-SSM,T4-'
                            + ' PIM-SM,T5- PIM-Bidir'+"\n"
                            + '       T6- Ingress-Replication,T7- mLDP-MP2MP,T1'
                            + '1- BIER'+"\n"
                            + '(flags:type:label:id)/Flags'
                              ;
                  type ncd:string-all {
                    length 0..119 ;
                  }
                }
                leaf ir-tunnel {
                  description 'Ingress replication tunnel.'+"\n"
                            + 'Flags: L- Local,R- Remote,J- Join Ptnl,S- Start '
                            + 'Ptnl,T0- No Ptnl '+"\n"
                            + '       T1- RSVP-TE,T2- mLDP-P2MP,T3- PIM-SSM,T4-'
                            + ' PIM-SM,T5- PIM-Bidir'+"\n"
                            + '       T6- Ingress-Replication,T7- mLDP-MP2MP,T1'
                            + '1- BIER'+"\n"
                            + '(flags:type:label:id)/Flags'
                              ;
                  type ncd:string-all {
                    length 0..119 ;
                  }
                }
                ncd:select origin-ip ;
              }
            }
            container inter-ases {
              description 'Inter-AS auto dicovery route.'
                          ;
              list inter-as {
                description 'Inter-AS auto dicovery route.'
                            ;
                key 'rd source-as'
                    ;
                leaf rd {
                  description RD. ;
                  type string {
                    length 0..23 ;
                  }
                }
                leaf source-as {
                  description 'Source autonomous system number.'
                              ;
                  type uint32 ;
                }
                leaf root-tunnel {
                  description 'Root Tunnel.'+"\n"
                            + 'Flags: L- Local,R- Remote,J- Join Ptnl,S- Start '
                            + 'Ptnl,T0- No Ptnl '+"\n"
                            + '       T1- RSVP-TE,T2- mLDP-P2MP,T3- PIM-SSM,T4-'
                            + ' PIM-SM,T5- PIM-Bidir'+"\n"
                            + '       T6- Ingress-Replication,T7- mLDP-MP2MP,T1'
                            + '1- BIER'+"\n"
                            + '(flags:type:label:id)/Flags'
                              ;
                  type ncd:string-all {
                    length 0..119 ;
                  }
                }
                leaf leaf-tunnel {
                  description 'Leaf Tunnel.'+"\n"
                            + 'Flags: L- Local,R- Remote,J- Join Ptnl,S- Start '
                            + 'Ptnl,T0- No Ptnl '+"\n"
                            + '       T1- RSVP-TE,T2- mLDP-P2MP,T3- PIM-SSM,T4-'
                            + ' PIM-SM,T5- PIM-Bidir'+"\n"
                            + '       T6- Ingress-Replication,T7- mLDP-MP2MP,T1'
                            + '1- BIER'+"\n"
                            + '(flags:type:label:id)/Flags'
                              ;
                  type ncd:string-all {
                    length 0..119 ;
                  }
                }
                leaf ir-tunnel {
                  description 'Ingress replication tunnel.'+"\n"
                            + 'Flags: L- Local,R- Remote,J- Join Ptnl,S- Start '
                            + 'Ptnl,T0- No Ptnl '+"\n"
                            + '       T1- RSVP-TE,T2- mLDP-P2MP,T3- PIM-SSM,T4-'
                            + ' PIM-SM,T5- PIM-Bidir'+"\n"
                            + '       T6- Ingress-Replication,T7- mLDP-MP2MP,T1'
                            + '1- BIER'+"\n"
                            + '(flags:type:label:id)/Flags'
                              ;
                  type ncd:string-all {
                    length 0..119 ;
                  }
                }
                ncd:select source-as ;
              }
            }
            container spmsi-ads {
              description 'Spmsi-AD auto dicovery route.'
                          ;
              list spmsi-ad {
                description 'Spmsi-AD auto dicovery route.'
                            ;
                key 'rd source group origin-ip'
                    ;
                leaf rd {
                  description RD. ;
                  type string {
                    length 0..23 ;
                  }
                }
                leaf source {
                  description 'Source address.'
                              ;
                  type ncd:ipv6-address ;
                }
                leaf group {
                  description 'Group address.'
                              ;
                  type ncd:ipv6-address ;
                }
                leaf origin-ip {
                  description 'Origin IP address.'
                              ;
                  type ncd:ipv4-address ;
                }
                leaf root-tunnel {
                  description 'Root Tunnel.'+"\n"
                            + 'Flags: L- Local,R- Remote,J- Join Ptnl,S- Start '
                            + 'Ptnl,T0- No Ptnl '+"\n"
                            + '       T1- RSVP-TE,T2- mLDP-P2MP,T3- PIM-SSM,T4-'
                            + ' PIM-SM,T5- PIM-Bidir'+"\n"
                            + '       T6- Ingress-Replication,T7- mLDP-MP2MP,T1'
                            + '1- BIER'+"\n"
                            + '(flags:type:label:id)/Flags'
                              ;
                  type ncd:string-all {
                    length 0..119 ;
                  }
                }
                leaf leaf-tunnel {
                  description 'Leaf Tunnel.'+"\n"
                            + 'Flags: L- Local,R- Remote,J- Join Ptnl,S- Start '
                            + 'Ptnl,T0- No Ptnl '+"\n"
                            + '       T1- RSVP-TE,T2- mLDP-P2MP,T3- PIM-SSM,T4-'
                            + ' PIM-SM,T5- PIM-Bidir'+"\n"
                            + '       T6- Ingress-Replication,T7- mLDP-MP2MP,T1'
                            + '1- BIER'+"\n"
                            + '(flags:type:label:id)/Flags'
                              ;
                  type ncd:string-all {
                    length 0..119 ;
                  }
                }
                leaf ir-tunnel {
                  description 'Ingress replication tunnel.'+"\n"
                            + 'Flags: L- Local,R- Remote,J- Join Ptnl,S- Start '
                            + 'Ptnl,T0- No Ptnl '+"\n"
                            + '       T1- RSVP-TE,T2- mLDP-P2MP,T3- PIM-SSM,T4-'
                            + ' PIM-SM,T5- PIM-Bidir'+"\n"
                            + '       T6- Ingress-Replication,T7- mLDP-MP2MP,T1'
                            + '1- BIER'+"\n"
                            + '(flags:type:label:id)/Flags'
                              ;
                  type ncd:string-all {
                    length 0..119 ;
                  }
                }
                ncd:select source ;
                ncd:select group ;
                ncd:select origin-ip ;
                ncd:select 'source group'
                           ;
                ncd:select 'source origin-ip'
                           ;
                ncd:select 'group origin-ip'
                           ;
                ncd:select 'source group origin-ip'
                           ;
              }
            }
            container leaf-ads {
              description 'Leaf-AD auto dicovery route.'
                          ;
              list leaf-ad {
                description 'Leaf-AD auto dicovery route.'
                            ;
                key 'type sub-rd sub-source sub-group sub-origin-ip sub-source-'
                  + 'as origin-ip'
                    ;
                leaf type {
                  description 'AD route type.'+"\n"
                            + '1:Intra-AS'+"\n"
                            + '2:Inter-AS'+"\n"
                            + '3:Spmsi-AD'
                              ;
                  type enumeration {
                    enum Intra-AS {
                      value 1 ;
                    }
                    enum Inter-AS {
                      value 2 ;
                    }
                    enum Spmsi-AD {
                      value 3 ;
                    }
                  }
                }
                leaf sub-rd {
                  description 'Sub RD.'
                              ;
                  type string {
                    length 0..23 ;
                  }
                }
                leaf sub-source {
                  description 'Sub source address.'
                              ;
                  type ncd:ipv6-address ;
                }
                leaf sub-group {
                  description 'Sub group address.'
                              ;
                  type ncd:ipv6-address ;
                }
                leaf sub-origin-ip {
                  description 'Sub origin IP address.'
                              ;
                  type ncd:ipv4-address ;
                }
                leaf sub-source-as {
                  description 'Sub source autonomous system number.'
                              ;
                  type uint32 ;
                }
                leaf origin-ip {
                  description 'Origin IP address.'
                              ;
                  type ncd:ipv4-address ;
                }
                leaf p-tunnel {
                  description 'Public tunnel.'+"\n"
                            + 'Flags: L- Local,R- Remote,J- Join Ptnl,S- Start '
                            + 'Ptnl,T0- No Ptnl '+"\n"
                            + '       T1- RSVP-TE,T2- mLDP-P2MP,T3- PIM-SSM,T4-'
                            + ' PIM-SM,T5- PIM-Bidir'+"\n"
                            + '       T6- Ingress-Replication,T7- mLDP-MP2MP,T1'
                            + '1- BIER'+"\n"
                            + '(flags:type:label:id)/Flags'
                              ;
                  type ncd:string-all {
                    length 0..119 ;
                  }
                }
                ncd:select origin-ip ;
              }
            }
            container source-actives {
              description 'Source active auto dicovery route.'
                          ;
              list source-active {
                description 'Source active auto dicovery route.'
                            ;
                key 'ad-state rd source group'
                    ;
                leaf ad-state {
                  description 'AD route state.
0:Remote
1:Local'
                              ;
                  type enumeration {
                    enum Remote {
                      value 0 ;
                    }
                    enum Local {
                      value 1 ;
                    }
                  }
                }
                leaf rd {
                  description RD. ;
                  type string {
                    length 0..23 ;
                  }
                }
                leaf source {
                  description 'Source address.'
                              ;
                  type ncd:ipv6-address ;
                }
                leaf group {
                  description 'Group address.'
                              ;
                  type ncd:ipv6-address ;
                }
                leaf nexthop {
                  description 'Nexthop address.'
                              ;
                  type ncd:ipv4-address ;
                }
                ncd:select source ;
                ncd:select group ;
                ncd:select 'source group'
                           ;
              }
            }
            container xg-joins {
              description 'XG join route.'
                          ;
              list xg-join {
                description 'XG join route.'
                            ;
                key 'ad-state rd source-as rp-addr group'
                    ;
                leaf ad-state {
                  description 'AD route state.
0:Remote
1:Local'
                              ;
                  type enumeration {
                    enum Remote {
                      value 0 ;
                    }
                    enum Local {
                      value 1 ;
                    }
                  }
                }
                leaf rd {
                  description RD. ;
                  type string {
                    length 0..23 ;
                  }
                }
                leaf source-as {
                  description 'Source autonomous system number.'
                              ;
                  type uint32 ;
                }
                leaf rp-addr {
                  description 'RP address.'
                              ;
                  type ncd:ipv6-address ;
                }
                leaf group {
                  description 'Group address.'
                              ;
                  type ncd:ipv6-address ;
                }
                leaf nexthop {
                  description 'Nexthop address.'
                              ;
                  type ncd:ipv4-address ;
                }
                ncd:select rp-addr ;
                ncd:select group ;
                ncd:select 'rp-addr group'
                           ;
              }
            }
            container sg-joins {
              description 'SG join route.'
                          ;
              list sg-join {
                description 'SG join route.'
                            ;
                key 'ad-state rd source-as source group'
                    ;
                leaf ad-state {
                  description 'AD route state.
0:Remote
1:Local'
                              ;
                  type enumeration {
                    enum Remote {
                      value 0 ;
                    }
                    enum Local {
                      value 1 ;
                    }
                  }
                }
                leaf rd {
                  description RD. ;
                  type string {
                    length 0..23 ;
                  }
                }
                leaf source-as {
                  description 'Source autonomous system number.'
                              ;
                  type uint32 ;
                }
                leaf source {
                  description 'Source address.'
                              ;
                  type ncd:ipv6-address ;
                }
                leaf group {
                  description 'Group address.'
                              ;
                  type ncd:ipv6-address ;
                }
                leaf nexthop {
                  description 'Nexthop address.'
                              ;
                  type ncd:ipv4-address ;
                }
                ncd:select source ;
                ncd:select group ;
                ncd:select 'source group'
                           ;
              }
            }
            ncd:revise-date 2020-06-20 ;
          }
          container mtibs {
            description 'MVPN tunnel information.'
                        ;
            list mtib {
              description 'MVPN tunnel information.'
                          ;
              key 'tunnel-id tunnel-type'
                  ;
              leaf tunnel-id {
                description 'Tunnel ID.'
                            ;
                type uint32 ;
              }
              leaf tunnel-type {
                description 'Tunnel type.'+"\n"
                          + '0:No-Tunnel'+"\n"
                          + '1:TE-P2MP'+"\n"
                          + '2:mLDP-P2MP'+"\n"
                          + '3:PIM-SSM'+"\n"
                          + '4:PIM-SM'+"\n"
                          + '5:PIM-BIDIR'+"\n"
                          + '6:INGRESS-RPL'+"\n"
                          + '7:mLDP-MP2MP'+"\n"
                          + '11:BIER'
                            ;
                type enumeration {
                  enum No-Tunnel {
                    value 0 ;
                  }
                  enum TE-P2MP {
                    value 1 ;
                  }
                  enum mLDP-P2MP {
                    value 2 ;
                  }
                  enum PIM-SSM {
                    value 3 ;
                  }
                  enum PIM-SM {
                    value 4 ;
                  }
                  enum PIM-BIDIR {
                    value 5 ;
                  }
                  enum INGRESS-RPL {
                    value 6 ;
                  }
                  enum mLDP-MP2MP {
                    value 7 ;
                  }
                  enum BIER {
                    value 11 ;
                  }
                }
              }
              leaf tunnel-state {
                description 'Tunnel state.
0:Root
1:Leaf'
                            ;
                type enumeration {
                  enum Root {
                    value 0 ;
                  }
                  enum Leaf {
                    value 1 ;
                  }
                }
              }
              leaf leaf-require {
                description 'Leaf require.
0:N
1:Y'
                            ;
                type enumeration {
                  enum N {
                    value 0 ;
                  }
                  enum Y {
                    value 1 ;
                  }
                }
              }
              leaf protocol-state {
                description 'Protocol state.
0:Up
1:Down
2:Join
3:Leave'
                            ;
                type enumeration {
                  enum Up {
                    value 0 ;
                  }
                  enum Down {
                    value 1 ;
                  }
                  enum Join {
                    value 2 ;
                  }
                  enum Leave {
                    value 3 ;
                  }
                }
              }
              leaf tunnel-label {
                description 'Tunnel label.'
                            ;
                type uint32 ;
              }
              leaf tunnel-attr {
                description 'Tunnel attribute.'
                            ;
                type ncd:string-all {
                  length 0..119 ;
                }
              }
              leaf leave-delay {
                description 'Leave delay.'
                            ;
                type string {
                  length 0..15 ;
                }
              }
              container multi-imports {
                description 'Multi-import VPN infomation.'
                            ;
                list multi-import {
                  description 'Multi-import VPN infomation.'
                              ;
                  key sub-vrf-name ;
                  leaf sub-vrf-name {
                    description 'Multi-import VPN Routing/Forwarding instance n'
                              + 'ame.'+"\n"
                              + 'If the instance is public, the value of the no'
                              + 'de is IP global, else is VRF name.'
                                ;
                    type ncd:string-all {
                      length 1..32 ;
                    }
                  }
                  leaf sub-tunnel-state {
                    description 'Tunnel state.'
                                ;
                    type ncd:string-all {
                      length 0..15 ;
                    }
                  }
                  ncd:select sub-vrf-name ;
                }
              }
              ncd:select 'tunnel-id tunnel-type'
                         ;
            }
            ncd:revise-date 2020-06-20 ;
          }
          container mribs {
            description 'MVPN route information.'
                        ;
            list mrib {
              description 'MVPN route information.'
                          ;
              key 'source group'
                  ;
              leaf source {
                description 'Source address.'
                            ;
                type ncd:ipv6-address ;
              }
              leaf group {
                description 'Group address.'
                            ;
                type ncd:ipv6-address ;
              }
              leaf intf-state {
                description 'Interface state.'+"\n"
                          + 'IFT -- Receive from P-tunnel'+"\n"
                          + 'OFT -- Send to P-tunnel'+"\n"
                          + 'OFNL -- Downstream join state'
                            ;
                type string {
                  length 0..15 ;
                }
              }
              leaf upstream-tunnel {
                description 'Upstream tunnel.'
                            ;
                type ncd:string-all {
                  length 0..79 ;
                }
              }
              leaf upstream-pe {
                description 'Upstream PE address.'
                            ;
                type ncd:ipv4-address ;
              }
              leaf rpf-tunnel-id {
                description 'RPF tunnel ID.'
                            ;
                type uint32 ;
              }
              leaf rpf-vrf-name {
                description 'RPF VPN Routing/Forwarding instance name.'
                            ;
                type string {
                  length 0..32 ;
                }
              }
              leaf downstream-tunnel {
                description 'Downstream tunnel.'
                            ;
                type ncd:string-all {
                  length 0..79 ;
                }
              }
              leaf switch-tunnel {
                description 'Switch tunnel.'
                            ;
                type ncd:string-all {
                  length 0..79 ;
                }
              }
              leaf switch-time {
                description 'Switch time.'
                            ;
                type string {
                  length 0..15 ;
                }
              }
              container spmsi-auto-discoveries {
                description 'Spmsi-AD auto dicovery route.'
                            ;
                list spmsi-auto-discovery {
                  description 'Spmsi-AD auto dicovery route.'
                              ;
                  key 'rd source group origin-ip'
                      ;
                  leaf rd {
                    description RD. ;
                    type string {
                      length 0..23 ;
                    }
                  }
                  leaf source {
                    description 'Source address.'
                                ;
                    type ncd:ipv6-address ;
                  }
                  leaf group {
                    description 'Group address.'
                                ;
                    type ncd:ipv6-address ;
                  }
                  leaf origin-ip {
                    description 'Origin IP address.'
                                ;
                    type ncd:ipv4-address ;
                  }
                  leaf ad-state {
                    description 'AD route state.'+"\n"
                              + '0:Remote'+"\n"
                              + '1:Local'+"\n"
                              + '2:Local/Remote'
                                ;
                    type enumeration {
                      enum Remote {
                        value 0 ;
                      }
                      enum Local {
                        value 1 ;
                      }
                      enum Local/Remote {
                        value 2 ;
                      }
                    }
                  }
                  leaf root-tunnel {
                    description 'Root tunnel.'
                                ;
                    type ncd:string-all {
                      length 0..79 ;
                    }
                  }
                  leaf leaf-tunnel {
                    description 'Leaf tunnel.'
                                ;
                    type ncd:string-all {
                      length 0..79 ;
                    }
                  }
                  leaf ir-tunnel {
                    description 'Ingress replication tunnel.'
                                ;
                    type ncd:string-all {
                      length 0..79 ;
                    }
                  }
                  leaf uptime {
                    description Uptime. ;
                    type string {
                      length 0..15 ;
                    }
                  }
                  ncd:select origin-ip ;
                }
              }
              container leaf-auto-discoveries {
                description 'Leaf-AD auto discovery route.'
                            ;
                list leaf-auto-discovery {
                  description 'Leaf-AD auto discovery route.'
                              ;
                  key 'type sub-rd sub-source sub-group sub-origin-ip origin-ip'
                      ;
                  leaf type {
                    description 'AD route type.'+"\n"
                              + '1:Intra-AS'+"\n"
                              + '2:Inter-AS'+"\n"
                              + '3:Spmsi-AD'
                                ;
                    type enumeration {
                      enum Intra-AS {
                        value 1 ;
                      }
                      enum Inter-AS {
                        value 2 ;
                      }
                      enum Spmsi-AD {
                        value 3 ;
                      }
                    }
                  }
                  leaf sub-rd {
                    description 'Sub RD.'
                                ;
                    type string {
                      length 0..23 ;
                    }
                  }
                  leaf sub-source {
                    description 'Sub source address.'
                                ;
                    type ncd:ipv6-address ;
                  }
                  leaf sub-group {
                    description 'Sub group address.'
                                ;
                    type ncd:ipv6-address ;
                  }
                  leaf sub-origin-ip {
                    description 'Sub origin IP.'
                                ;
                    type ncd:ipv4-address ;
                  }
                  leaf origin-ip {
                    description 'Origin IP address.'
                                ;
                    type ncd:ipv4-address ;
                  }
                  leaf ad-state {
                    description 'AD route state.'+"\n"
                              + '0:Remote'+"\n"
                              + '1:Local'+"\n"
                              + '2:Local/Remote'
                                ;
                    type enumeration {
                      enum Remote {
                        value 0 ;
                      }
                      enum Local {
                        value 1 ;
                      }
                      enum Local/Remote {
                        value 2 ;
                      }
                    }
                  }
                  leaf uptime {
                    description Uptime. ;
                    type string {
                      length 0..15 ;
                    }
                  }
                  ncd:select origin-ip ;
                }
              }
              container source-actives {
                description 'Source active auto dicovery route.'
                            ;
                list source-active {
                  description 'Source active auto dicovery route.'
                              ;
                  key 'ad-state rd source group'
                      ;
                  leaf ad-state {
                    description 'AD route state.
0:Remote
1:Local'
                                ;
                    type enumeration {
                      enum Remote {
                        value 0 ;
                      }
                      enum Local {
                        value 1 ;
                      }
                    }
                  }
                  leaf rd {
                    description RD. ;
                    type string {
                      length 0..23 ;
                    }
                  }
                  leaf source {
                    description 'Source address.'
                                ;
                    type ncd:ipv6-address ;
                  }
                  leaf group {
                    description 'Group address.'
                                ;
                    type ncd:ipv6-address ;
                  }
                  leaf uptime {
                    description Uptime. ;
                    type string {
                      length 0..15 ;
                    }
                  }
                  ncd:select ad-state ;
                }
              }
              container xg-joins {
                description 'XG join route.'
                            ;
                list xg-join {
                  description 'XG join route.'
                              ;
                  key 'ad-state rd source-as rp-addr group'
                      ;
                  leaf ad-state {
                    description 'AD route state.
0:Remote
1:Local'
                                ;
                    type enumeration {
                      enum Remote {
                        value 0 ;
                      }
                      enum Local {
                        value 1 ;
                      }
                    }
                  }
                  leaf rd {
                    description RD. ;
                    type string {
                      length 0..23 ;
                    }
                  }
                  leaf source-as {
                    description 'Source autonomous system number.'
                                ;
                    type uint32 ;
                  }
                  leaf rp-addr {
                    description 'RP address.'
                                ;
                    type ncd:ipv6-address ;
                  }
                  leaf group {
                    description 'Group address.'
                                ;
                    type ncd:ipv6-address ;
                  }
                  leaf uptime {
                    description Uptime. ;
                    type string {
                      length 0..15 ;
                    }
                  }
                  ncd:select ad-state ;
                }
              }
              container sg-joins {
                description 'SG join route.'
                            ;
                list sg-join {
                  description 'SG join route.'
                              ;
                  key 'ad-state rd source-as source group'
                      ;
                  leaf ad-state {
                    description 'AD route state.
0:Remote
1:Local'
                                ;
                    type enumeration {
                      enum Remote {
                        value 0 ;
                      }
                      enum Local {
                        value 1 ;
                      }
                    }
                  }
                  leaf rd {
                    description RD. ;
                    type string {
                      length 0..23 ;
                    }
                  }
                  leaf source-as {
                    description 'Source autonomous system number.'
                                ;
                    type uint32 ;
                  }
                  leaf source {
                    description 'Source address.'
                                ;
                    type ncd:ipv6-address ;
                  }
                  leaf group {
                    description 'Group address.'
                                ;
                    type ncd:ipv6-address ;
                  }
                  leaf uptime {
                    description Uptime. ;
                    type string {
                      length 0..15 ;
                    }
                  }
                  ncd:select ad-state ;
                }
              }
              ncd:select source ;
              ncd:select group ;
              ncd:select 'source group'
                         ;
            }
            ncd:revise-date 2020-06-20 ;
          }
          container ad-summary {
            description 'The summary information of AD route.'
                        ;
            leaf intra-as-local {
              description 'Local intra-AS route summary.'
                          ;
              type uint32 ;
            }
            leaf intra-as-remote {
              description 'Remote intra-AS route summary.'
                          ;
              type uint32 ;
            }
            leaf intra-as-all {
              description 'Intra-AS route summary.'
                          ;
              type uint32 ;
            }
            leaf inter-as-local {
              description 'Local inter-AS route summary.'
                          ;
              type uint32 ;
            }
            leaf inter-as-remote {
              description 'Remote inter-AS route summary.'
                          ;
              type uint32 ;
            }
            leaf inter-as-all {
              description 'Inter-AS route summary.'
                          ;
              type uint32 ;
            }
            leaf spmsi-ad-local {
              description 'Local spmsi-AD route summary.'
                          ;
              type uint32 ;
            }
            leaf spmsi-ad-remote {
              description 'Remote spmsi-AD route summary.'
                          ;
              type uint32 ;
            }
            leaf spmsi-ad-all {
              description 'Spmsi-AD route summary.'
                          ;
              type uint32 ;
            }
            leaf leaf-ad-local {
              description 'Local leaf-AD route summary.'
                          ;
              type uint32 ;
            }
            leaf leaf-ad-remote {
              description 'Remote leaf-AD route summary.'
                          ;
              type uint32 ;
            }
            leaf leaf-ad-all {
              description 'Leaf-AD route summary.'
                          ;
              type uint32 ;
            }
            leaf source-active-local {
              description 'Local source active route summary.'
                          ;
              type uint32 ;
            }
            leaf source-active-remote {
              description 'Remote source active route summary.'
                          ;
              type uint32 ;
            }
            leaf source-active-all {
              description 'Source active route summary.'
                          ;
              type uint32 ;
            }
            leaf xg-join-local {
              description 'Local XG join route summary.'
                          ;
              type uint32 ;
            }
            leaf xg-join-remote {
              description 'Remote XG join route summary.'
                          ;
              type uint32 ;
            }
            leaf xg-join-all {
              description 'XG join route summary.'
                          ;
              type uint32 ;
            }
            leaf sg-join-local {
              description 'Local SG join route summary.'
                          ;
              type uint32 ;
            }
            leaf sg-join-remote {
              description 'Remote SG join route summary.'
                          ;
              type uint32 ;
            }
            leaf sg-join-all {
              description 'SG join route summary.'
                          ;
              type uint32 ;
            }
            leaf local-ad-all {
              description 'Local AD route summary.'
                          ;
              type uint32 ;
            }
            leaf remote-ad-all {
              description 'Remote AD route summary.'
                          ;
              type uint32 ;
            }
            leaf ad-all {
              description 'AD route summary.'
                          ;
              type uint32 ;
            }
            ncd:revise-date 2020-06-20 ;
          }
          container public-ad-summary {
            description 'The summary information of AD route of public instance.'
                        ;
            leaf intra-as-local {
              description 'Local intra-AS route summary.'
                          ;
              type uint32 ;
            }
            leaf intra-as-remote {
              description 'Remote intra-AS route summary.'
                          ;
              type uint32 ;
            }
            leaf intra-as-all {
              description 'Intra-AS route summary.'
                          ;
              type uint32 ;
            }
            leaf inter-as-local {
              description 'Local inter-AS route summary.'
                          ;
              type uint32 ;
            }
            leaf inter-as-remote {
              description 'Remote inter-AS route summary.'
                          ;
              type uint32 ;
            }
            leaf inter-as-all {
              description 'Inter-AS route summary.'
                          ;
              type uint32 ;
            }
            leaf spmsi-ad-local {
              description 'Local spmsi-AD route summary.'
                          ;
              type uint32 ;
            }
            leaf spmsi-ad-remote {
              description 'Remote spmsi-AD route summary.'
                          ;
              type uint32 ;
            }
            leaf spmsi-ad-all {
              description 'Spmsi-AD route summary.'
                          ;
              type uint32 ;
            }
            leaf leaf-ad-local {
              description 'Local leaf-AD route summary.'
                          ;
              type uint32 ;
            }
            leaf leaf-ad-remote {
              description 'Remote leaf-AD route summary.'
                          ;
              type uint32 ;
            }
            leaf leaf-ad-all {
              description 'Leaf-AD route summary.'
                          ;
              type uint32 ;
            }
            leaf source-active-local {
              description 'Local source active route summary.'
                          ;
              type uint32 ;
            }
            leaf source-active-remote {
              description 'Remote source active route summary.'
                          ;
              type uint32 ;
            }
            leaf source-active-all {
              description 'Source active route summary.'
                          ;
              type uint32 ;
            }
            leaf xg-join-local {
              description 'Local XG join route summary.'
                          ;
              type uint32 ;
            }
            leaf xg-join-remote {
              description 'Remote XG join route summary.'
                          ;
              type uint32 ;
            }
            leaf xg-join-all {
              description 'XG join route summary.'
                          ;
              type uint32 ;
            }
            leaf sg-join-local {
              description 'Local SG join route summary.'
                          ;
              type uint32 ;
            }
            leaf sg-join-remote {
              description 'Remote SG join route summary.'
                          ;
              type uint32 ;
            }
            leaf sg-join-all {
              description 'SG join route summary.'
                          ;
              type uint32 ;
            }
            leaf local-ad-all {
              description 'Local AD route summary.'
                          ;
              type uint32 ;
            }
            leaf remote-ad-all {
              description 'Remote AD route summary.'
                          ;
              type uint32 ;
            }
            leaf ad-all {
              description 'AD route summary.'
                          ;
              type uint32 ;
            }
            ncd:revise-date 2020-06-20 ;
          }
          ncd:revise-date 2019-07-15 ;
        }
      }
      container private {
        description 'Private mode of IPv6 multicast.'
                    ;
        container mroutes {
          description 'Multicast route information.'
                      ;
          list mroute {
            description 'Multicast route information.'
                        ;
            key 'vrf-name group-addr source-addr'
                ;
            leaf vrf-name {
              description 'VRF name'
                          ;
              type string {
                length 1..32 ;
              }
            }
            leaf group-addr {
              description 'Group address'
                          ;
              type ncd:ipv6-address ;
            }
            leaf source-addr {
              description 'Source address'
                          ;
              type ncd:ipv6-address ;
            }
            leaf rp-addr {
              description 'RP address'
                          ;
              type ncd:ipv6-address ;
            }
            leaf iif-name {
              description 'Incoming interface name'
                          ;
              type ncd:string-all {
                length 0..31 ;
              }
            }
            leaf secondary-rpf-intf {
              description 'Secondary RPF interface name'
                          ;
              type ncd:string-all {
                length 0..31 ;
              }
            }
            leaf mrt-flag {
              description 'Mroute flag.'+"\n"
                        + 'NS:SPT upsend,RT:Reg upsend,MT:Tunnel,NTP:NTP join,B'
                        + ':Bidir,SU:Slave in use.'
                          ;
              type ncd:string-all {
                length 0..31 ;
              }
            }
            leaf mrt-type {
              description 'Mroute type:"STATIC","DYNAMIC".'
                          ;
              type ncd:string-all {
                length 0..19 ;
              }
            }
            leaf iif-flag {
              description 'Incoming interface flag.
NS:SPT upsend,MT:Tunnel.'
                          ;
              type ncd:string-all {
                length 0..31 ;
              }
            }
            leaf fallback-vrf {
              description 'The upstream instance name of mroute.If the instance'
                        + ' of upstream is public, the value of the node is IP '
                        + 'global, else is VRF name.'
                          ;
              type ncd:string-all {
                length 0..32 ;
              }
              ncd:revise-date 2015-12-09 ;
            }
            list oif-list {
              description 'Downstream interface list'
                          ;
              key oif-name ;
              leaf oif-name {
                description 'Downstream interface name'
                            ;
                type ncd:string-all {
                  length 0..31 ;
                }
              }
              leaf oif-flag {
                description 'Downstream interface flag.'+"\n"
                          + 'F:Forward,RT:Reg upsend,MT:Tunnel,DF:DF.'
                            ;
                type ncd:string-all {
                  length 0..31 ;
                }
              }
              ncd:select oif-name ;
            }
            list fallback-extranet {
              description 'Fallback extranet receiver info.'
                          ;
              key vrf-name ;
              leaf vrf-name {
                description 'The downstream instance name of mroute.If the inst'
                          + 'ance of downstream is public, the value of the nod'
                          + 'e is IP global, else is VRF name.'
                            ;
                type ncd:string-all {
                  length 1..32 ;
                }
              }
              ncd:revise-date 2015-12-09 ;
            }
            list vpn-extranet {
              description 'MVPN multi-import receiver info.'
                          ;
              key vrf-name ;
              leaf vrf-name {
                description 'VRF name.'
                            ;
                type ncd:string-all {
                  length 1..32 ;
                }
              }
              ncd:revise-date 2020-06-20 ;
            }
            list bier-info {
              description 'Bit index explicit replication information.'
                          ;
              key 'subdomain-id bfer-prefix'
                  ;
              leaf subdomain-id {
                description 'Subdomain ID.'
                            ;
                type uint8 {
                  range 0..255 ;
                }
              }
              leaf bfer-prefix {
                description 'BFER prefix.'
                            ;
                type string {
                  length 1..39 ;
                }
              }
              leaf bfr-id {
                description 'BFR ID.'
                            ;
                type uint16 {
                  range 0..65535 ;
                }
              }
              ncd:select bfer-prefix ;
              ncd:revise-date 2020-06-20 ;
            }
            ncd:select 'vrf-name group-addr source-addr'
                       ;
            ncd:select 'vrf-name group-addr'
                       ;
            ncd:select 'vrf-name source-addr'
                       ;
            ncd:select 'group-addr source-addr'
                       ;
            ncd:select vrf-name ;
            ncd:select group-addr ;
            ncd:select source-addr ;
          }
        }
        container summarys {
          description 'The summary information of mroute.'
                      ;
          list summary {
            description 'The summary information of mroute.'
                        ;
            key vrf-name ;
            leaf vrf-name {
              description 'VRF name'
                          ;
              type string {
                length 1..32 ;
              }
            }
            leaf xg-count {
              description 'XG summary'
                          ;
              type uint32 ;
            }
            leaf sg-count {
              description 'SG summary'
                          ;
              type uint32 ;
            }
            leaf mroute-count {
              description 'XG and SG mroute summary'
                          ;
              type uint32 ;
            }
            ncd:select vrf-name ;
          }
        }
        container briefs {
          description 'The brief information of mroute'
                      ;
          list brief {
            description 'The brief information of mroute'
                        ;
            key 'vrf-name group source'
                ;
            leaf vrf-name {
              description 'VRF name'
                          ;
              type string {
                length 1..32 ;
              }
            }
            leaf group {
              description 'Group address'
                          ;
              type ncd:ipv6-address ;
            }
            leaf source {
              description 'Source address'
                          ;
              type ncd:ipv6-address ;
            }
            leaf type {
              description 'Mroute type:"STATIC","DYNAMIC".'
                          ;
              type string {
                length 1..11 ;
              }
            }
            ncd:select vrf-name ;
            ncd:select group ;
            ncd:select source ;
            ncd:select 'vrf-name group'
                       ;
            ncd:select 'vrf-name source'
                       ;
            ncd:select 'group source'
                       ;
            ncd:select 'vrf-name group source'
                       ;
          }
        }
        container nexthops {
          description 'The nexthop information of mroute'
                      ;
          list nexthop {
            description 'The nexthop information of mroute'
                        ;
            key 'vrf-name dest-addr type'
                ;
            leaf vrf-name {
              description 'VRF name'
                          ;
              type string {
                length 1..32 ;
              }
            }
            leaf dest-addr {
              description 'Destination address'
                          ;
              type ncd:ipv6-address ;
            }
            leaf type {
              description 'Type:"Mstatic nexthop","Mdt nexthop","Mbgp nexthop",'
                        + '"Migp nexthop","Rtm nexthop"'
                          ;
              type ncd:string-all {
                length 0..31 ;
              }
              ncd:revise-date 2015-08-28 ;
            }
            leaf time {
              description 'Nexthop create time'
                          ;
              type ncd:string-all {
                length 0..31 ;
              }
            }
            leaf user {
              description 'Nexthop user:"PIM","DM","MSDP","MSN","MVPN"'
                          ;
              type ncd:string-all {
                length 0..31 ;
              }
            }
            leaf metric {
              description Metric ;
              type uint32 ;
            }
            leaf preference {
              description Preference ;
              type uint32 ;
            }
            leaf mask-len {
              description 'Mask length'
                          ;
              type uint16 ;
            }
            leaf flag {
              description 'Flag.'+"\n"
                        + 'L:Local,C:Connect,UNR:Unreachable unicast,CTOP:Acros'
                        + 's the backbone'
                          ;
              type ncd:string-all {
                length 0..31 ;
              }
            }
            leaf fallback-vrf {
              description 'The instance name of fallback nexthop.If the instanc'
                        + 'e of nexthop is public, the value of the node is IP '
                        + 'global, else is VRF name.'
                          ;
              type ncd:string-all {
                length 0..32 ;
              }
              ncd:revise-date 2015-12-09 ;
            }
            list ecmp {
              description 'ECMP information'
                          ;
              key 'nexthop oif-name'
                  ;
              leaf nexthop {
                description 'Nexthop address'
                            ;
                type ncd:ipv6-address ;
              }
              leaf oif-name {
                description 'Downstream interface name'
                            ;
                type ncd:string-all {
                  length 0..31 ;
                }
              }
              leaf oif-flag {
                description 'Downstream interface flag.'+"\n"
                          + 'Mdt:Mdt nexthop'+"\n"
                          + 'Down:Interface down'+"\n"
                          + 'S:Slave '+"\n"
                          + 'M:Maste'
                            ;
                type ncd:string-all {
                  length 0..31 ;
                }
              }
              leaf remote-pe {
                description 'Remote PE address.'
                            ;
                type ncd:ipv6-address ;
              }
              leaf real-nexthop {
                description 'Real nexthop address.'
                            ;
                type ncd:ipv6-address ;
              }
              ncd:select 'nexthop oif-name'
                         ;
            }
            ncd:select vrf-name ;
            ncd:select dest-addr ;
            ncd:select 'vrf-name dest-addr'
                       ;
          }
        }
        container mvpn {
          description 'MVPN show info.'
                      ;
          container mdts {
            description 'MDT information.'
                        ;
            list mdt {
              description 'MDT information.'
                          ;
              key vrf-name ;
              leaf vrf-name {
                description 'VPN Routing/Forwarding instance name.'
                            ;
                type string {
                  length 1..32 ;
                }
              }
              leaf default-mode {
                description 'MDT default mode.
0:NO-MDT
1:GRE
2:MLDP'
                            ;
                type enumeration {
                  enum NO-MDT {
                    value 0 ;
                    description 'NO-MDT mode.'
                                ;
                  }
                  enum GRE {
                    value 1 ;
                    description 'GRE default mode.'
                                ;
                  }
                  enum MLDP {
                    value 2 ;
                    description 'MLDP default mode.'
                                ;
                  }
                }
              }
              leaf data-mode {
                description 'MDT data mode.
0:NO-MDT
1:GRE
2:MLDP'
                            ;
                type enumeration {
                  enum NO-MDT {
                    value 0 ;
                    description 'NO-MDT mode.'
                                ;
                  }
                  enum GRE {
                    value 1 ;
                    description 'GRE data mode.'
                                ;
                  }
                  enum MLDP {
                    value 2 ;
                    description 'MLDP data mode.'
                                ;
                  }
                }
              }
              leaf root-id {
                description 'Root ID.'
                            ;
                type ncd:ipv4-address ;
              }
              leaf global-vpn-id {
                description 'Global VPN ID.'
                            ;
                type string {
                  length 0..15 ;
                }
              }
              leaf data-tree-num {
                description 'MLDP data tree number.'
                            ;
                type uint16 {
                  range 1..5000 ;
                }
              }
              leaf next-spmsi-index {
                description 'MLDP next spmsi index.'
                            ;
                type uint16 {
                  range 1..5000 ;
                }
              }
              leaf mtunnel-addr {
                description 'Mtunnel address.'
                            ;
                type ncd:ipv4-address ;
              }
              leaf mtunnel-name {
                description 'Mtunnel name.'
                            ;
                type ncd:ifname {
                  length 0..31 ;
                }
              }
              leaf mtunnel-state {
                description 'Mtunnel state.
"PIM-MDT disable"
"PIM ok"'
                            ;
                type ncd:string-all {
                  length 0..15 ;
                }
              }
              leaf default-group {
                description 'MDT default group address.'
                            ;
                type ncd:ipv4-address ;
              }
              leaf data-group {
                description 'MDT data group address.'
                            ;
                type ncd:ipv4-address ;
              }
              leaf data-group-mask-len {
                description 'MDT data group mask length.'
                            ;
                type uint8 {
                  range 24..32 ;
                }
              }
              leaf data-acl-name {
                description 'MDT data ACL name.'
                            ;
                type string {
                  length 0..31 ;
                }
              }
              ncd:select vrf-name ;
            }
            ncd:revise-date 2019-07-15 ;
          }
          container mdt-tlvs {
            description 'MDT TLV information.'
                        ;
            list mdt-tlv {
              description 'MDT TLV information.'
                          ;
              key 'vrf-name source group mdt-sender mdt-data'
                  ;
              leaf vrf-name {
                description 'VPN Routing/Forwarding instance name.'
                            ;
                type string {
                  length 1..32 ;
                }
              }
              leaf source {
                description 'Source address.'
                            ;
                type ncd:ipv6-address ;
              }
              leaf group {
                description 'Group address.'
                            ;
                type ncd:ipv6-address ;
              }
              leaf mdt-sender {
                description 'MDT TLV sender information.'
                            ;
                type ncd:string-with-blank {
                  length 1..99 ;
                }
              }
              leaf mdt-data {
                description 'MDT TLV data information.'
                            ;
                type ncd:string-with-blank {
                  length 1..99 ;
                }
              }
              leaf expire-time {
                description 'MDT TLV expire time.'
                            ;
                type string {
                  length 1..31 ;
                }
              }
              ncd:select vrf-name ;
              ncd:select 'vrf-name source'
                         ;
              ncd:select 'vrf-name group'
                         ;
              ncd:select 'vrf-name source group'
                         ;
            }
            ncd:revise-date 2019-07-15 ;
          }
          container instances {
            description 'MVPN instance information.'
                        ;
            list instance {
              description 'MVPN instance information.'
                          ;
              key vrf-name ;
              leaf vrf-name {
                description 'VPN Routing/Forwarding instance name.'
                            ;
                type string {
                  length 1..32 ;
                }
              }
              leaf rd {
                description RD. ;
                type string {
                  length 0..23 ;
                }
              }
              leaf import-rt {
                description 'MVPN import RT.'
                            ;
                type string {
                  length 0..23 ;
                }
              }
              leaf origin-ip {
                description 'Origin IP address.'
                            ;
                type ncd:ipv4-address ;
              }
              leaf te-id {
                description 'TE root ID.'
                            ;
                type ncd:ipv4-address ;
              }
              leaf origin-state {
                description 'Origin state.'+"\n"
                          + '"Un-routable"'+"\n"
                          + '"Routable,Local"'+"\n"
                          + '"Routable,Not Local"'
                            ;
                type ncd:string-all {
                  length 0..23 ;
                }
              }
              leaf te-state {
                description 'TE state.
"in-use"
"Not in-use"'
                            ;
                type ncd:string-all {
                  length 0..15 ;
                }
              }
              leaf mtunnel-type {
                description 'Mtunnel type.'+"\n"
                          + '0:No-Tunnel'+"\n"
                          + '1:TE-P2MP'+"\n"
                          + '2:mLDP-P2MP'+"\n"
                          + '3:PIM-SSM'+"\n"
                          + '4:PIM-SM'+"\n"
                          + '5:PIM-BIDIR'+"\n"
                          + '6:INGRESS-RPL'+"\n"
                          + '7:mLDP-MP2MP'+"\n"
                          + '8:PIM-MDT'+"\n"
                          + '11:BIER'
                            ;
                type enumeration {
                  enum No-Tunnel {
                    value 0 ;
                  }
                  enum TE-P2MP {
                    value 1 ;
                  }
                  enum mLDP-P2MP {
                    value 2 ;
                  }
                  enum PIM-SSM {
                    value 3 ;
                  }
                  enum PIM-SM {
                    value 4 ;
                  }
                  enum PIM-BIDIR {
                    value 5 ;
                  }
                  enum INGRESS-RPL {
                    value 6 ;
                  }
                  enum mLDP-MP2MP {
                    value 7 ;
                  }
                  enum PIM-MDT {
                    value 8 ;
                  }
                  enum BIER {
                    value 11 ;
                  }
                }
              }
              leaf route-state {
                description 'Route state.
0: Disable
1: Enable'
                            ;
                type enumeration {
                  enum Disable {
                    value 0 ;
                  }
                  enum Enable {
                    value 1 ;
                  }
                }
              }
              leaf mldp-state {
                description 'MLDP state.
0: Disable
1: Enable'
                            ;
                type enumeration {
                  enum Disable {
                    value 0 ;
                  }
                  enum Enable {
                    value 1 ;
                  }
                }
              }
              leaf p-pim-state {
                description 'P-PIM state.
0: Disable
1: Enable'
                            ;
                type enumeration {
                  enum Disable {
                    value 0 ;
                  }
                  enum Enable {
                    value 1 ;
                  }
                }
              }
              leaf c-pim-state {
                description 'C-PIM state.
0: Disable
1: Enable'
                            ;
                type enumeration {
                  enum Disable {
                    value 0 ;
                  }
                  enum Enable {
                    value 1 ;
                  }
                }
              }
              leaf us-protocol {
                description 'Upstream Protocol.
0: Unknown
1: BGP
2: PIM'
                            ;
                type enumeration {
                  enum Unknown {
                    value 0 ;
                  }
                  enum BGP {
                    value 1 ;
                  }
                  enum PIM {
                    value 2 ;
                  }
                }
              }
              leaf mtunnel-name {
                description 'Mtunnel name.'
                            ;
                type ncd:ifname {
                  length 0..31 ;
                }
              }
              leaf mtunnel-state {
                description 'Mtunnel state.'+"\n"
                          + '"up / PIM enable"'+"\n"
                          + '"down / PIM enable"'+"\n"
                          + '"up / PIM disable"'+"\n"
                          + '"down / PIM disable"'
                            ;
                type ncd:string-all {
                  length 0..23 ;
                }
              }
              leaf mtunnel-addr {
                description 'Mtunnel address.'
                            ;
                type ncd:ipv4-address ;
              }
              leaf default-group {
                description 'MDT default group address.'
                            ;
                type ncd:ipv4-address ;
              }
              leaf data-group {
                description 'MDT data group address.'
                            ;
                type ncd:ipv4-address ;
              }
              leaf data-group-mask-len {
                description 'MDT data group mask length.'
                            ;
                type uint8 {
                  range 24..32 ;
                }
              }
              leaf data-acl-name {
                description 'MDT data ACL name.'
                            ;
                type string {
                  length 0..31 ;
                }
              }
              ncd:select vrf-name ;
            }
          }
          container ad-routes {
            status obsolete {
              ncd:revise-date 2016-11-29 ;
            }
            description 'MVPN auto discovery route information.'
                        ;
            list ad-route {
              description 'MVPN auto discovery route information.'
                          ;
              key 'vrf-name pe-addr'
                  ;
              leaf vrf-name {
                description 'VPN Routing/Forwarding instance name.'
                            ;
                type string {
                  length 1..32 ;
                }
              }
              leaf pe-addr {
                description 'PE address.'
                            ;
                type ncd:ipv4-address ;
              }
              container intra-ases {
                description 'Intra-AS auto dicovery route.'
                            ;
                list intra-as {
                  description 'Intra-AS auto dicovery route.'
                              ;
                  key 'ad-state rd origin-ip'
                      ;
                  leaf ad-state {
                    description 'AD route state.
0:Remote
1:Local'
                                ;
                    type enumeration {
                      enum Remote {
                        value 0 ;
                      }
                      enum Local {
                        value 1 ;
                      }
                    }
                  }
                  leaf rd {
                    description RD. ;
                    type string {
                      length 0..23 ;
                    }
                  }
                  leaf origin-ip {
                    description 'Origin IP address.'
                                ;
                    type ncd:ipv4-address ;
                  }
                  leaf tunnel-label {
                    description 'Tunnel label.'
                                ;
                    type uint32 ;
                  }
                  leaf tunnel-type {
                    description 'Tunnel type.'+"\n"
                              + '0:No-Tunnel'+"\n"
                              + '1:TE-P2MP'+"\n"
                              + '2:mLDP-P2MP'+"\n"
                              + '3:PIM-SSM'+"\n"
                              + '4:PIM-SM'+"\n"
                              + '5:PIM-BIDIR'+"\n"
                              + '6:INGRESS-RPL'+"\n"
                              + '7:mLDP-MP2MP'
                                ;
                    type enumeration {
                      enum No-Tunnel {
                        value 0 ;
                      }
                      enum TE-P2MP {
                        value 1 ;
                      }
                      enum mLDP-P2MP {
                        value 2 ;
                      }
                      enum PIM-SSM {
                        value 3 ;
                      }
                      enum PIM-SM {
                        value 4 ;
                      }
                      enum PIM-BIDIR {
                        value 5 ;
                      }
                      enum INGRESS-RPL {
                        value 6 ;
                      }
                      enum mLDP-MP2MP {
                        value 7 ;
                      }
                    }
                  }
                  leaf tunnel-state {
                    description 'Tunnel state.
1:Leave
2:Join'
                                ;
                    type enumeration {
                      enum Leave {
                        value 1 ;
                      }
                      enum Join {
                        value 2 ;
                      }
                    }
                  }
                  leaf tunnel-id {
                    description 'Tunnel ID.'
                                ;
                    type string {
                      length 0..31 ;
                    }
                  }
                  ncd:select origin-ip ;
                }
              }
              container spmsi-ads {
                description 'Spmsi-AD auto dicovery route.'
                            ;
                list spmsi-ad {
                  description 'Spmsi-AD auto dicovery route.'
                              ;
                  key 'ad-state rd source group origin-ip'
                      ;
                  leaf ad-state {
                    description 'AD route state.
0:Remote
1:Local'
                                ;
                    type enumeration {
                      enum Remote {
                        value 0 ;
                      }
                      enum Local {
                        value 1 ;
                      }
                    }
                  }
                  leaf rd {
                    description RD. ;
                    type string {
                      length 0..23 ;
                    }
                  }
                  leaf source {
                    description 'Source address.'
                                ;
                    type ncd:ipv6-address ;
                  }
                  leaf group {
                    description 'Group address.'
                                ;
                    type ncd:ipv6-address ;
                  }
                  leaf origin-ip {
                    description 'Origin IP address.'
                                ;
                    type ncd:ipv4-address ;
                  }
                  leaf tunnel-label {
                    description 'Tunnel label.'
                                ;
                    type uint32 ;
                  }
                  leaf tunnel-type {
                    description 'Tunnel type.'+"\n"
                              + '0:No-Tunnel'+"\n"
                              + '1:TE-P2MP'+"\n"
                              + '2:mLDP-P2MP'+"\n"
                              + '3:PIM-SSM'+"\n"
                              + '4:PIM-SM'+"\n"
                              + '5:PIM-BIDIR'+"\n"
                              + '6:INGRESS-RPL'+"\n"
                              + '7:mLDP-MP2MP'
                                ;
                    type enumeration {
                      enum No-Tunnel {
                        value 0 ;
                      }
                      enum TE-P2MP {
                        value 1 ;
                      }
                      enum mLDP-P2MP {
                        value 2 ;
                      }
                      enum PIM-SSM {
                        value 3 ;
                      }
                      enum PIM-SM {
                        value 4 ;
                      }
                      enum PIM-BIDIR {
                        value 5 ;
                      }
                      enum INGRESS-RPL {
                        value 6 ;
                      }
                      enum mLDP-MP2MP {
                        value 7 ;
                      }
                    }
                  }
                  leaf tunnel-state {
                    description 'Tunnel state.
1:Leave
2:Join'
                                ;
                    type enumeration {
                      enum Leave {
                        value 1 ;
                      }
                      enum Join {
                        value 2 ;
                      }
                    }
                  }
                  leaf leaf-require {
                    description 'Leaf require.
0:N
1:Y'
                                ;
                    type enumeration {
                      enum N {
                        value 0 ;
                      }
                      enum Y {
                        value 1 ;
                      }
                    }
                  }
                  leaf tunnel-id {
                    description 'Tunnel ID.'
                                ;
                    type string {
                      length 0..31 ;
                    }
                  }
                  ncd:select source ;
                  ncd:select group ;
                  ncd:select origin-ip ;
                  ncd:select 'source group'
                             ;
                  ncd:select 'source origin-ip'
                             ;
                  ncd:select 'group origin-ip'
                             ;
                  ncd:select 'source group origin-ip'
                             ;
                }
              }
              container leaf-ads {
                description 'Leaf-AD auto dicovery route.'
                            ;
                list leaf-ad {
                  description 'Leaf-AD auto dicovery route.'
                              ;
                  key 'ad-state type spmsi-rd spmsi-source spmsi-group spmsi-or'
                    + 'igin-ip origin-ip'
                      ;
                  leaf ad-state {
                    description 'AD route state.
0:Remote
1:Local'
                                ;
                    type enumeration {
                      enum Remote {
                        value 0 ;
                      }
                      enum Local {
                        value 1 ;
                      }
                    }
                  }
                  leaf type {
                    description 'AD route type.
2:Inter-AS
3:Spmsi-AD'
                                ;
                    type enumeration {
                      enum Inter-AS {
                        value 2 ;
                      }
                      enum Spmsi-AD {
                        value 3 ;
                      }
                    }
                  }
                  leaf spmsi-rd {
                    description 'Spmsi-AD RD.'
                                ;
                    type string {
                      length 0..23 ;
                    }
                  }
                  leaf spmsi-source {
                    description 'Spmsi-AD source address.'
                                ;
                    type ncd:ipv6-address ;
                  }
                  leaf spmsi-group {
                    description 'Spmsi-AD group address.'
                                ;
                    type ncd:ipv6-address ;
                  }
                  leaf spmsi-origin-ip {
                    description 'Spmsi-AD origin IP address.'
                                ;
                    type ncd:ipv4-address ;
                  }
                  leaf origin-ip {
                    description 'Origin IP address.'
                                ;
                    type ncd:ipv4-address ;
                  }
                  leaf nexthop {
                    description 'Nexthop address.'
                                ;
                    type ncd:ipv4-address ;
                  }
                  ncd:select spmsi-source ;
                  ncd:select spmsi-group ;
                  ncd:select origin-ip ;
                  ncd:select 'spmsi-source spmsi-group'
                             ;
                  ncd:select 'spmsi-source origin-ip'
                             ;
                  ncd:select 'spmsi-group origin-ip'
                             ;
                  ncd:select 'spmsi-source spmsi-group origin-ip'
                             ;
                }
              }
              container source-actives {
                description 'Source-active auto dicovery route.'
                            ;
                list source-active {
                  description 'Source-active auto dicovery route.'
                              ;
                  key 'ad-state rd source group'
                      ;
                  leaf ad-state {
                    description 'AD route state.
0:Remote
1:Local'
                                ;
                    type enumeration {
                      enum Remote {
                        value 0 ;
                      }
                      enum Local {
                        value 1 ;
                      }
                    }
                  }
                  leaf rd {
                    description RD. ;
                    type string {
                      length 0..23 ;
                    }
                  }
                  leaf source {
                    description 'Source address.'
                                ;
                    type ncd:ipv6-address ;
                  }
                  leaf group {
                    description 'Group address.'
                                ;
                    type ncd:ipv6-address ;
                  }
                  leaf nexthop {
                    description 'Nexthop address.'
                                ;
                    type ncd:ipv4-address ;
                  }
                  ncd:select source ;
                  ncd:select group ;
                  ncd:select 'source group'
                             ;
                }
              }
              container xg-joins {
                description 'XG-join route.'
                            ;
                list xg-join {
                  description 'XG-join route.'
                              ;
                  key 'ad-state rd source-as rp-addr group'
                      ;
                  leaf ad-state {
                    description 'AD route state.
0:Remote
1:Local'
                                ;
                    type enumeration {
                      enum Remote {
                        value 0 ;
                      }
                      enum Local {
                        value 1 ;
                      }
                    }
                  }
                  leaf rd {
                    description RD. ;
                    type string {
                      length 0..23 ;
                    }
                  }
                  leaf source-as {
                    description 'Source autonomous system number.'
                                ;
                    type uint32 ;
                  }
                  leaf rp-addr {
                    description 'RP address.'
                                ;
                    type ncd:ipv6-address ;
                  }
                  leaf group {
                    description 'Group address.'
                                ;
                    type ncd:ipv6-address ;
                  }
                  leaf nexthop {
                    description 'Nexthop address.'
                                ;
                    type ncd:ipv4-address ;
                  }
                  ncd:select rp-addr ;
                  ncd:select group ;
                  ncd:select 'rp-addr group'
                             ;
                }
                ncd:revise-date 2015-08-12 ;
              }
              container sg-joins {
                description 'SG-join route.'
                            ;
                list sg-join {
                  description 'SG-join route.'
                              ;
                  key 'ad-state rd source-as source group'
                      ;
                  leaf ad-state {
                    description 'AD route state.
0:Remote
1:Local'
                                ;
                    type enumeration {
                      enum Remote {
                        value 0 ;
                      }
                      enum Local {
                        value 1 ;
                      }
                    }
                  }
                  leaf rd {
                    description RD. ;
                    type string {
                      length 0..23 ;
                    }
                  }
                  leaf source-as {
                    description 'Source autonomous system number.'
                                ;
                    type uint32 ;
                  }
                  leaf source {
                    description 'Source address.'
                                ;
                    type ncd:ipv6-address ;
                  }
                  leaf group {
                    description 'Group address.'
                                ;
                    type ncd:ipv6-address ;
                  }
                  leaf nexthop {
                    description 'Nexthop address.'
                                ;
                    type ncd:ipv4-address ;
                  }
                  ncd:select source ;
                  ncd:select group ;
                  ncd:select 'source group'
                             ;
                }
              }
              ncd:select vrf-name ;
            }
          }
          container auto-discovery-routes {
            description 'MVPN auto discovery route information.'
                        ;
            list auto-discovery-route {
              description 'MVPN auto discovery route information.'
                          ;
              key vrf-name ;
              leaf vrf-name {
                description 'VPN Routing/Forwarding instance name.'
                            ;
                type string {
                  length 1..32 ;
                }
              }
              container intra-ases {
                description 'Intra-AS auto dicovery route.'
                            ;
                list intra-as {
                  description 'Intra-AS auto dicovery route.'
                              ;
                  key 'rd origin-ip'
                      ;
                  leaf rd {
                    description RD. ;
                    type string {
                      length 0..23 ;
                    }
                  }
                  leaf origin-ip {
                    description 'Origin IP address.'
                                ;
                    type ncd:ipv4-address ;
                  }
                  leaf root-tunnel {
                    description 'Root Tunnel.'+"\n"
                              + 'Flags: L- Local,R- Remote,J- Join Ptnl,S- Star'
                              + 't Ptnl,T0- No Ptnl '+"\n"
                              + '       T1- RSVP-TE,T2- mLDP-P2MP,T3- PIM-SSM,T'
                              + '4- PIM-SM,T5- PIM-Bidir'+"\n"
                              + '       T6- Ingress-Replication,T7- mLDP-MP2MP,'
                              + 'T11- BIER'+"\n"
                              + '(flags:type:label:id)/Flags'
                                ;
                    type ncd:string-all {
                      length 0..119 ;
                    }
                  }
                  leaf leaf-tunnel {
                    description 'Leaf Tunnel.'+"\n"
                              + 'Flags: L- Local,R- Remote,J- Join Ptnl,S- Star'
                              + 't Ptnl,T0- No Ptnl '+"\n"
                              + '       T1- RSVP-TE,T2- mLDP-P2MP,T3- PIM-SSM,T'
                              + '4- PIM-SM,T5- PIM-Bidir'+"\n"
                              + '       T6- Ingress-Replication,T7- mLDP-MP2MP,'
                              + 'T11- BIER'+"\n"
                              + '(flags:type:label:id)/Flags'
                                ;
                    type ncd:string-all {
                      length 0..119 ;
                    }
                  }
                  leaf ir-tunnel {
                    description 'Ingress replication tunnel.'+"\n"
                              + 'Flags: L- Local,R- Remote,J- Join Ptnl,S- Star'
                              + 't Ptnl,T0- No Ptnl '+"\n"
                              + '       T1- RSVP-TE,T2- mLDP-P2MP,T3- PIM-SSM,T'
                              + '4- PIM-SM,T5- PIM-Bidir'+"\n"
                              + '       T6- Ingress-Replication,T7- mLDP-MP2MP,'
                              + 'T11- BIER'+"\n"
                              + '(flags:type:label:id)/Flags'
                                ;
                    type ncd:string-all {
                      length 0..119 ;
                    }
                  }
                  ncd:select origin-ip ;
                }
              }
              container inter-ases {
                description 'Inter-AS auto dicovery route.'
                            ;
                list inter-as {
                  description 'Inter-AS auto dicovery route.'
                              ;
                  key 'rd source-as'
                      ;
                  leaf rd {
                    description RD. ;
                    type string {
                      length 0..23 ;
                    }
                  }
                  leaf source-as {
                    description 'Source autonomous system number.'
                                ;
                    type uint32 ;
                  }
                  leaf root-tunnel {
                    description 'Root Tunnel.'+"\n"
                              + 'Flags: L- Local,R- Remote,J- Join Ptnl,S- Star'
                              + 't Ptnl,T0- No Ptnl '+"\n"
                              + '       T1- RSVP-TE,T2- mLDP-P2MP,T3- PIM-SSM,T'
                              + '4- PIM-SM,T5- PIM-Bidir'+"\n"
                              + '       T6- Ingress-Replication,T7- mLDP-MP2MP,'
                              + 'T11- BIER'+"\n"
                              + '(flags:type:label:id)/Flags'
                                ;
                    type ncd:string-all {
                      length 0..119 ;
                    }
                  }
                  leaf leaf-tunnel {
                    description 'Leaf Tunnel.'+"\n"
                              + 'Flags: L- Local,R- Remote,J- Join Ptnl,S- Star'
                              + 't Ptnl,T0- No Ptnl '+"\n"
                              + '       T1- RSVP-TE,T2- mLDP-P2MP,T3- PIM-SSM,T'
                              + '4- PIM-SM,T5- PIM-Bidir'+"\n"
                              + '       T6- Ingress-Replication,T7- mLDP-MP2MP,'
                              + 'T11- BIER'+"\n"
                              + '(flags:type:label:id)/Flags'
                                ;
                    type ncd:string-all {
                      length 0..119 ;
                    }
                  }
                  leaf ir-tunnel {
                    description 'Ingress replication tunnel.'+"\n"
                              + 'Flags: L- Local,R- Remote,J- Join Ptnl,S- Star'
                              + 't Ptnl,T0- No Ptnl '+"\n"
                              + '       T1- RSVP-TE,T2- mLDP-P2MP,T3- PIM-SSM,T'
                              + '4- PIM-SM,T5- PIM-Bidir'+"\n"
                              + '       T6- Ingress-Replication,T7- mLDP-MP2MP,'
                              + 'T11- BIER'+"\n"
                              + '(flags:type:label:id)/Flags'
                                ;
                    type ncd:string-all {
                      length 0..119 ;
                    }
                  }
                  ncd:select source-as ;
                }
              }
              container spmsi-ads {
                description 'Spmsi-AD auto dicovery route.'
                            ;
                list spmsi-ad {
                  description 'Spmsi-AD auto dicovery route.'
                              ;
                  key 'rd source group origin-ip'
                      ;
                  leaf rd {
                    description RD. ;
                    type string {
                      length 0..23 ;
                    }
                  }
                  leaf source {
                    description 'Source address.'
                                ;
                    type ncd:ipv6-address ;
                  }
                  leaf group {
                    description 'Group address.'
                                ;
                    type ncd:ipv6-address ;
                  }
                  leaf origin-ip {
                    description 'Origin IP address.'
                                ;
                    type ncd:ipv4-address ;
                  }
                  leaf root-tunnel {
                    description 'Root Tunnel.'+"\n"
                              + 'Flags: L- Local,R- Remote,J- Join Ptnl,S- Star'
                              + 't Ptnl,T0- No Ptnl '+"\n"
                              + '       T1- RSVP-TE,T2- mLDP-P2MP,T3- PIM-SSM,T'
                              + '4- PIM-SM,T5- PIM-Bidir'+"\n"
                              + '       T6- Ingress-Replication,T7- mLDP-MP2MP,'
                              + 'T11- BIER'+"\n"
                              + '(flags:type:label:id)/Flags'
                                ;
                    type ncd:string-all {
                      length 0..119 ;
                    }
                  }
                  leaf leaf-tunnel {
                    description 'Leaf Tunnel.'+"\n"
                              + 'Flags: L- Local,R- Remote,J- Join Ptnl,S- Star'
                              + 't Ptnl,T0- No Ptnl '+"\n"
                              + '       T1- RSVP-TE,T2- mLDP-P2MP,T3- PIM-SSM,T'
                              + '4- PIM-SM,T5- PIM-Bidir'+"\n"
                              + '       T6- Ingress-Replication,T7- mLDP-MP2MP,'
                              + 'T11- BIER'+"\n"
                              + '(flags:type:label:id)/Flags'
                                ;
                    type ncd:string-all {
                      length 0..119 ;
                    }
                  }
                  leaf ir-tunnel {
                    description 'Ingress replication tunnel.'+"\n"
                              + 'Flags: L- Local,R- Remote,J- Join Ptnl,S- Star'
                              + 't Ptnl,T0- No Ptnl '+"\n"
                              + '       T1- RSVP-TE,T2- mLDP-P2MP,T3- PIM-SSM,T'
                              + '4- PIM-SM,T5- PIM-Bidir'+"\n"
                              + '       T6- Ingress-Replication,T7- mLDP-MP2MP,'
                              + 'T11- BIER'+"\n"
                              + '(flags:type:label:id)/Flags'
                                ;
                    type ncd:string-all {
                      length 0..119 ;
                    }
                  }
                  ncd:select source ;
                  ncd:select group ;
                  ncd:select origin-ip ;
                  ncd:select 'source group'
                             ;
                  ncd:select 'source origin-ip'
                             ;
                  ncd:select 'group origin-ip'
                             ;
                  ncd:select 'source group origin-ip'
                             ;
                }
              }
              container leaf-ads {
                description 'Leaf-AD auto dicovery route.'
                            ;
                list leaf-ad {
                  description 'Leaf-AD auto dicovery route.'
                              ;
                  key 'type sub-rd sub-source sub-group sub-origin-ip sub-sourc'
                    + 'e-as origin-ip'
                      ;
                  leaf type {
                    description 'AD route type.'+"\n"
                              + '1:Intra-AS'+"\n"
                              + '2:Inter-AS'+"\n"
                              + '3:Spmsi-AD'
                                ;
                    type enumeration {
                      enum Intra-AS {
                        value 1 ;
                      }
                      enum Inter-AS {
                        value 2 ;
                      }
                      enum Spmsi-AD {
                        value 3 ;
                      }
                    }
                  }
                  leaf sub-rd {
                    description 'Sub RD.'
                                ;
                    type string {
                      length 0..23 ;
                    }
                  }
                  leaf sub-source {
                    description 'Sub source address.'
                                ;
                    type ncd:ipv6-address ;
                  }
                  leaf sub-group {
                    description 'Sub group address.'
                                ;
                    type ncd:ipv6-address ;
                  }
                  leaf sub-origin-ip {
                    description 'Sub origin IP address.'
                                ;
                    type ncd:ipv4-address ;
                  }
                  leaf sub-source-as {
                    description 'Sub source autonomous system number.'
                                ;
                    type uint32 ;
                  }
                  leaf origin-ip {
                    description 'Origin IP address.'
                                ;
                    type ncd:ipv4-address ;
                  }
                  leaf p-tunnel {
                    description 'Public tunnel.'+"\n"
                              + 'Flags: L- Local,R- Remote,J- Join Ptnl,S- Star'
                              + 't Ptnl,T0- No Ptnl '+"\n"
                              + '       T1- RSVP-TE,T2- mLDP-P2MP,T3- PIM-SSM,T'
                              + '4- PIM-SM,T5- PIM-Bidir'+"\n"
                              + '       T6- Ingress-Replication,T7- mLDP-MP2MP,'
                              + 'T11- BIER'+"\n"
                              + '(flags:type:label:id)/Flags'
                                ;
                    type ncd:string-all {
                      length 0..119 ;
                    }
                  }
                  ncd:select origin-ip ;
                }
              }
              container source-actives {
                description 'Source active auto dicovery route.'
                            ;
                list source-active {
                  description 'Source active auto dicovery route.'
                              ;
                  key 'ad-state rd source group'
                      ;
                  leaf ad-state {
                    description 'AD route state.
0:Remote
1:Local'
                                ;
                    type enumeration {
                      enum Remote {
                        value 0 ;
                      }
                      enum Local {
                        value 1 ;
                      }
                    }
                  }
                  leaf rd {
                    description RD. ;
                    type string {
                      length 0..23 ;
                    }
                  }
                  leaf source {
                    description 'Source address.'
                                ;
                    type ncd:ipv6-address ;
                  }
                  leaf group {
                    description 'Group address.'
                                ;
                    type ncd:ipv6-address ;
                  }
                  leaf nexthop {
                    description 'Nexthop address.'
                                ;
                    type ncd:ipv4-address ;
                  }
                  ncd:select source ;
                  ncd:select group ;
                  ncd:select 'source group'
                             ;
                }
              }
              container xg-joins {
                description 'XG join route.'
                            ;
                list xg-join {
                  description 'XG join route.'
                              ;
                  key 'ad-state rd source-as rp-addr group'
                      ;
                  leaf ad-state {
                    description 'AD route state.
0:Remote
1:Local'
                                ;
                    type enumeration {
                      enum Remote {
                        value 0 ;
                      }
                      enum Local {
                        value 1 ;
                      }
                    }
                  }
                  leaf rd {
                    description RD. ;
                    type string {
                      length 0..23 ;
                    }
                  }
                  leaf source-as {
                    description 'Source autonomous system number.'
                                ;
                    type uint32 ;
                  }
                  leaf rp-addr {
                    description 'RP address.'
                                ;
                    type ncd:ipv6-address ;
                  }
                  leaf group {
                    description 'Group address.'
                                ;
                    type ncd:ipv6-address ;
                  }
                  leaf nexthop {
                    description 'Nexthop address.'
                                ;
                    type ncd:ipv4-address ;
                  }
                  ncd:select rp-addr ;
                  ncd:select group ;
                  ncd:select 'rp-addr group'
                             ;
                }
              }
              container sg-joins {
                description 'SG join route.'
                            ;
                list sg-join {
                  description 'SG join route.'
                              ;
                  key 'ad-state rd source-as source group'
                      ;
                  leaf ad-state {
                    description 'AD route state.
0:Remote
1:Local'
                                ;
                    type enumeration {
                      enum Remote {
                        value 0 ;
                      }
                      enum Local {
                        value 1 ;
                      }
                    }
                  }
                  leaf rd {
                    description RD. ;
                    type string {
                      length 0..23 ;
                    }
                  }
                  leaf source-as {
                    description 'Source autonomous system number.'
                                ;
                    type uint32 ;
                  }
                  leaf source {
                    description 'Source address.'
                                ;
                    type ncd:ipv6-address ;
                  }
                  leaf group {
                    description 'Group address.'
                                ;
                    type ncd:ipv6-address ;
                  }
                  leaf nexthop {
                    description 'Nexthop address.'
                                ;
                    type ncd:ipv4-address ;
                  }
                  ncd:select source ;
                  ncd:select group ;
                  ncd:select 'source group'
                             ;
                }
              }
              ncd:select vrf-name ;
            }
            ncd:revise-date 2016-11-29 ;
          }
          container mtibs {
            description 'MVPN tunnel information.'
                        ;
            list mtib {
              description 'MVPN tunnel information.'
                          ;
              key 'vrf-name tunnel-id tunnel-type'
                  ;
              leaf vrf-name {
                description 'VPN Routing/Forwarding instance name.'
                            ;
                type string {
                  length 1..32 ;
                }
              }
              leaf tunnel-id {
                description 'Tunnel ID.'
                            ;
                type uint32 ;
              }
              leaf tunnel-type {
                description 'Tunnel type.'+"\n"
                          + '0:No-Tunnel'+"\n"
                          + '1:TE-P2MP'+"\n"
                          + '2:mLDP-P2MP'+"\n"
                          + '3:PIM-SSM'+"\n"
                          + '4:PIM-SM'+"\n"
                          + '5:PIM-BIDIR'+"\n"
                          + '6:INGRESS-RPL'+"\n"
                          + '7:mLDP-MP2MP'+"\n"
                          + '11:BIER'
                            ;
                type enumeration {
                  enum No-Tunnel {
                    value 0 ;
                  }
                  enum TE-P2MP {
                    value 1 ;
                  }
                  enum mLDP-P2MP {
                    value 2 ;
                  }
                  enum PIM-SSM {
                    value 3 ;
                  }
                  enum PIM-SM {
                    value 4 ;
                  }
                  enum PIM-BIDIR {
                    value 5 ;
                  }
                  enum INGRESS-RPL {
                    value 6 ;
                  }
                  enum mLDP-MP2MP {
                    value 7 ;
                  }
                  enum BIER {
                    value 11 ;
                  }
                }
              }
              leaf tunnel-state {
                description 'Tunnel state.
0:Root
1:Leaf'
                            ;
                type enumeration {
                  enum Root {
                    value 0 ;
                  }
                  enum Leaf {
                    value 1 ;
                  }
                }
              }
              leaf leaf-require {
                description 'Leaf require.
0:N
1:Y'
                            ;
                type enumeration {
                  enum N {
                    value 0 ;
                  }
                  enum Y {
                    value 1 ;
                  }
                }
              }
              leaf protocol-state {
                description 'Protocol state.
0:Up
1:Down
2:Join
3:Leave'
                            ;
                type enumeration {
                  enum Up {
                    value 0 ;
                  }
                  enum Down {
                    value 1 ;
                  }
                  enum Join {
                    value 2 ;
                  }
                  enum Leave {
                    value 3 ;
                  }
                }
              }
              leaf tunnel-label {
                description 'Tunnel label.'
                            ;
                type uint32 ;
              }
              leaf tunnel-attr {
                description 'Tunnel attribute.'
                            ;
                type ncd:string-all {
                  length 0..119 ;
                }
              }
              leaf leave-delay {
                description 'Leave delay.'
                            ;
                type string {
                  length 0..15 ;
                }
              }
              container multi-imports {
                description 'Multi-import VPN infomation.'
                            ;
                list multi-import {
                  description 'Multi-import VPN infomation.'
                              ;
                  key sub-vrf-name ;
                  leaf sub-vrf-name {
                    description 'Multi-import VPN Routing/Forwarding instance n'
                              + 'ame.'+"\n"
                              + 'If the instance is public, the value of the no'
                              + 'de is IP global, else is VRF name.'
                                ;
                    type ncd:string-all {
                      length 1..32 ;
                    }
                  }
                  leaf sub-tunnel-state {
                    description 'Tunnel state.'
                                ;
                    type ncd:string-all {
                      length 0..15 ;
                    }
                    ncd:revise-date 2016-11-29 ;
                  }
                  ncd:select sub-vrf-name ;
                }
              }
              ncd:select vrf-name ;
              ncd:select 'vrf-name tunnel-id tunnel-type'
                         ;
            }
          }
          container mribs {
            description 'MVPN route information.'
                        ;
            list mrib {
              description 'MVPN route information.'
                          ;
              key 'vrf-name source group'
                  ;
              leaf vrf-name {
                description 'VPN Routing/Forwarding instance name.'
                            ;
                type string {
                  length 1..32 ;
                }
              }
              leaf source {
                description 'Source address.'
                            ;
                type ncd:ipv6-address ;
              }
              leaf group {
                description 'Group address.'
                            ;
                type ncd:ipv6-address ;
              }
              leaf intf-state {
                description 'Interface state.'+"\n"
                          + 'IFT -- Receive from P-tunnel'+"\n"
                          + 'OFT -- Send to P-tunnel'+"\n"
                          + 'OFNL -- Downstream join state'
                            ;
                type string {
                  length 0..15 ;
                }
              }
              leaf upstream-tunnel {
                description 'Upstream tunnel.'
                            ;
                type ncd:string-all {
                  length 0..79 ;
                }
              }
              leaf upstream-pe {
                description 'Upstream PE address.'
                            ;
                type ncd:ipv4-address ;
              }
              leaf rpf-tunnel-id {
                description 'RPF tunnel ID.'
                            ;
                type uint32 ;
              }
              leaf rpf-vrf-name {
                description 'RPF VPN Routing/Forwarding instance name.'
                            ;
                type string {
                  length 0..32 ;
                }
              }
              leaf downstream-tunnel {
                description 'Downstream tunnel.'
                            ;
                type ncd:string-all {
                  length 0..79 ;
                }
              }
              leaf switch-tunnel {
                description 'Switch tunnel.'
                            ;
                type ncd:string-all {
                  length 0..79 ;
                }
              }
              leaf switch-time {
                description 'Switch time.'
                            ;
                type string {
                  length 0..15 ;
                }
              }
              container spmsi-ads {
                status obsolete {
                  ncd:revise-date 2016-11-29 ;
                }
                description 'Spmsi-AD auto dicovery route.'
                            ;
                list spmsi-ad {
                  description 'Spmsi-AD auto dicovery route.'
                              ;
                  key 'ad-state rd source group origin-ip'
                      ;
                  leaf ad-state {
                    description 'AD route state.
0:Remote
1:Local'
                                ;
                    type enumeration {
                      enum Remote {
                        value 0 ;
                      }
                      enum Local {
                        value 1 ;
                      }
                    }
                  }
                  leaf rd {
                    description RD. ;
                    type string {
                      length 0..23 ;
                    }
                  }
                  leaf source {
                    description 'Source address.'
                                ;
                    type ncd:ipv6-address ;
                  }
                  leaf group {
                    description 'Group address.'
                                ;
                    type ncd:ipv6-address ;
                  }
                  leaf origin-ip {
                    description 'Origin IP address.'
                                ;
                    type ncd:ipv4-address ;
                  }
                  leaf spmsi-tunnel {
                    description 'Spmsi tunnel.'
                                ;
                    type ncd:string-all {
                      length 0..79 ;
                    }
                  }
                  leaf uptime {
                    description Uptime. ;
                    type string {
                      length 0..15 ;
                    }
                  }
                  ncd:select origin-ip ;
                }
              }
              container leaf-ads {
                status obsolete {
                  ncd:revise-date 2016-11-29 ;
                }
                description 'Leaf-AD auto discovery route.'
                            ;
                list leaf-ad {
                  description 'Leaf-AD auto discovery route.'
                              ;
                  key 'ad-state type spmsi-rd spmsi-source spmsi-group spmsi-or'
                    + 'igin-ip origin-ip'
                      ;
                  leaf ad-state {
                    description 'AD route state.
0:Remote
1:Local'
                                ;
                    type enumeration {
                      enum Remote {
                        value 0 ;
                      }
                      enum Local {
                        value 1 ;
                      }
                    }
                  }
                  leaf type {
                    description 'AD route type.
2:Inter-AS
3:Spmsi-AD'
                                ;
                    type enumeration {
                      enum Inter-AS {
                        value 2 ;
                      }
                      enum Spmsi-AD {
                        value 3 ;
                      }
                    }
                  }
                  leaf spmsi-rd {
                    description 'Spmsi-AD RD.'
                                ;
                    type string {
                      length 0..23 ;
                    }
                  }
                  leaf spmsi-source {
                    description 'Spmsi-AD source address.'
                                ;
                    type ncd:ipv6-address ;
                  }
                  leaf spmsi-group {
                    description 'Spmsi-AD group address.'
                                ;
                    type ncd:ipv6-address ;
                  }
                  leaf spmsi-origin-ip {
                    description 'Spmsi-AD origin IP.'
                                ;
                    type ncd:ipv4-address ;
                  }
                  leaf origin-ip {
                    description 'Origin IP address.'
                                ;
                    type ncd:ipv4-address ;
                  }
                  leaf uptime {
                    description Uptime. ;
                    type string {
                      length 0..15 ;
                    }
                  }
                  ncd:select origin-ip ;
                }
              }
              container spmsi-auto-discoveries {
                description 'Spmsi-AD auto dicovery route.'
                            ;
                list spmsi-auto-discovery {
                  description 'Spmsi-AD auto dicovery route.'
                              ;
                  key 'rd source group origin-ip'
                      ;
                  leaf rd {
                    description RD. ;
                    type string {
                      length 0..23 ;
                    }
                  }
                  leaf source {
                    description 'Source address.'
                                ;
                    type ncd:ipv6-address ;
                  }
                  leaf group {
                    description 'Group address.'
                                ;
                    type ncd:ipv6-address ;
                  }
                  leaf origin-ip {
                    description 'Origin IP address.'
                                ;
                    type ncd:ipv4-address ;
                  }
                  leaf ad-state {
                    description 'AD route state.'+"\n"
                              + '0:Remote'+"\n"
                              + '1:Local'+"\n"
                              + '2:Local/Remote'
                                ;
                    type enumeration {
                      enum Remote {
                        value 0 ;
                      }
                      enum Local {
                        value 1 ;
                      }
                      enum Local/Remote {
                        value 2 ;
                      }
                    }
                  }
                  leaf root-tunnel {
                    description 'Root tunnel.'
                                ;
                    type ncd:string-all {
                      length 0..79 ;
                    }
                  }
                  leaf leaf-tunnel {
                    description 'Leaf tunnel.'
                                ;
                    type ncd:string-all {
                      length 0..79 ;
                    }
                  }
                  leaf ir-tunnel {
                    description 'Ingress replication tunnel.'
                                ;
                    type ncd:string-all {
                      length 0..79 ;
                    }
                  }
                  leaf uptime {
                    description Uptime. ;
                    type string {
                      length 0..15 ;
                    }
                  }
                  ncd:select origin-ip ;
                }
                ncd:revise-date 2016-11-29 ;
              }
              container leaf-auto-discoveries {
                description 'Leaf-AD auto discovery route.'
                            ;
                list leaf-auto-discovery {
                  description 'Leaf-AD auto discovery route.'
                              ;
                  key 'type sub-rd sub-source sub-group sub-origin-ip origin-ip'
                      ;
                  leaf type {
                    description 'AD route type.'+"\n"
                              + '1:Intra-AS'+"\n"
                              + '2:Inter-AS'+"\n"
                              + '3:Spmsi-AD'
                                ;
                    type enumeration {
                      enum Intra-AS {
                        value 1 ;
                      }
                      enum Inter-AS {
                        value 2 ;
                      }
                      enum Spmsi-AD {
                        value 3 ;
                      }
                    }
                  }
                  leaf sub-rd {
                    description 'Sub RD.'
                                ;
                    type string {
                      length 0..23 ;
                    }
                  }
                  leaf sub-source {
                    description 'Sub source address.'
                                ;
                    type ncd:ipv6-address ;
                  }
                  leaf sub-group {
                    description 'Sub group address.'
                                ;
                    type ncd:ipv6-address ;
                  }
                  leaf sub-origin-ip {
                    description 'Sub origin IP.'
                                ;
                    type ncd:ipv4-address ;
                  }
                  leaf origin-ip {
                    description 'Origin IP address.'
                                ;
                    type ncd:ipv4-address ;
                  }
                  leaf ad-state {
                    description 'AD route state.'+"\n"
                              + '0:Remote'+"\n"
                              + '1:Local'+"\n"
                              + '2:Local/Remote'
                                ;
                    type enumeration {
                      enum Remote {
                        value 0 ;
                      }
                      enum Local {
                        value 1 ;
                      }
                      enum Local/Remote {
                        value 2 ;
                      }
                    }
                  }
                  leaf uptime {
                    description Uptime. ;
                    type string {
                      length 0..15 ;
                    }
                  }
                  ncd:select origin-ip ;
                }
                ncd:revise-date 2016-11-29 ;
              }
              container source-actives {
                description 'Source active auto dicovery route.'
                            ;
                list source-active {
                  description 'Source active auto dicovery route.'
                              ;
                  key 'ad-state rd source group'
                      ;
                  leaf ad-state {
                    description 'AD route state.
0:Remote
1:Local'
                                ;
                    type enumeration {
                      enum Remote {
                        value 0 ;
                      }
                      enum Local {
                        value 1 ;
                      }
                    }
                  }
                  leaf rd {
                    description RD. ;
                    type string {
                      length 0..23 ;
                    }
                  }
                  leaf source {
                    description 'Source address.'
                                ;
                    type ncd:ipv6-address ;
                  }
                  leaf group {
                    description 'Group address.'
                                ;
                    type ncd:ipv6-address ;
                  }
                  leaf uptime {
                    description Uptime. ;
                    type string {
                      length 0..15 ;
                    }
                  }
                  ncd:select ad-state ;
                }
              }
              container xg-joins {
                description 'XG join route.'
                            ;
                list xg-join {
                  description 'XG join route.'
                              ;
                  key 'ad-state rd source-as rp-addr group'
                      ;
                  leaf ad-state {
                    description 'AD route state.
0:Remote
1:Local'
                                ;
                    type enumeration {
                      enum Remote {
                        value 0 ;
                      }
                      enum Local {
                        value 1 ;
                      }
                    }
                  }
                  leaf rd {
                    description RD. ;
                    type string {
                      length 0..23 ;
                    }
                  }
                  leaf source-as {
                    description 'Source autonomous system number.'
                                ;
                    type uint32 ;
                  }
                  leaf rp-addr {
                    description 'RP address.'
                                ;
                    type ncd:ipv6-address ;
                  }
                  leaf group {
                    description 'Group address.'
                                ;
                    type ncd:ipv6-address ;
                  }
                  leaf uptime {
                    description Uptime. ;
                    type string {
                      length 0..15 ;
                    }
                  }
                  ncd:select ad-state ;
                }
                ncd:revise-date 2015-08-12 ;
              }
              container sg-joins {
                description 'SG join route.'
                            ;
                list sg-join {
                  description 'SG join route.'
                              ;
                  key 'ad-state rd source-as source group'
                      ;
                  leaf ad-state {
                    description 'AD route state.
0:Remote
1:Local'
                                ;
                    type enumeration {
                      enum Remote {
                        value 0 ;
                      }
                      enum Local {
                        value 1 ;
                      }
                    }
                  }
                  leaf rd {
                    description RD. ;
                    type string {
                      length 0..23 ;
                    }
                  }
                  leaf source-as {
                    description 'Source autonomous system number.'
                                ;
                    type uint32 ;
                  }
                  leaf source {
                    description 'Source address.'
                                ;
                    type ncd:ipv6-address ;
                  }
                  leaf group {
                    description 'Group address.'
                                ;
                    type ncd:ipv6-address ;
                  }
                  leaf uptime {
                    description Uptime. ;
                    type string {
                      length 0..15 ;
                    }
                  }
                  ncd:select ad-state ;
                }
              }
              ncd:select vrf-name ;
              ncd:select source ;
              ncd:select group ;
              ncd:select 'vrf-name source'
                         ;
              ncd:select 'vrf-name group'
                         ;
              ncd:select 'source group'
                         ;
              ncd:select 'vrf-name source group'
                         ;
            }
          }
          container ad-summarys {
            description 'The summary information of AD route.'
                        ;
            list ad-summary {
              description 'The summary information of AD route.'
                          ;
              key vrf-name ;
              leaf vrf-name {
                description 'VPN Routing/Forwarding instance name.'
                            ;
                type string {
                  length 1..32 ;
                }
              }
              leaf intra-as-local {
                description 'Local intra-AS route summary.'
                            ;
                type uint32 ;
              }
              leaf intra-as-remote {
                description 'Remote intra-AS route summary.'
                            ;
                type uint32 ;
              }
              leaf intra-as-all {
                description 'Intra-AS route summary.'
                            ;
                type uint32 ;
              }
              leaf inter-as-local {
                description 'Local inter-AS route summary.'
                            ;
                type uint32 ;
              }
              leaf inter-as-remote {
                description 'Remote inter-AS route summary.'
                            ;
                type uint32 ;
              }
              leaf inter-as-all {
                description 'Inter-AS route summary.'
                            ;
                type uint32 ;
              }
              leaf spmsi-ad-local {
                description 'Local spmsi-AD route summary.'
                            ;
                type uint32 ;
              }
              leaf spmsi-ad-remote {
                description 'Remote spmsi-AD route summary.'
                            ;
                type uint32 ;
              }
              leaf spmsi-ad-all {
                description 'Spmsi-AD route summary.'
                            ;
                type uint32 ;
              }
              leaf leaf-ad-local {
                description 'Local leaf-AD route summary.'
                            ;
                type uint32 ;
              }
              leaf leaf-ad-remote {
                description 'Remote leaf-AD route summary.'
                            ;
                type uint32 ;
              }
              leaf leaf-ad-all {
                description 'Leaf-AD route summary.'
                            ;
                type uint32 ;
              }
              leaf source-active-local {
                description 'Local source active route summary.'
                            ;
                type uint32 ;
              }
              leaf source-active-remote {
                description 'Remote source active route summary.'
                            ;
                type uint32 ;
              }
              leaf source-active-all {
                description 'Source active route summary.'
                            ;
                type uint32 ;
              }
              leaf xg-join-local {
                description 'Local XG join route summary.'
                            ;
                type uint32 ;
              }
              leaf xg-join-remote {
                description 'Remote XG join route summary.'
                            ;
                type uint32 ;
              }
              leaf xg-join-all {
                description 'XG join route summary.'
                            ;
                type uint32 ;
              }
              leaf sg-join-local {
                description 'Local SG join route summary.'
                            ;
                type uint32 ;
              }
              leaf sg-join-remote {
                description 'Remote SG join route summary.'
                            ;
                type uint32 ;
              }
              leaf sg-join-all {
                description 'SG join route summary.'
                            ;
                type uint32 ;
              }
              leaf local-ad-all {
                description 'Local AD route summary.'
                            ;
                type uint32 ;
              }
              leaf remote-ad-all {
                description 'Remote AD route summary.'
                            ;
                type uint32 ;
              }
              leaf ad-all {
                description 'AD route summary.'
                            ;
                type uint32 ;
              }
              ncd:select vrf-name ;
            }
            ncd:revise-date 2016-11-29 ;
          }
        }
      }
    }
    ncd:revise-date 2015-03-31 ;
  }
  container operation {
    config false ;
    description 'Operation module.'
                ;
    container ipv6-multicast {
      description 'IPv6 multicast'
                  ;
      container public {
        description 'Public mode of IPv6 multicast.'
                    ;
        container clear {
          description 'Clear node'
                      ;
          container mroutes {
            description 'Multicast route.'
                        ;
            list source-group {
              description 'Clear mroute of the designed source and group addres'
                        + 's.'
                          ;
              key 'group source'
                  ;
              leaf group {
                description 'Group address'
                            ;
                type ncd:ipv6-address ;
              }
              leaf source {
                description 'Source address'
                            ;
                type ncd:ipv6-address ;
              }
            }
            list group {
              description 'Clear mroute of the designed group address.'
                          ;
              key group ;
              leaf group {
                description 'Group address'
                            ;
                type ncd:ipv6-address ;
              }
            }
            container mroute {
              description 'Clear multicast public route.'
                          ;
              leaf public {
                description Public ;
                type empty ;
              }
            }
          }
        }
      }
      container private {
        description 'Private mode of IPv6 multicast.'
                    ;
        container clear {
          description 'Clear node'
                      ;
          container mroutes {
            description 'Multicast route.'
                        ;
            list source-group {
              description 'Clear mroute of the designed vrf name,source and gro'
                        + 'up address.'
                          ;
              key 'vrf-name group source'
                  ;
              leaf vrf-name {
                description 'VRF name'
                            ;
                type string {
                  length 1..32 ;
                }
              }
              leaf group {
                description 'Group address'
                            ;
                type ncd:ipv6-address ;
              }
              leaf source {
                description 'Source address'
                            ;
                type ncd:ipv6-address ;
              }
            }
            list group {
              description 'Clear mroute of the designed vrf name and group addr'
                        + 'ess.'
                          ;
              key 'vrf-name group'
                  ;
              leaf vrf-name {
                description 'VRF name'
                            ;
                type string {
                  length 1..32 ;
                }
              }
              leaf group {
                description 'Group address'
                            ;
                type ncd:ipv6-address ;
              }
            }
            list mroute {
              description 'Clear mroute of the designed vrf name.'
                          ;
              key vrf-name ;
              leaf vrf-name {
                description 'VRF name'
                            ;
                type string {
                  length 1..32 ;
                }
              }
            }
          }
        }
      }
    }
    ncd:revise-date 2015-03-31 ;
  }
}
