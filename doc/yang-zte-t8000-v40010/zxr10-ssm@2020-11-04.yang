module zxr10-ssm {
  namespace 'http://www.zte.com.cn/zxr10/netconf/schema/rosng/ssm'
            ;
  prefix ssm ;
  yang-version 1 ;
  import zxr10-netconf-defs {
    prefix ncd ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe SSM clock.'
              ;
  revision 2020-11-04 {
    description 'Add ssm-mode enumeration types(itu-expssm) for ssm/configurati'
              + 'on/global/ssm-mode,'+"\n"
              + '    Add QL enumeration types (QL-ePRTC/QL-PRTC/QL-ePRC/QL-eSEC'
              + ') for all QL leafs.'+"\n"
              + 'Add ssm/state/ssm/current-clock/current-clock-id'+"\n"
              + 'Add ssm/state/ssm/current-clock/internal-clock-id'
                ;
  }
  revision 2020-01-09 {
    description 'Add /ssm:configuration/ssm:ssm/ssm:oam-node/ssm:pll-abnormal-a'
              + 'ssociate'
                ;
  }
  revision 2019-12-26 {
    description 'Add /ssm:configuration/ssm:ssm/ssm:ssm-transmit/ssm:transmit.'
                ;
  }
  revision 2019-01-07 {
    description 'Add /ssm:configuration/ssm:flexe-sync,'+"\n"
              + 'Add /ssm:state/ssm:flexe-sync.'
                ;
  }
  revision 2017-09-21 {
    description 'Add /ssm:configuration/ssm:ssm/ssm:frequency-check,'+"\n"
              + 'Add /ssm:configuration/ssm:ssm/ssm:global/ssm:holdover-time.'
                ;
  }
  revision 2016-02-02 {
    description 'Delete /ssm:configuration/ssm:ssm/ssm:sync-clocks/ssm:sync-clo'
              + 'ck/ssm:frame,'+"\n"
              + '/ssm:configuration/ssm:ssm/ssm:sync-clocks/ssm:sync-unif-clock'
              + '/ssm:frame;'+"\n"
              + 'Modify the enum of /ssm:configuration/ssm:ssm/ssm:sync-clocks/'
              + 'ssm:sync-clock/ssm:frame-mode;'+"\n"
              + '/ssm:configuration/ssm:ssm/ssm:sync-clocks/ssm:sync-unif-clock'
              + '/ssm:frame-mode.'
                ;
  }
  revision 2016-01-27 {
    description 'Add /ssm:configuration/ssm:ssm/ssm:sync-clocks/ssm:sync-clock/'
              + 'ssm:frame,'+"\n"
              + '/ssm:configuration/ssm:ssm/ssm:sync-clocks/ssm:sync-unif-clock'
              + '/ssm:frame;'+"\n"
              + 'Obsolete /ssm:configuration/ssm:ssm/ssm:sync-clocks/ssm:sync-c'
              + 'lock/ssm:frame-mode,'+"\n"
              + '/ssm:configuration/ssm:ssm/ssm:sync-clocks/ssm:sync-unif-clock'
              + '/ssm:frame-mode.'
                ;
  }
  revision 2015-11-11 {
    description 'Add:state/ssm/sync-clocks/sync-unif-clock(list)'+"\n"
              + '    state/ssm/sync-clocks/sync-clock(list)'
                ;
  }
  revision 2015-07-30 {
    description 'Modify the config flag of state and operation to FALSE.'
                ;
  }
  revision 2015-06-18 {
    description 'Modify the enum of /ssm:configuration/ssm:ssm/ssm:sync-clocks/'
              + 'ssm:sync-clock/ssm:frame-mode;'+"\n"
              + '/ssm:configuration/ssm:ssm/ssm:sync-clocks/ssm:sync-unif-clock'
              + '/ssm:frame-mode;'+"\n"
              + 'Modify the description of '+"\n"
              + '/ssm:configuration/ssm:ssm/ssm:extimer-clocks/ssm:out-clock/ss'
              + 'm:quality-limit;'+"\n"
              + '/ssm:state/ssm:ssm/ssm:current-clock/ssm:pll-state.'
                ;
  }
  revision 2014-12-04 {
    description 'Change the range of /ssm:configuration/ssm:ssm/ssm:extimer-clo'
              + 'cks/ssm:out-clock/ssm:out-clock-list/ssm:bind-if-name from 0~3'
              + '1 to 1~31'
                ;
  }
  revision 2014-05-19 {
    description 'Change the attribution id of'+"\n"
              + '/configuration/ssm/sa-position/sa-position-list/sa-receive-pos'
              + 'ition and'+"\n"
              + '/configuration/ssm/sa-position/sa-position-list/sa-transmit-po'
              + 'sition.'+"\n"
              + 'Modify the mimaction of'+"\n"
              + '/configuration/ssm/edge-link/edgelink.'+"\n"
              + 'Modify the description of'+"\n"
              + '/configuration/ssm/global/station-id;'+"\n"
              + '/configuration/ssm/global/sec-quality;'+"\n"
              + '/configuration/ssm/global/wtr-time;'+"\n"
              + '/configuration/ssm/global/lock-bits-send-dnu;'+"\n"
              + '/configuration/ssm/sync-clocks;'+"\n"
              + '/configuration/ssm/sync-clocks/sync-clock/if-name;'+"\n"
              + '/configuration/ssm/sync-clocks/sync-clock/priority;'+"\n"
              + '/configuration/ssm/sync-clocks/sync-clock/rcv-quality-mode;'+"\n"
              + '/configuration/ssm/sync-clocks/sync-clock/manual-rcv-quality;'+"\n"
              + '/configuration/ssm/sync-clocks/sync-unif-clock/priority;'+"\n"
              + '/configuration/ssm/sync-clocks/sync-unif-clock/rcv-quality-mod'
              + 'e;'+"\n"
              + '/configuration/ssm/sync-clocks/sync-unif-clock/manual-rcv-qual'
              + 'ity;'+"\n"
              + '/configuration/ssm/sync-clocks/sync-external-cmd/if-name;'+"\n"
              + '/configuration/ssm/sync-clocks/sync-external-cmd/lock-out;'+"\n"
              + '/configuration/ssm/sync-clocks/sync-external-cmd/switch-mode;'+"\n"
              + '/configuration/ssm/sync-clocks/sync-unif-external-cmd/lock-out'
              + ';'+"\n"
              + '/configuration/ssm/sync-clocks/sync-unif-external-cmd/switch-m'
              + 'ode;'+"\n"
              + '/configuration/ssm/extimer-clocks/out-clock/if-attribute;'+"\n"
              + '/configuration/ssm/extimer-clocks/out-clock-list/priority;'+"\n"
              + '/configuration/ssm/extimer-clocks/out-clock-unif-list/priority'
              + ';'+"\n"
              + '/configuration/ssm/sa-position/sa-position-list/sa-receive-pos'
              + 'ition;'+"\n"
              + '/configuration/ssm/sa-position/sa-position-list/sa-transmit-po'
              + 'sition;'+"\n"
              + '/configuration/ssm/ssm-transmit/transmit-disable;'+"\n"
              + '/configuration/ssm/ssm-transmit/transmit-disable/if-name;'+"\n"
              + '/configuration/ssm/ssm-transmit/trans-ssm;'+"\n"
              + '/configuration/ssm/ssm-transmit/trans-ssm/if-name;'+"\n"
              + '/configuration/ssm/ssm-transmit/trans-ssm/transmit-quality;'+"\n"
              + '/configuration/ssm/edge-link/edgelink/if-name;'
                ;
  }
  revision 2014-04-28 {
    description 'change'+"\n"
              + 'state/ssm/current-out-clock/current-out-clock-list/out-state'
                ;
  }
  revision 2014-03-04 {
    description 'change'+"\n"
              + 'configuration/ssm/extimer-clocks/out-mode'+"\n"
              + 'state/ssm/current-clock/usessm'
                ;
  }
  revision 2014-01-27 {
    description 'del:configuration/ssm/ssm-transmit/transmit-disable/transmit-o'
              + 'ption'+"\n"
              + '    configuration/ssm/edge-link/edgelink/edgelink-option'
                ;
  }
  revision 2014-01-15 {
    description 'change:'+"\n"
              + 'configuration/ssm/sync-clocks/sync-external-cmd/switch-mode(ma'
              + 'naul change to manual)'+"\n"
              + 'configuration/ssm/sync-clocks/sync-unif-external-cmd/switch-mo'
              + 'de(manaul change to manual)'
                ;
  }
  revision 2013-12-31 {
    description 'Add:configuration/ssm/global/lock-bits-send-dnu'+"\n"
              + '    configuration/ssm/extimer-clocks/if-attribute'+"\n"
              + '    configuration/ssm/extimer-clocks/out-clock-unif-list/clock'
              + '-type/current-clock'+"\n"
              + '    configuration/ssm/sa-position'+"\n"
              + '    configuration/ssm/edge-link/edgelink/clock-type/stm-clk'
                ;
  }
  revision 2013-10-31 {
    description 'Add:configuration/ssm/sync-clocks/sync-unif-clock(list)'+"\n"
              + '    configuration/ssm/sync-clocks/sync-unif-external-cmd(list)'
              + ''+"\n"
              + '    configuration/ssm/global/ssm-mode(default)'+"\n"
              + '    configuration/ssm/sync-clocks/sync-clock(list:select)'+"\n"
              + '    configuration/ssm/sync-clocks/sync-external-cmd(list:selec'
              + 't)'+"\n"
              + '    configuration/ssm/extimer-clocks/out-clock-list(list:selec'
              + 't)'+"\n"
              + '    configuration/ssm/ssm-transmit/transmit-disable(list:selec'
              + 't)'+"\n"
              + '    configuration/ssm/ssm-transmit/trans-ssm(list:select)'+"\n"
              + '    configuration/ssm/edge-link/edgelink(list:select)'+"\n"
              + 'change:'+"\n"
              + '    configuration/ssm/sync-clocks/sync-clock/clock-type(value)'
              + ''+"\n"
              + '    configuration/ssm/sync-clocks/sync-external-cmd/clock-type'
              + '(value)'+"\n"
              + '    configuration/ssm/sync-clocks/sync-clock/frame-mode(defaul'
              + 't)'+"\n"
              + '    configuration/ssm/out-clock/out-clock-list/if-name(name ch'
              + 'ange to bind-if-name)'
                ;
  }
  revision 2013-09-20 {
    description 'Add:configuration/ssm/extimer-clocks/sa-positon(Container)'+"\n"
              + '    operation/ssm/wtr-clear-action(Container)'+"\n"
              + '    configuration/ssm/sync-clocks/sync-clock/frane-mode(value)'
              + ''+"\n"
              + 'change:configuration/ssm/ssm-transmit/transmit-disable/transmi'
              + 't-option'+"\n"
              + '     configuration/ssm/edge-link/edgelink/edgelink-option'
                ;
  }
  revision 2013-07-22 {
    description 'Initial version.'
                ;
  }
  feature frequency-check {
    description 'The frequency check feature.'
                ;
  }
  container configuration {
    description 'The configuration of SSM.'
                ;
    container ssm {
      description 'The node of SSM.'
                  ;
      container global {
        description 'The node of SSM global configuration.'
                    ;
        leaf usessm {
          description 'The switch of SSM algorithm for clock selection,enable/d'
                    + 'isable.'
                      ;
          type enumeration {
            enum enable {
              value 1 ;
              description 'Enable the SSM algorithm.'
                          ;
            }
            enum disable {
              value 2 ;
              description 'Disable the SSM algorithm.'
                          ;
            }
          }
          default disable ;
        }
        leaf ssm-mode {
          description 'The synchronization clock selection algorithm,ssm/ex-ssm.'
                      ;
          type enumeration {
            enum ssm {
              value 1 ;
              description 'Standard SSM algorithm of ITU.'
                          ;
            }
            enum expssm {
              value 2 ;
              description 'Expand SSM algorithm of ZTE.'
                          ;
            }
            enum itu-expssm {
              value 3 ;
              description 'ITU Expand SSM algorithm.'
                          ;
            }
          }
          default ssm ;
        }
        leaf station {
          description 'The switch of NE station,yes/no.'
                      ;
          type enumeration {
            enum no {
              value 0 ;
              description 'Set NE station.'
                          ;
            }
            enum yes {
              value 1 ;
              description 'Cancel NE station.'
                          ;
            }
          }
          default no ;
        }
        leaf station-id {
          description 'ID of NE station,the range is 1-7.'
                      ;
          type uint8 {
            range 1..7 ;
          }
          default 7 ;
        }
        leaf id-protect {
          description 'The switch of ID protection,open/close.'
                      ;
          type enumeration {
            enum open {
              value 1 ;
              description 'Open the ID protection.'
                          ;
            }
            enum close {
              value 2 ;
              description 'Close the ID protection.'
                          ;
            }
          }
          default close ;
        }
        leaf quality-unknown {
          description 'The switch of QL unknown mode,open/close.'
                      ;
          type enumeration {
            enum open {
              value 1 ;
              description 'Open QL unknown.'
                          ;
            }
            enum close {
              value 2 ;
              description 'Close QL unknown.'
                          ;
            }
          }
          default close ;
        }
        leaf sec-quality {
          description 'The QL of inner clock.'
                      ;
          type enumeration {
            enum QL-UNK {
              value 0 ;
              description 'The QL is unknown.'
                          ;
            }
            enum QL-PRC {
              value 2 ;
              description 'The QL is PRC.'
                          ;
            }
            enum QL-SSU-A {
              value 4 ;
              description 'The QL is SSU-A.'
                          ;
            }
            enum QL-SSU-B {
              value 8 ;
              description 'The QL is SSU-B.'
                          ;
            }
            enum QL-SEC {
              value 11 ;
              description 'The QL is SEC.'
                          ;
            }
            enum QL-PRTC {
              value 5 ;
              description 'The QL is PRTC.'
                          ;
            }
            enum QL-ePRTC {
              value 1 ;
              description 'The QL is ePRTC.'
                          ;
            }
            enum QL-ePRC {
              value 7 ;
              description 'The QL is ePRC.'
                          ;
            }
            enum QL-eSEC {
              value 10 ;
              description 'The QL is eSEC.'
                          ;
            }
          }
          default QL-SEC ;
        }
        leaf wtr-time {
          description 'The wait time to restore.the range is 0-12 minutes.'
                      ;
          type uint8 {
            range 0..12 ;
          }
          units minute ;
          default 5 ;
        }
        leaf quality-limit {
          description 'The switch of local clock QL limit,enable/disable.'
                      ;
          type enumeration {
            enum enable {
              value 1 ;
              description 'Enable the QL limit.'
                          ;
            }
            enum disable {
              value 2 ;
              description 'Disable the QL limit.'
                          ;
            }
          }
          default disable ;
        }
        leaf lock-bits-send-dnu {
          description 'The switch of sending DNU when system locks bits clock,e'
                    + 'nable/disable.'
                      ;
          type enumeration {
            enum enable {
              value 1 ;
              description 'Enable switch.'
                          ;
            }
            enum disable {
              value 2 ;
              description 'Disable switch.'
                          ;
            }
          }
          default disable ;
        }
        leaf holdover-time {
          description 'Holdover time(h).'
                      ;
          type uint32 {
            range 0..10000 ;
          }
          units hour ;
          default 24 ;
          ncd:revise-date 2017-09-21 ;
        }
      }
      container sync-clocks {
        description 'The node of synchronization clock configuration.'
                    ;
        list sync-clock {
          description 'The synchronization clock list.'
                      ;
          key 'if-name clock-type'
              ;
          leaf if-name {
            description 'The interface name of clock,inner-clk or PTP1588-clk i'
                      + 's NULL.'
                        ;
            type string {
              length 0..31 ;
            }
          }
          leaf clock-type {
            description 'The clock type.'
                        ;
            type enumeration {
              enum external-clk {
                value 1 ;
                description 'External clock.'
                            ;
              }
              enum line-clk {
                value 2 ;
                description 'Line clock.'
                            ;
              }
              enum tributeline-clk {
                value 5 ;
                description 'Tribute line clock.'
                            ;
              }
              enum gps-clk {
                value 7 ;
                description 'GPS clock.'
                            ;
              }
              enum stm-clk {
                value 8 ;
                description 'Stm-n clock.'
                            ;
              }
            }
          }
          leaf priority {
            description 'The clock priority,the range is 1-255.'
                        ;
            type uint8 {
              range 1..255 {
                description 'The value of DIS is 255.'
                            ;
              }
            }
            default 255 ;
          }
          leaf rcv-quality-mode {
            description 'The mode of receive clock QL,auto/manual.'
                        ;
            type enumeration {
              enum auto {
                value 1 ;
                description 'Automatically receive SSM mode.'
                            ;
              }
              enum manual {
                value 2 ;
                description 'Manually receive SSM mode.'
                            ;
              }
            }
            default auto ;
          }
          leaf manual-rcv-quality {
            description 'The value of receive clock QL by manual.'
                        ;
            type enumeration {
              enum QL-UNK {
                value 0 ;
                description 'The QL is unknown.'
                            ;
              }
              enum QL-PRC {
                value 2 ;
                description 'The QL is PRC.'
                            ;
              }
              enum QL-SSU-A {
                value 4 ;
                description 'The QL is SSU-A.'
                            ;
              }
              enum QL-SSU-B {
                value 8 ;
                description 'The QL is SSU-B.'
                            ;
              }
              enum QL-SEC {
                value 11 ;
                description 'The QL is SEC.'
                            ;
              }
              enum QL-DNU {
                value 15 ;
                description 'The QL is DNU.'
                            ;
              }
              enum QL-PRTC {
                value 5 ;
                description 'The QL is PRTC.'
                            ;
              }
              enum QL-ePRTC {
                value 1 ;
                description 'The QL is ePRTC.'
                            ;
              }
              enum QL-ePRC {
                value 7 ;
                description 'The QL is ePRC.'
                            ;
              }
              enum QL-eSEC {
                value 10 ;
                description 'The QL is eSEC.'
                            ;
              }
            }
            default QL-DNU ;
          }
          leaf frame-mode {
            description 'The frame mode for bits interface,unframe/frame.'
                        ;
            type enumeration {
              enum frame {
                value 1 ;
                description 'Frame mode.'
                            ;
              }
              enum unframe {
                value 2 ;
                description 'Unframe mode.'
                            ;
              }
              enum invaild {
                value 254 ;
                description 'Property is invalid.'
                            ;
              }
            }
            default invaild ;
          }
        }
        list sync-unif-clock {
          description 'The synchronization clock list.'
                      ;
          key clock-type ;
          leaf clock-type {
            description 'The clock type.'
                        ;
            type enumeration {
              enum inner-clk {
                value 3 ;
                description 'Internal clock.'
                            ;
              }
              enum PTP1588-clk {
                value 6 ;
                description 'PTP clock.'
                            ;
              }
            }
          }
          leaf priority {
            description 'The clock priority,the range is 1-255.'
                        ;
            type uint8 {
              range 1..255 {
                description 'The value of DIS is 255.'
                            ;
              }
            }
            default 255 ;
          }
          leaf rcv-quality-mode {
            description 'The mode of receive clock QL,auto/manual.'
                        ;
            type enumeration {
              enum auto {
                value 1 ;
                description 'Automatically receive SSM mode'
                            ;
              }
              enum manual {
                value 2 ;
                description 'Manually receive SSM mode'
                            ;
              }
            }
            default manual ;
          }
          leaf manual-rcv-quality {
            description 'The value of receive clock QL by manual.'
                        ;
            type enumeration {
              enum QL-UNK {
                value 0 ;
                description 'The QL is unknown.'
                            ;
              }
              enum QL-PRC {
                value 2 ;
                description 'The QL is PRC.'
                            ;
              }
              enum QL-SSU-A {
                value 4 ;
                description 'The QL is SSU-A.'
                            ;
              }
              enum QL-SSU-B {
                value 8 ;
                description 'The QL is SSU-B.'
                            ;
              }
              enum QL-SEC {
                value 11 ;
                description 'The QL is SEC.'
                            ;
              }
              enum QL-DNU {
                value 15 ;
                description 'The QL is DNU.'
                            ;
              }
              enum QL-PRTC {
                value 5 ;
                description 'The QL is PRTC.'
                            ;
              }
              enum QL-ePRTC {
                value 1 ;
                description 'The QL is ePRTC.'
                            ;
              }
              enum QL-ePRC {
                value 7 ;
                description 'The QL is ePRC.'
                            ;
              }
              enum QL-eSEC {
                value 10 ;
                description 'The QL is eSEC.'
                            ;
              }
            }
            default QL-DNU ;
          }
          leaf frame-mode {
            description 'The frame mode for bits interface,unframe/frame.'
                        ;
            type enumeration {
              enum frame {
                value 1 ;
                description 'Frame mode.'
                            ;
              }
              enum unframe {
                value 2 ;
                description 'Unframe mode.'
                            ;
              }
              enum invaild {
                value 254 ;
                description 'Property is invalid.'
                            ;
              }
            }
            default invaild ;
          }
        }
        list sync-external-cmd {
          description 'The external commands for synchronization clock.'
                      ;
          key 'if-name clock-type'
              ;
          leaf if-name {
            description 'The interface name of clock,inner-clk or PTP1588-clk i'
                      + 's NULL.'
                        ;
            type string {
              length 0..31 ;
            }
          }
          leaf clock-type {
            description 'The clock type.'
                        ;
            type enumeration {
              enum external-clk {
                value 1 ;
                description 'External clock.'
                            ;
              }
              enum line-clk {
                value 2 ;
                description 'Line clock.'
                            ;
              }
              enum tributeline-clk {
                value 5 ;
                description 'Tribute line clock.'
                            ;
              }
              enum gps-clk {
                value 7 ;
                description 'GPS clock.'
                            ;
              }
              enum stm-clk {
                value 8 ;
                description 'Stm-n clock.'
                            ;
              }
            }
          }
          leaf lock-out {
            description 'The lockout state of synchronization clock,on/off.'
                        ;
            type enumeration {
              enum on {
                value 1 ;
                description 'Open lockout.'
                            ;
              }
              enum off {
                value 2 ;
                description 'Close lockout.'
                            ;
              }
            }
            default off ;
          }
          leaf switch-mode {
            description 'The switch mode of synchronization clock:normal/force/'
                      + 'manual,there is only one synchronization clock in forc'
                      + 'e/manual switch mode.'
                        ;
            type enumeration {
              enum normal {
                value 1 ;
                description 'Normal mode.'
                            ;
              }
              enum force {
                value 2 ;
                description 'Force mode.'
                            ;
              }
              enum manual {
                value 3 ;
                description 'Manual mode.'
                            ;
              }
            }
            default normal ;
          }
        }
        list sync-unif-external-cmd {
          description 'The external commands for synchronization clock.'
                      ;
          key clock-type ;
          leaf clock-type {
            description 'The clock type.'
                        ;
            type enumeration {
              enum inner-clk {
                value 3 ;
                description 'Internal clock.'
                            ;
              }
              enum PTP1588-clk {
                value 6 ;
                description 'PTP clock.'
                            ;
              }
            }
          }
          leaf lock-out {
            description 'The lockout state of synchronization clock,on/off.'
                        ;
            type enumeration {
              enum on {
                value 1 ;
                description 'Open lockout.'
                            ;
              }
              enum off {
                value 2 ;
                description 'Close lockout.'
                            ;
              }
            }
            default off ;
          }
          leaf switch-mode {
            description 'The switch mode of synchronization clock:normal/force/'
                      + 'manual,there is only one synchronization clock in forc'
                      + 'e/manual switch mode.'
                        ;
            type enumeration {
              enum normal {
                value 1 ;
                description 'Normal mode.'
                            ;
              }
              enum force {
                value 2 ;
                description 'Force mode.'
                            ;
              }
              enum manual {
                value 3 ;
                description 'Manual mode.'
                            ;
              }
            }
            default normal ;
          }
        }
      }
      container extimer-clocks {
        description 'The node of extimer clock configuration.'
                    ;
        list out-clock {
          description 'The configuration of out clock.'
                      ;
          key if-name ;
          leaf if-name {
            description 'The extimer clock interface name.'
                        ;
            type string {
              length 0..31 ;
            }
          }
          leaf if-attribute {
            description 'The port attribute.'
                        ;
            type enumeration {
              enum 2Mbits {
                value 1 ;
                description '2Mbits of port attribute.'
                            ;
              }
              enum 2Mhz {
                value 2 ;
                description '2Mhz of port attribute.'
                            ;
              }
            }
            default 2Mbits ;
          }
          leaf quality-limit {
            description 'The minimum limit quality of out clock port.'
                        ;
            type enumeration {
              enum QL-UNK {
                value 0 ;
                description 'The QL is unknown.'
                            ;
              }
              enum QL-PRC {
                value 2 ;
                description 'The QL is PRC.'
                            ;
              }
              enum QL-SSU-A {
                value 4 ;
                description 'The QL is SSU-A.'
                            ;
              }
              enum QL-SSU-B {
                value 8 ;
                description 'The QL is SSU-B.'
                            ;
              }
              enum QL-SEC {
                value 11 ;
                description 'The QL is SEC.'
                            ;
              }
              enum QL-PRTC {
                value 5 ;
                description 'The QL is PRTC.'
                            ;
              }
              enum QL-ePRTC {
                value 1 ;
                description 'The QL is ePRTC.'
                            ;
              }
              enum QL-ePRC {
                value 7 ;
                description 'The QL is ePRC.'
                            ;
              }
              enum QL-eSEC {
                value 10 ;
                description 'The QL is eSEC.'
                            ;
              }
            }
            default QL-SEC ;
          }
          leaf out-mode {
            description 'The selection algorithm of out clock port:priority/qua'
                      + 'lity.'
                        ;
            type enumeration {
              enum priority {
                value 1 ;
                description 'According to priority'
                            ;
              }
              enum quality {
                value 2 ;
                description 'According to quality-level'
                            ;
              }
            }
            default priority ;
          }
          list out-clock-list {
            description 'The out clock source configuration list.'
                        ;
            key 'bind-if-name clock-type'
                ;
            leaf bind-if-name {
              description 'The interface name of out clock source.'
                          ;
              type string {
                length 1..31 ;
              }
            }
            leaf clock-type {
              description 'The clock type of out clock source.'
                          ;
              type enumeration {
                enum external-clk {
                  value 1 ;
                  description 'External clock.'
                              ;
                }
                enum line-clk {
                  value 2 ;
                  description 'Line clock.'
                              ;
                }
                enum tributeline-clk {
                  value 5 ;
                  description 'Tribute line clock.'
                              ;
                }
                enum gps-clk {
                  value 7 ;
                  description 'GPS clock.'
                              ;
                }
                enum stm-clk {
                  value 8 ;
                  description 'Stm-n clock.'
                              ;
                }
              }
            }
            leaf priority {
              description 'The clock priority,the range is 1-255.'
                          ;
              type uint8 {
                range 1..255 ;
              }
              default 255 ;
            }
          }
          list out-clock-unif-list {
            description 'The out clock source configuration list.'
                        ;
            key clock-type ;
            leaf clock-type {
              description 'The clock type of out clock source.'
                          ;
              type enumeration {
                enum PTP1588-clk {
                  value 6 ;
                  description 'PTP clock.'
                              ;
                }
                enum current-clock {
                  value 19 ;
                  description 'Current system clock.'
                              ;
                }
              }
            }
            leaf priority {
              description 'The clock priority,the range is 1-255.'
                          ;
              type uint8 {
                range 1..255 ;
              }
              default 255 ;
            }
          }
        }
      }
      container sa-position {
        description sa-position. ;
        list sa-position-list {
          description 'The configuration of sa position.'
                      ;
          key if-name ;
          leaf if-name {
            description 'The extimer clock interface name.'
                        ;
            type string {
              length 0..31 ;
            }
          }
          leaf sa-receive-position {
            description 'The sa position of receiving SSM,the range is 4-8.'
                        ;
            type uint8 {
              range 4..8 ;
            }
            default 4 ;
          }
          leaf sa-transmit-position {
            description 'The sa position of transmitting SSM,the range is 4-8.'
                        ;
            type uint8 {
              range 4..8 ;
            }
            default 4 ;
          }
        }
      }
      container ssm-transmit {
        description 'The node of clock transmit configuration.'
                    ;
        list transmit-disable {
          description 'The ethernet port list that is disabled to transmit SSM.'
                      ;
          key 'if-name clock-type'
              ;
          leaf if-name {
            description 'The interface name of clock.'
                        ;
            type string {
              length 0..31 ;
            }
          }
          leaf clock-type {
            description 'The clock type.'
                        ;
            type enumeration {
              enum line-clk {
                value 2 ;
                description 'Line clock.'
                            ;
              }
            }
          }
        }
        list trans-ssm {
          description 'The list of setting transmit clock QL.'
                      ;
          key 'if-name clock-type'
              ;
          leaf if-name {
            description 'The interface name of clock.'
                        ;
            type string {
              length 0..31 ;
            }
          }
          leaf clock-type {
            description 'The clock type.'
                        ;
            type enumeration {
              enum external-clk {
                value 1 ;
                description 'External clock.'
                            ;
              }
              enum line-clk {
                value 2 ;
                description 'Line clock.'
                            ;
              }
              enum stm-clk {
                value 8 ;
                description 'Stm-n clock.'
                            ;
              }
            }
          }
          leaf transmit-quality {
            description 'The value of transmitting clock QL by manual.'
                        ;
            type enumeration {
              enum QL-UNK {
                value 0 ;
                description 'The QL is unknown.'
                            ;
              }
              enum QL-PRC {
                value 2 ;
                description 'The QL is PRC.'
                            ;
              }
              enum QL-SSU-A {
                value 4 ;
                description 'The QL is SSU-A.'
                            ;
              }
              enum QL-SSU-B {
                value 8 ;
                description 'The QL is SSU-B.'
                            ;
              }
              enum QL-SEC {
                value 11 ;
                description 'The QL is SEC.'
                            ;
              }
              enum QL-DNU {
                value 15 ;
                description 'The QL is DNU.'
                            ;
              }
              enum QL-PRTC {
                value 5 ;
                description 'The QL is PRTC.'
                            ;
              }
              enum QL-ePRTC {
                value 1 ;
                description 'The QL is ePRTC.'
                            ;
              }
              enum QL-ePRC {
                value 7 ;
                description 'The QL is ePRC.'
                            ;
              }
              enum QL-eSEC {
                value 10 ;
                description 'The QL is eSEC.'
                            ;
              }
            }
            default QL-DNU ;
          }
        }
        list transmit {
          description 'Config ethernet port enable or disable to transmit SSM.'
                      ;
          key 'if-name clock-type'
              ;
          leaf if-name {
            description 'The interface name of clock.'
                        ;
            type string {
              length 0..31 ;
            }
          }
          leaf clock-type {
            description 'The clock type.'
                        ;
            type enumeration {
              enum line-clk {
                value 2 ;
                description 'Line clock.'
                            ;
              }
            }
          }
          leaf switch {
            description 'Enable or disable the ethernet port to transmit SSM,1 '
                      + 'means enable,2 means disable.'
                        ;
            type uint8 {
              range 1..2 {
                description '1:enable transmit,2:disable transmit'
                            ;
              }
            }
          }
          ncd:revise-date 2019-12-26 ;
        }
      }
      container edge-link {
        description 'The edge compatibility of clock port.'
                    ;
        list edgelink {
          description 'The edge link clock list.'
                      ;
          key 'if-name clock-type'
              ;
          leaf if-name {
            description 'The interface name of clock.'
                        ;
            type string {
              length 0..31 ;
            }
          }
          leaf clock-type {
            description 'The clock type.'
                        ;
            type enumeration {
              enum line-clk {
                value 2 ;
                description 'Line clock.'
                            ;
              }
              enum stm-clk {
                value 8 ;
                description 'Stm-n clock.'
                            ;
              }
            }
          }
        }
      }
      container frequency-check {
        if-feature frequency-check ;
        description 'The node of frequency check.'
                    ;
        choice frequency-check {
          description 'The choice of frequency check.'
                      ;
          default off ;
          case manual {
            description 'The case of frequency check,mode is manual.'
                        ;
            container manual {
              description 'The frequency check mode is manual.'
                          ;
              presence true ;
              leaf clock-type {
                description 'The clock type.'
                            ;
                type enumeration {
                  enum external {
                    value 1 ;
                  }
                  enum line {
                    value 2 ;
                  }
                  enum tribute-line {
                    value 5 ;
                  }
                  enum stm {
                    value 8 ;
                  }
                }
                mandatory true ;
              }
              leaf ifname {
                description 'The interface name of clock.'
                            ;
                type string {
                  length 1..31 ;
                }
                mandatory true ;
              }
            }
          }
          case auto {
            description 'The case of frequency check,mode is auto.'
                        ;
            container auto {
              description 'The frequency check mode is auto.'
                          ;
              presence true ;
              leaf auto {
                description 'The frequency check mode is auto.'
                            ;
                type enumeration {
                  enum auto {
                    value 1 ;
                  }
                }
                mandatory true ;
              }
            }
          }
          case off {
            description 'The frequency check is off.'
                        ;
            container off {
              description 'The frequency check is off.'
                          ;
              presence true ;
              leaf off {
                description 'The frequency check is off.'
                            ;
                type enumeration {
                  enum off {
                    value 0 ;
                  }
                }
                mandatory true ;
              }
            }
          }
        }
        ncd:revise-date 2017-09-21 ;
      }
      container oam-node {
        description 'The node of SSM oam configuration.'
                    ;
        leaf pll-abnormal-associate {
          description 'The switch of PLL abnormal associate.'
                      ;
          type enumeration {
            enum on {
              value 1 ;
              description 'Turn on.'
                          ;
            }
            enum off {
              value 2 ;
              description 'Turn off.'
                          ;
            }
          }
          default on ;
        }
        ncd:revise-date 2020-01-09 ;
      }
    }
    container flexe-sync {
      description 'The node of flexegroup synchronization configuration.'
                  ;
      container sync-channels {
        description 'The node of synchronization channel configuration.'
                    ;
        list sync-channel {
          description 'The synchronization channel list.'
                      ;
          key ifname ;
          leaf ifname {
            description 'The interface name of flexegroup.'
                        ;
            type ncd:ifname ;
          }
          leaf revertive-mode {
            description 'The revertive mode of sync channel,revertive/non-rever'
                      + 'tive.'
                        ;
            type enumeration {
              enum revertive {
                value 0 ;
              }
              enum non-revertive {
                value 1 ;
              }
            }
            default revertive ;
          }
          leaf wtr-time {
            description 'The wait time to restore.the range is 0-12 minutes.'
                        ;
            type uint8 {
              range 0..12 ;
            }
            units minute ;
            default 5 ;
          }
          choice switch-mode {
            description 'The switch mode of sync channel,auto/manual.'
                        ;
            default auto ;
            case auto {
              description 'The case of switch mode,mode is auto.'
                          ;
              container auto {
                description 'The switch mode is auto.'
                            ;
                leaf auto {
                  description 'The switch mode is auto.'
                              ;
                  type enumeration {
                    enum auto {
                      value 0 ;
                    }
                  }
                }
              }
            }
            case manual {
              description 'The case of switch mode,mode is manual.'
                          ;
              container manual {
                description 'The switch mode is manual.'
                            ;
                leaf phy-if {
                  description 'The interface name of manual mode.'
                              ;
                  type ncd:ifname ;
                }
              }
            }
          }
        }
      }
      ncd:revise-date 2019-01-07 ;
    }
  }
  container state {
    config false ;
    description 'The state of SSM.'
                ;
    container ssm {
      description 'The node of SSM.'
                  ;
      container current-clock {
        description 'SSM current system clock information.'
                    ;
        leaf if-name {
          description 'SSM current interface name of clock,inner-clk,hold-off o'
                    + 'r PTP1588-clk is NULL.'
                      ;
          type string {
            length 0..31 ;
          }
        }
        leaf clock-type {
          description 'SSM current clock type.'
                      ;
          type enumeration {
            enum external-clk {
              value 1 ;
              description 'External clock.'
                          ;
            }
            enum line-clk {
              value 2 ;
              description 'Line clock.'
                          ;
            }
            enum inner-clk {
              value 3 ;
              description 'Internal clock.'
                          ;
            }
            enum holdover {
              value 4 ;
              description 'Hold over.'
                          ;
            }
            enum tributeline-clk {
              value 5 ;
              description 'Tribute line clock.'
                          ;
            }
            enum PTP1588-clk {
              value 6 ;
              description 'PTP clock.'
                          ;
            }
            enum gps-clk {
              value 7 ;
              description 'GPS clock.'
                          ;
            }
            enum stm-clk {
              value 8 ;
              description 'Stm-n clock.'
                          ;
            }
          }
        }
        leaf pll-state {
          description 'SSM current clock PLL status.'
                      ;
          type enumeration {
            enum autorun {
              value 0 ;
              description 'PLL status is auto-run.'
                          ;
            }
            enum capture {
              value 1 ;
              description 'PLL status is captured.'
                          ;
            }
            enum track {
              value 2 ;
              description 'PLL status is track.'
                          ;
            }
            enum lock {
              value 3 ;
              description 'PLL status is locked.'
                          ;
            }
            enum unlock {
              value 4 ;
              description 'PLL status is unlocked.'
                          ;
            }
            enum NULL {
              value 254 ;
              description 'PLL status is invalid.'
                          ;
            }
          }
        }
        leaf usessm {
          description 'SSM current clock SSM enable state.'
                      ;
          type enumeration {
            enum enable {
              value 1 ;
              description 'Enable the SSM algorithm.'
                          ;
            }
            enum disable {
              value 2 ;
              description 'Disable the SSM algorithm.'
                          ;
            }
          }
        }
        leaf switch-option {
          description 'SSM current switch status.'
                      ;
          type enumeration {
            enum normal {
              value 1 ;
              description 'Normal mode.'
                          ;
            }
            enum force {
              value 2 ;
              description 'Force mode.'
                          ;
            }
            enum manual {
              value 3 ;
              description 'Manual mode.'
                          ;
            }
          }
        }
        leaf current-quality {
          description 'SSM current clock QL.'
                      ;
          type enumeration {
            enum QL-UNK {
              value 0 ;
              description 'The QL is unknown.'
                          ;
            }
            enum QL-PRC {
              value 2 ;
              description 'The QL is PRC.'
                          ;
            }
            enum QL-SSU-A {
              value 4 ;
              description 'The QL is SSU-A.'
                          ;
            }
            enum QL-SSU-B {
              value 8 ;
              description 'The QL is SSU-B.'
                          ;
            }
            enum QL-SEC {
              value 11 ;
              description 'The QL is SEC.'
                          ;
            }
            enum QL-DNU {
              value 15 ;
              description 'The QL is DNU.'
                          ;
            }
            enum QL-PRTC {
              value 5 ;
              description 'The QL is PRTC.'
                          ;
            }
            enum QL-ePRTC {
              value 1 ;
              description 'The QL is ePRTC.'
                          ;
            }
            enum QL-ePRC {
              value 7 ;
              description 'The QL is ePRC.'
                          ;
            }
            enum QL-eSEC {
              value 10 ;
              description 'The QL is eSEC.'
                          ;
            }
            enum invalid {
              value 254 ;
            }
          }
        }
        leaf current-clock-id {
          description 'SSM current clock ID.'
                      ;
          type string {
            length 0..24 ;
          }
          ncd:revise-date 2020-11-04 ;
        }
        leaf internal-clock-id {
          description 'SSM internal clock ID.'
                      ;
          type string {
            length 0..24 ;
          }
          ncd:revise-date 2020-11-04 ;
        }
      }
      container current-out-clock {
        description 'SSM current out clock information.'
                    ;
        list current-out-clock-list {
          description 'The list of current ssm out clock information.'
                      ;
          key if-name ;
          leaf if-name {
            description 'The interface name of out clock.'
                        ;
            type string {
              length 0..31 ;
            }
          }
          leaf out-state {
            description 'The state of the current out clock.'
                        ;
            type enumeration {
              enum enable {
                value 1 ;
                description 'The state of the current out clock is enabled.'
                            ;
              }
              enum disable {
                value 2 ;
                description 'The state of the current out clock is disabled.'
                            ;
              }
              enum unsupported {
                value 3 ;
                description 'The state of the current out clock is unsupported.'
                            ;
              }
            }
          }
          leaf out-mode {
            description 'The mode of the current out clock.'
                        ;
            type enumeration {
              enum priority {
                value 1 ;
                description 'According to priority'
                            ;
              }
              enum quality {
                value 2 ;
                description 'According to quality-level'
                            ;
              }
            }
          }
          leaf sub-if-name {
            description 'The interface name of output clock source.'
                        ;
            type string {
              length 0..31 ;
            }
          }
          leaf sub-clock-type {
            description 'The clock type of output clock source.'
                        ;
            type enumeration {
              enum external-clk {
                value 1 ;
                description 'External clock.'
                            ;
              }
              enum line-clk {
                value 2 ;
                description 'Line clock.'
                            ;
              }
              enum inner-clk {
                value 3 ;
                description 'Internal clock.'
                            ;
              }
              enum tributline-clk {
                value 5 ;
                description 'Tribute line clock.'
                            ;
              }
              enum PTP1588-clk {
                value 6 ;
                description 'PTP clock.'
                            ;
              }
              enum gps-clk {
                value 7 ;
                description 'GPS clock.'
                            ;
              }
              enum stm-clk {
                value 8 ;
                description 'Stm-n clock.'
                            ;
              }
              enum current-clock {
                value 19 ;
                description 'Current system clock.'
                            ;
              }
            }
          }
          leaf out-quality {
            description 'The current out clock QL.'
                        ;
            type enumeration {
              enum QL-UNK {
                value 0 ;
                description 'The QL is unknown.'
                            ;
              }
              enum QL-PRC {
                value 2 ;
                description 'The QL is PRC.'
                            ;
              }
              enum QL-SSU-A {
                value 4 ;
                description 'The QL is SSU-A.'
                            ;
              }
              enum QL-SSU-B {
                value 8 ;
                description 'The QL is SSU-B.'
                            ;
              }
              enum QL-SEC {
                value 11 ;
                description 'The QL is SEC.'
                            ;
              }
              enum QL-DNU {
                value 15 ;
                description 'The QL is DNU.'
                            ;
              }
              enum QL-PRTC {
                value 5 ;
                description 'The QL is PRTC.'
                            ;
              }
              enum QL-ePRTC {
                value 1 ;
                description 'The QL is ePRTC.'
                            ;
              }
              enum QL-ePRC {
                value 7 ;
                description 'The QL is ePRC.'
                            ;
              }
              enum QL-eSEC {
                value 10 ;
                description 'The QL is eSEC.'
                            ;
              }
              enum invalid {
                value 254 ;
              }
            }
          }
        }
      }
      container sync-clocks {
        description 'The node of synchronization clock.'
                    ;
        list sync-unif-clock {
          description 'The synchronization clock list.'
                      ;
          key clock-type ;
          leaf clock-type {
            description 'The clock type.'
                        ;
            type enumeration {
              enum inner-clk {
                value 3 ;
                description 'Internal clock.'
                            ;
              }
              enum PTP1588-clk {
                value 6 ;
                description 'PTP clock.'
                            ;
              }
            }
          }
          leaf rcv-quality {
            description 'The value of received clock QL.'
                        ;
            type enumeration {
              enum QL-UNK {
                value 0 ;
                description 'The QL is unknown.'
                            ;
              }
              enum QL-PRC {
                value 2 ;
                description 'The QL is PRC.'
                            ;
              }
              enum QL-SSU-A {
                value 4 ;
                description 'The QL is SSU-A.'
                            ;
              }
              enum QL-SSU-B {
                value 8 ;
                description 'The QL is SSU-B.'
                            ;
              }
              enum QL-SEC {
                value 11 ;
                description 'The QL is SEC.'
                            ;
              }
              enum QL-DNU {
                value 15 ;
                description 'The QL is DNU.'
                            ;
              }
              enum QL-PRTC {
                value 5 ;
                description 'The QL is PRTC.'
                            ;
              }
              enum QL-ePRTC {
                value 1 ;
                description 'The QL is ePRTC.'
                            ;
              }
              enum QL-ePRC {
                value 7 ;
                description 'The QL is ePRC.'
                            ;
              }
              enum QL-eSEC {
                value 10 ;
                description 'The QL is eSEC.'
                            ;
              }
            }
          }
        }
        list sync-clock {
          description 'The synchronization clock list.'
                      ;
          key 'if-name clock-type'
              ;
          leaf if-name {
            description 'The interface name of clock.'
                        ;
            type string {
              length 1..31 ;
            }
          }
          leaf clock-type {
            description 'The clock type.'
                        ;
            type enumeration {
              enum external-clk {
                value 1 ;
                description 'External clock.'
                            ;
              }
              enum line-clk {
                value 2 ;
                description 'Line clock.'
                            ;
              }
              enum tributeline-clk {
                value 5 ;
                description 'Tribute line clock.'
                            ;
              }
              enum gps-clk {
                value 7 ;
                description 'GPS clock.'
                            ;
              }
              enum stm-clk {
                value 8 ;
                description 'Stm-n clock.'
                            ;
              }
            }
          }
          leaf rcv-quality {
            description 'The value of received clock QL.'
                        ;
            type enumeration {
              enum QL-UNK {
                value 0 ;
                description 'The QL is unknown.'
                            ;
              }
              enum QL-PRC {
                value 2 ;
                description 'The QL is PRC.'
                            ;
              }
              enum QL-SSU-A {
                value 4 ;
                description 'The QL is SSU-A.'
                            ;
              }
              enum QL-SSU-B {
                value 8 ;
                description 'The QL is SSU-B.'
                            ;
              }
              enum QL-SEC {
                value 11 ;
                description 'The QL is SEC.'
                            ;
              }
              enum QL-DNU {
                value 15 ;
                description 'The QL is DNU.'
                            ;
              }
              enum QL-PRTC {
                value 5 ;
                description 'The QL is PRTC.'
                            ;
              }
              enum QL-ePRTC {
                value 1 ;
                description 'The QL is ePRTC.'
                            ;
              }
              enum QL-ePRC {
                value 7 ;
                description 'The QL is ePRC.'
                            ;
              }
              enum QL-eSEC {
                value 10 ;
                description 'The QL is eSEC.'
                            ;
              }
            }
          }
        }
      }
    }
    container flexe-sync {
      description 'The node of flexegroup synchronization state.'
                  ;
      container sync-channels {
        description 'The node of synchronization channel state.'
                    ;
        list sync-channel {
          description 'The synchronization channel list.'
                      ;
          key ifname ;
          leaf ifname {
            description 'The interface name of flexegroup.'
                        ;
            type ncd:ifname ;
          }
          leaf phy-if {
            description 'The switch interface.'
                        ;
            type string ;
          }
        }
      }
      ncd:revise-date 2019-01-07 ;
    }
  }
  container operation {
    config false ;
    description 'The operation of SSM.'
                ;
    container ssm {
      description 'The node of SSM.'
                  ;
      container wtr-clear-action {
        description 'Clear wait to restore action.'
                    ;
        choice wtr-clear {
          description 'To clear wait to restore state.'
                      ;
          case clear-oneclock {
            description 'To clear one clock wait to restore state.'
                        ;
            leaf if-name {
              description 'The interface name of clock,inner-clk or PTP1588-clk'
                        + ' is NULL.'
                          ;
              type string {
                length 0..31 ;
              }
            }
            leaf clock-type {
              description 'The clock type.'
                          ;
              type enumeration {
                enum external-clk {
                  value 1 ;
                  description 'External clock.'
                              ;
                }
                enum line-clk {
                  value 2 ;
                  description 'Line clock.'
                              ;
                }
                enum inner-clk {
                  value 3 ;
                  description 'Internal clock.'
                              ;
                }
                enum tributeline-clk {
                  value 5 ;
                  description 'Tribute line clock.'
                              ;
                }
                enum PTP1588-clk {
                  value 6 ;
                  description 'PTP clock.'
                              ;
                }
                enum gps-clk {
                  value 7 ;
                  description 'GPS clock.'
                              ;
                }
                enum stm-clk {
                  value 8 ;
                  description 'Stm-n clock.'
                              ;
                }
              }
            }
          }
          case clear-allclock {
            description 'To clear all clock wait to restore state.'
                        ;
            leaf allclock {
              description 'The flag of all clock ports.'
                          ;
              type uint8 {
                range 1 ;
              }
            }
          }
        }
      }
    }
  }
}
