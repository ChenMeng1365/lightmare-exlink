module zxr10-isis {
  namespace 'http://www.zte.com.cn/zxr10/netconf/schema/rosng/isis'
            ;
  prefix isis ;
  yang-version 1 ;
  import zxr10-netconf-defs {
    prefix ncd ;
    revision-date 2013-11-22 ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  description 'The netconf module to describe ISIS.This module describes a mana'
            + 'gement information base for the IS-IS Routing protocol, as descr'
            + 'ibed in ISO 10589.'
              ;
  revision 2021-04-21 {
    description '1.Path:/configuration/route-isis/isis-instances/isis-isis/isis'
              + '-instances/isis-instance/ipv4-summary-policys. Add this contai'
              + 'ner.'+"\n"
              + '2.Path:/configuration/route-isis/isis-instances/isis-isis/isis'
              + '-instances/isis-instance/ipv6-summary-policys. Add this contai'
              + 'ner.'
                ;
  }
  revision 2021-03-30 {
    description '1.Path:/configuration/route-isis/isis-instances/isis-attr/ipv4'
              + '-distances/distance-with-rmp. Add this list.'+"\n"
              + '2.Path:/configuration/route-isis/isis-instances/isis-attr/ipv6'
              + '-distances/distance-with-rmp. Add this list.'+"\n"
              + '3.Path:/isis:configuration/isis:route-isis/isis:isis-instances'
              + '/isis:isis-instance/isis:srv6-locators. Add this container.'
                ;
  }
  revision 2021-03-16 {
    description '1.Modify sr-feature. Add 61V5_1 project label.'
                ;
  }
  revision 2021-03-03 {
    description '1.Path:/configuration/route-isis/isis-instances/isis-isis/isis'
              + '-instances/isis-instance/isis-attr/crypto-authen-keychain-hmac'
              + '-md5.Add this leaf.'
                ;
  }
  revision 2021-03-02 {
    description '1.Path:/configuration/route-isis/isis-instances/isis-isis/isis'
              + '-instances/isis-instance/isis-intfs/isis-intf-attr/bfd-mode. A'
              + 'dd this leaf.'
                ;
  }
  revision 2021-02-25 {
    description '1.Path:/configuration/route-isis/isis-instances/isis-instance/'
              + 'spf-intervals/spf-interval/interval. The default value is chan'
              + 'ged , and customized by the performance parameter.'+"\n"
              + '2.Path:/configuration/route-isis/isis-instances/isis-instance/'
              + 'spf-intervals/spf-interval/init-delay. The default value is ch'
              + 'anged , and customized by the performance parameter.'+"\n"
              + '3.Path:/configuration/route-isis/isis-instances/isis-instance/'
              + 'spf-intervals/spf-interval/wait-first-second. The default valu'
              + 'e is changed , and customized by the performance parameter.'+"\n"
              + '4.Path:/configuration/route-isis/isis-instances/isis-instance/'
              + 'lsp-gen-intervals/lsp-gen-interval/init-delay. The default val'
              + 'ue is changed , and customized by the performance parameter.'+"\n"
              + '5.Path:/configuration/route-isis/isis-instances/isis-instance/'
              + 'lsp-gen-intervals/lsp-gen-interval/max-delay. The default valu'
              + 'e is changed , and customized by the performance parameter.'+"\n"
              + '6.Path:/configuration/route-isis/isis-instances/isis-instance/'
              + 'lsp-gen-intervals/lsp-gen-interval/wait-first-second. The defa'
              + 'ult value is changed , and customized by the performance param'
              + 'eter.'+"\n"
              + '7.Path:/configuration/route-isis/isis-instances/isis-instance/'
              + 'ipv6-spf-intervals/ipv6-spf-interval/interval. The default val'
              + 'ue is changed , and customized by the  performance parameter.'+"\n"
              + '8.Path:/configuration/route-isis/isis-instances/isis-instance/'
              + 'ipv6-spf-intervals/ipv6-spf-interval/init-delay. The default v'
              + 'alue is changed , and customized by the  performance parameter'
              + '.'+"\n"
              + '9.Path:/configuration/route-isis/isis-instances/isis-instance/'
              + 'ipv6-spf-intervals/ipv6-spf-interval/wait-first-second. The de'
              + 'fault value is changed , and customized by the  performance pa'
              + 'rameter.'
                ;
  }
  revision 2021-02-24 {
    description '1.Path:/configuration/route-isis/isis-instances/isis-instance/'
              + 'isis-attr/auto-metric-ref-bandwidth. Modify the max value of t'
              + 'his leaf node.'+"\n"
              + '2.Path:/configuration/route-isis/isis-instances/isis-instance/'
              + 'isis-attr/ipv6-auto-metric-ref-bw. Modify the max value of thi'
              + 's leaf node.'
                ;
  }
  revision 2021-02-23 {
    description '1.Path:/isis:configuration/isis:route-isis/isis:isis-instances'
              + '/isis:isis-instance/isis:ipv4-frr-state/multi-home. Add this l'
              + 'eaf.'+"\n"
              + '2.Path:/isis:configuration/isis:route-isis/isis:isis-instances'
              + '/isis:isis-instance/isis:ipv6-frr-state/multi-home. Add this l'
              + 'eaf.'+"\n"
              + '3.Path:/isis:configuration/isis:route-isis/isis:isis-instances'
              + '/isis:isis-instance/isis:ipv4-frr-state/state. The leaf state '
              + 'was reset mandatory.'+"\n"
              + '4.Path:/isis:configuration/isis:route-isis/isis:isis-instances'
              + '/isis:isis-instance/isis:ipv6-frr-state/state. The leaf state '
              + 'was reset mandatory.'
                ;
  }
  revision 2021-02-05 {
    description '1.Path:/configuration/route-isis/isis-instances/isis-isis/isis'
              + '-instances/isis-instance/isis-attr/prefix-attribute-advertise.'
              + 'Add this leaf.'+"\n"
              + '2.Path:/configuration/route-isis/isis-instances/isis-isis/isis'
              + '-instances/isis-instance/isis-attr/ipv6-prefix-attribute-adver'
              + 'tise. Add this leaf.'+"\n"
              + '3.Path:/configuration/global-config/ipv4-external-prefix-calcu'
              + 'late-low-preference. Add this leaf.'+"\n"
              + '4.Path:/configuration/global-config/ipv6-external-prefix-calcu'
              + 'late-low-preference. Add this leaf.'
                ;
  }
  revision 2021-01-15 {
    description '1.Path:/configuration/route-isis/isis-instances/isis-isis/isis'
              + '-instances/isis-instance/isis-attr/te-link-loss. Add this leaf'
              + '.'
                ;
  }
  revision 2020-12-11 {
    description '1.Path:/isis:configuration/isis:route-isis/isis:isis-instances'
              + '/isis:isis-instance/isis:isis-intfs/isis:isis-intf-attr/isis:f'
              + 'ast-reroute-srlgs. The state of this container is changed from'
              + ' current to obsolete.'+"\n"
              + '2.Path:/isis:configuration/isis:route-isis/isis:isis-instances'
              + '/isis:isis-instance/isis:isis-intfs/isis:isis-intf-attr/isis:f'
              + 'rr-srlgs. Add this container.'
                ;
  }
  revision 2020-12-10 {
    description '1.Path:/isis:configuration/isis:route-isis/isis:isis-instances'
              + '/isis:isis-instance/isis:ipv6-redistributes/isis:redis-other-p'
              + 'rotocols/isis:redis-other-protocol/isis:protocol.'+"\n"
              + 'Add an enum type:nptv6.'+"\n"
              + '2.Path:/configuration/route-isis/isis-instances/isis-isis/isis'
              + '-instances/isis-instance/isis-attr/te-link-bandwidth. Add this'
              + ' leaf.'
                ;
  }
  revision 2020-11-13 {
    description '1.Path:/configuration/route-isis/isis-instances/isis-isis/isis'
              + '-instances/isis-instance/isis-intfs/isis-intf-attr/fast-rerout'
              + 'e-tilfa-block. Add this container.'+"\n"
              + '2.Path:/configuration/route-isis/isis-instances/isis-isis/isis'
              + '-instances/isis-instance/isis-intfs/isis-intf-attr/ipv6-fast-r'
              + 'eroute-tilfa-block. Add this container.'
                ;
  }
  revision 2020-11-09 {
    description '1.Path:/configuration/route-isis/isis-instances/isis-isis/isis'
              + '-instances/isis-instance/isis-ipv6-router-id. Add this contain'
              + 'er.'
                ;
  }
  revision 2020-10-16 {
    description '1.Path:/configuration/route-isis/isis-instances/isis-isis/isis'
              + '-instances/isis-instance/ipv6-flex-algorithms. Add this contai'
              + 'ner.'
                ;
  }
  revision 2020-10-13 {
    description '1.Path:/configuration/route-isis/isis-instances/isis-isis/isis'
              + '-instances/isis-instance/isis-attr/adjacency-hold-time. Add th'
              + 'is leaf.'+"\n"
              + '2.Path:/configuration/route-isis/isis-instances/isis-isis/isis'
              + '-instances/isis-instance/isis-attr/lsp-hold-time. Add this lea'
              + 'f.'
                ;
  }
  revision 2020-09-24 {
    description '1.Path:/configuration/route-isis/isis-instances/isis-instance/'
              + 'bier The state of this container is changed from current to ob'
              + 'solete.'+"\n"
              + '2.Path:/configuration/route-isis/isis-instances/isis-instance/'
              + 'ipv4-bier. Add this container.'+"\n"
              + '3.Path:/configuration/route-isis/isis-instances/isis-instance/'
              + 'ipv6-bier. Add this container.'
                ;
  }
  revision 2020-09-09 {
    description '1.Path:/configuration/route-isis/isis-instances/isis-instance/'
              + 'set-ol-bit/link-block. The state of this container is changed '
              + 'from current to obsolete.'+"\n"
              + '2.Path:/configuration/route-isis/isis-instances/isis-instance/'
              + 'set-ol-bit/ol-link-block-attr. Add this container.'
                ;
  }
  revision 2020-08-26 {
    description '1.Path:/configuration/route-isis/isis-instances/isis-isis/isis'
              + '-instances/isis-instance/ipv6-traffic-eng. Add this container.'
                ;
  }
  revision 2020-07-15 {
    description '1.Path:/configuration/route-isis/isis-instances/isis-isis/isis'
              + '-instances/isis-instance/isis-intfs/isis-intf-attr/ipv4-bfd-te'
              + 'mplate. Add this container.'+"\n"
              + '2.Path:/configuration/route-isis/isis-instances/isis-isis/isis'
              + '-instances/isis-instance/isis-intfs/isis-intf-attr/ipv6-bfd-te'
              + 'mplate. Add this container.'
                ;
  }
  revision 2020-07-09 {
    description '1.Path:/configuration/global-config. Add this container.'
                ;
  }
  revision 2020-07-01 {
    description '1.Path:/configuration/route-isis/isis-instances/isis-instance/'
              + 'authentications/authentication/encrypted-pwd. Modify The lengt'
              + 'h of this leaf node.'+"\n"
              + '2.Path:/configuration/route-isis/isis-instances/isis-instance/'
              + 'isis-intfs/isis-intf-attr/authentications/authentication/encry'
              + 'pted-pwd. Modify The length of this leaf node.'
                ;
  }
  revision 2020-06-24 {
    description '1.Path:/configuration/route-isis/isis-instances/isis-attr/segm'
              + 'ent-routing-ipv6/end-sid. The state of this container is chang'
              + 'ed from current to obsolete.'
                ;
  }
  revision 2020-05-25 {
    description '1.Path:/configuration/route-isis/isis-instances/isis-instance/'
              + 'set-ol-bit/link-block. Add this container.'+"\n"
              + '2.The length of routemap-name has changed.'+"\n"
              + '3.The length of prefix has changed.'+"\n"
              + '4.The length of prefix-list-name has changed.'
                ;
  }
  revision 2020-05-16 {
    description '1.Path:/configuration/route-isis/isis-instances/isis-attr/segm'
              + 'ent-routing-ipv6/end-sid/index. Add this list.'+"\n"
              + '2.Path:/configuration/route-isis/isis-instances/isis-attr/segm'
              + 'ent-routing-ipv6/end-sid/non-psp.The state of this leaf is cha'
              + 'nged from current to obsolete.'+"\n"
              + '3.Path:/configuration/route-isis/isis-instances/isis-attr/segm'
              + 'ent-routing-ipv6/end-sid/style. The state of this choice is ch'
              + 'anged from current to obsolete.'
                ;
  }
  revision 2020-04-23 {
    description '1.Path:/isis:configuration/isis:route-isis/isis:isis-instances'
              + '/isis:isis-instance/isis:microloop-prevention-policy. Add this'
              + ' container.'+"\n"
              + '2.Path:/isis:configuration/isis:route-isis/isis:isis-instances'
              + '/isis:isis-instance/isis:frr-policy. Add this container.'+"\n"
              + '3.Path:/isis:configuration/isis:route-isis/isis:isis-instances'
              + '/isis:isis-instance/isis:ipv6-microloop-prevention-policy. Add'
              + ' this container.'+"\n"
              + '4.Path:/isis:configuration/isis:route-isis/isis:isis-instances'
              + '/isis:isis-instance/isis:ipv6-frr-policy. Add this container.'
                ;
  }
  revision 2020-04-15 {
    description '1.Path:/configuration/route-isis/isis-instances/isis-isis/isis'
              + '-instances/isis-instance/isis-attr/te-link-loss-anomalous-atta'
              + 'ch-sd. Add this leaf.'
                ;
  }
  revision 2020-04-09 {
    description '1.Path:/configuration/route-isis/isis-instances/isis-attr/desc'
              + 'ription. Add this leaf.'+"\n"
              + '2.Path:/configuration/route-isis/isis-instances/isis-attr/segm'
              + 'ent-routing-mpls-adj-sid. Add this leaf.'+"\n"
              + '3.Path:/configuration/route-isis/isis-instances/isis-attr/ipv6'
              + '-segment-routing-mpls-adj-sid. Add this leaf.'
                ;
  }
  revision 2020-03-31 {
    description '1.Path:/isis:configuration/isis:route-isis/isis:isis-instances'
              + '/isis:isis-instance/isis:isis-intfs/isis:isis-intf-attr/isis:f'
              + 'ast-reroute-srlgs. Add this container.'
                ;
  }
  revision 2020-03-30 {
    description '1.Path:/configuration/route-isis/isis-instances/isis-instance/'
              + 'set-ol-bit. Add on-start-up-invalid-branch case.'
                ;
  }
  revision 2020-03-11 {
    description '1.Path:/configuration/route-isis/isis-instances/isis-attr/host'
              + 'name-string. Add this leaf.'
                ;
  }
  revision 2020-02-11 {
    description '1.Path:/configuration/route-isis/isis-instances/isis-instance/'
              + 'aiis. Add this container.'+"\n"
              + '2.Path:/configuration/route-isis/isis-instances/isis-instance/'
              + 'flex-algorithms. Add this container.'
                ;
  }
  revision 2020-01-07 {
    description '1.Path:/configuration/route-isis/isis-instances/isis-isis/isis'
              + '-instances/isis-instance/isis-intfs/isis-intf-attr/reverse-met'
              + 'ric. Add this container.'
                ;
  }
  revision 2019-12-13 {
    description '1.Path:/configuration/route-isis/isis-instances/isis-isis/isis'
              + '-instances/isis-instance/isis-intfs/isis-intf-attr/flapping-da'
              + 'mping. Add this container.'+"\n"
              + '2.Path:/configuration/route-isis/isis-instances/isis-isis/isis'
              + '-instances/isis-instance/isis-intfs/isis-intf-attr/flapping-da'
              + 'mping/detect-parameter. Add this container.'
                ;
  }
  revision 2019-10-30 {
    description '1.Path:/configuration/route-isis/isis-instances/isis-instance/'
              + 'te-link-delay. Add this container.'
                ;
  }
  revision 2019-09-27 {
    description '1.Path:/configuration/route-isis/isis-instances/isis-instance/'
              + 'segment-routing-mpls/entropy-label. Add this container.'+"\n"
              + '2.Path:/configuration/route-isis/isis-instances/isis-instance/'
              + 'ipv6-segment-routing-mpls/ipv6-entropy-label. Add this contain'
              + 'er.'
                ;
  }
  revision 2019-09-18 {
    description '1.Path:/configuration/route-isis/isis-instances/isis-isis/isis'
              + '-instances/isis-instance/isis-intfs/isis-intf-attr/link-damped'
              + '-bfd-down. Add this container.'+"\n"
              + '2.Path:/configuration/route-isis/isis-instances/isis-isis/isis'
              + '-instances/isis-instance/isis-intfs/isis-intf-attr/ipv6-link-d'
              + 'amped-bfd-down. Add this container.'
                ;
  }
  revision 2019-09-02 {
    description '1.Path:/configuration/route-isis/isis-instances/isis-instance/'
              + 'frr-priority. Add ti-lfa-priority leaf.'
                ;
  }
  revision 2019-08-13 {
    description '1.Path:/configuration/route-isis/isis-instances/isis-isis/isis'
              + '-instances/isis-instance/isis-intfs/isis-intf-attr/ipv6-metric'
              + 's. Add this container.'
                ;
  }
  revision 2019-08-08 {
    description '1.Path:/configuration/route-isis/isis-instances/isis-isis/isis'
              + '-instances/isis-instance/isis-intfs/isis-intf-attr/link-damped'
              + '-link-sd. Add this container.'+"\n"
              + '2.Path:/configuration/route-isis/isis-instances/isis-isis/isis'
              + '-instances/isis-instance/isis-intfs/isis-intf-attr/ipv6-link-d'
              + 'amped-link-sd. Add this container.'+"\n"
              + '3.Path:/configuration/route-isis/isis-instances/isis-isis/isis'
              + '-instances/isis-instance/isis-intfs/isis-intf-attr/link-damped'
              + '-lag-detect-down. Add this container.'+"\n"
              + '4.Path:/configuration/route-isis/isis-instances/isis-isis/isis'
              + '-instances/isis-instance/isis-intfs/isis-intf-attr/ipv6-link-d'
              + 'amped-lag-detect-down. Add this container.'
                ;
  }
  revision 2019-08-05 {
    description '1.Path:/configuration/route-isis/isis-instances/isis-instance/'
              + 'route-leak-l1tol2. Add without-prefix-sid leaf.'+"\n"
              + '2.Path:/configuration/route-isis/isis-instances/isis-instance/'
              + 'route-leak-l1tol2. Add host-only leaf.'+"\n"
              + '3.Path:/configuration/route-isis/isis-instances/isis-instance/'
              + 'route-leak-l2tol1. Add without-prefix-sid leaf.'+"\n"
              + '4.Path:/configuration/route-isis/isis-instances/isis-instance/'
              + 'route-leak-l2tol1. Add host-only leaf.'+"\n"
              + '5.Path:/configuration/route-isis/isis-instances/isis-instance/'
              + 'redistributes/redis-isis-protocol/redis-isis. Add without-pref'
              + 'ix-sid leaf.'+"\n"
              + '6.Path:/configuration/route-isis/isis-instances/isis-instance/'
              + 'redistributes/redis-isis-protocol/redis-isis. Add host-only le'
              + 'af.'+"\n"
              + '7.Path:/configuration/route-isis/isis-instances/isis-instance/'
              + 'redistributes/redis-ospf-protocol/redis-ospf. Add without-pref'
              + 'ix-sid leaf.'+"\n"
              + '8.Path:/configuration/route-isis/isis-instances/isis-instance/'
              + 'redistributes/redis-ospf-protocol/redis-ospf. Add host-only le'
              + 'af.'+"\n"
              + '9.Path:/configuration/route-isis/isis-instances/isis-instance/'
              + 'redistributes/redis-other-protocols/redis-other-protocol. Add '
              + 'without-prefix-sid leaf.'+"\n"
              + '10.Path:/configuration/route-isis/isis-instances/isis-instance'
              + '/redistributes/redis-other-protocols/redis-other-protocol. Add'
              + ' host-only leaf.'+"\n"
              + '11.Path:/configuration/route-isis/isis-instances/isis-instance'
              + '/ipv6-route-leak-l1tol2. Add without-prefix-sid leaf.'+"\n"
              + '12.Path:/configuration/route-isis/isis-instances/isis-instance'
              + '/ipv6-route-leak-l1tol2. Add host-only leaf.'+"\n"
              + '13.Path:/configuration/route-isis/isis-instances/isis-instance'
              + '/ipv6-route-leak-l2tol1. Add without-prefix-sid leaf.'+"\n"
              + '14.Path:/configuration/route-isis/isis-instances/isis-instance'
              + '/ipv6-route-leak-l2tol1. Add host-only leaf.'+"\n"
              + '15.Path:/configuration/route-isis/isis-instances/isis-instance'
              + '/ipv6-redistributes/redis-isis-protocol/redis-isis. Add withou'
              + 't-prefix-sid leaf.'+"\n"
              + '16.Path:/configuration/route-isis/isis-instances/isis-instance'
              + '/ipv6-redistributes/redis-isis-protocol/redis-isis. Add host-o'
              + 'nly leaf.'+"\n"
              + '17.Path:/configuration/route-isis/isis-instances/isis-instance'
              + '/ipv6-redistributes/redis-ospf-protocol/redis-ospf. Add withou'
              + 't-prefix-sid leaf.'+"\n"
              + '18.Path:/configuration/route-isis/isis-instances/isis-instance'
              + '/ipv6-redistributes/redis-ospf-protocol/redis-ospf. Add host-o'
              + 'nly leaf.'+"\n"
              + '19.Path:/configuration/route-isis/isis-instances/isis-instance'
              + '/ipv6-redistributes/redis-other-protocols/redis-other-protocol'
              + '. Add without-prefix-sid leaf.'+"\n"
              + '20.Path:/configuration/route-isis/isis-instances/isis-instance'
              + '/ipv6-redistributes/redis-other-protocols/redis-other-protocol'
              + '. Add host-only leaf.'
                ;
  }
  revision 2019-07-26 {
    description '1.Path:/configuration/route-isis/isis-instances/isis-instance/'
              + 'ipv6-microloop-prevention-segment-routing. Add this container.'
                ;
  }
  revision 2019-07-23 {
    description '1.Path:/configuration/route-isis/isis-instances/isis-instance/'
              + 'ipv6-frr-ti-lfa-sr-mpls. Add this container.'+"\n"
              + '2.Path:/configuration/route-isis/isis-instances/isis-instance/'
              + 'frr-ti-lfa.Add strategy leaf.'+"\n"
              + '3.Path:/configuration/route-isis/isis-instances/isis-instance/'
              + 'ipv6-frr-ti-lfa.Add strategy leaf.'
                ;
  }
  revision 2019-07-02 {
    description '1.Path:/configuration/route-isis/isis-instances/isis-isis/isis'
              + '-instances/isis-instance/isis-intfs/isis-intf-attr/link-damped'
              + '-metric. Add this container.'+"\n"
              + '2.Path:/configuration/route-isis/isis-instances/isis-isis/isis'
              + '-instances/isis-instance/isis-intfs/isis-intf-attr/ipv6-link-d'
              + 'amped-metric. Add this container.'+"\n"
              + '3.Path:/configuration/route-isis/isis-instances/isis-isis/isis'
              + '-instances/isis-instance/isis-intfs/isis-intf-attr/link-metric'
              + '. The state of this container is changed from current to obsol'
              + 'ete.'+"\n"
              + '4.Path:/configuration/route-isis/isis-instances/isis-isis/isis'
              + '-instances/isis-instance/isis-intfs/isis-intf-attr/link-dampin'
              + 'g. The state of this container is changed from current to obso'
              + 'lete.'+"\n"
              + '5.Path:/configuration/route-isis/isis-instances/isis-isis/isis'
              + '-instances/isis-instance/isis-intfs/isis-intf-attr/mt-ipv6-lin'
              + 'k-damping. The state of this container is changed from current'
              + ' to obsolete.'
                ;
  }
  revision 2019-04-11 {
    description '1.Path:/configuration/route-isis/isis-instances/isis-isis/isis'
              + '-instances/isis-instance/isis-intfs/isis-intf-attr/link-damped'
              + '-adj-establish. Add this container.'+"\n"
              + '2.Path:/configuration/route-isis/isis-instances/isis-isis/isis'
              + '-instances/isis-instance/isis-intfs/isis-intf-attr/ipv6-link-d'
              + 'amped-adj-establish. Add this container.'+"\n"
              + '3.Path:/configuration/route-isis/isis-instances/isis-isis/isis'
              + '-instances/isis-instance/isis-intfs/isis-intf-attr/link-damped'
              + '-revert-interval. Add this container.'+"\n"
              + '4.Path:/configuration/route-isis/isis-instances/isis-isis/isis'
              + '-instances/isis-instance/isis-intfs/isis-intf-attr/ipv6-link-d'
              + 'amped-revert-interval. Add this container.'
                ;
  }
  revision 2019-03-18 {
    description '1.Path:/configuration/route-isis/isis-instances/isis-instance/'
              + 'segment-routing-ipv6/ipv6-sr-mpls-mapping-server.The state of '
              + 'this container is changed from current to obsolete.'
                ;
  }
  revision 2019-01-28 {
    description '1.Path:/configuration/route-isis/isis-instances/isis-instance/'
              + 'ipv6-segment-routing-mpls.Add this container.'+"\n"
              + '2.Add sr-feature.'
                ;
  }
  revision 2019-01-08 {
    description '1.Path:/configuration/route-isis/isis-instances/isis-instance/'
              + 'microloop-prevention-segment-routing. Add this container.'
                ;
  }
  revision 2018-10-19 {
    description '1.Path:/configuration/route-isis/isis-instances/isis-instance/'
              + 'segment-routing-ipv6. The state of this container is changed f'
              + 'rom obsolete to current.'+"\n"
              + '2.Path:/configuration/route-isis/isis-instances/isis-instance/'
              + 'ipv6-frr-ti-lfa. The state of this container is changed from o'
              + 'bsolete to current.'+"\n"
              + '3.Path:/configuration/route-isis/isis-instances/isis-instance/'
              + 'bgp-link-states/bgp-ls/instance-id. Add this container.'
                ;
  }
  revision 2018-09-11 {
    description '1.Path:/state/route-isis/isis-peer-routerids/isis-peer-routeri'
              + 'd. Add this container.'+"\n"
              + '2.Path:/state/route-isis/isis-adjacencies/isis-adjacency/adj-i'
              + 'd. Add this leaf.'+"\n"
              + '3.Path:/state/route-isis/isis-adjacencies/isis-adjacency/adj-2'
              + 'way-state. Add this leaf.'+"\n"
              + '4.Path:/state/route-isis/isis-adjacencies/isis-adjacency/adj-l'
              + 'ast-uptime. Add this leaf.'+"\n"
              + '5.Path:/configuration/route-isis/isis-instances/isis-instance/'
              + 'microloop-prevention-rlfa.Add this container.'+"\n"
              + '6.Path:/configuration/route-isis/isis-instances/isis-instance/'
              + 'ipv6-microloop-prevention-link-up. Add this container.'
                ;
  }
  revision 2018-09-07 {
    description '1.Path:/configuration/route-isis/isis-instances/isis-instance/'
              + 'segment-routing-ipv6. Add this container.'+"\n"
              + '2.Path:/configuration/route-isis/isis-instances/isis-instance/'
              + 'segment-routing-ipv6. The state of this container is changed f'
              + 'rom current to obsolete.'+"\n"
              + '3.Path:/configuration/route-isis/isis-instances/isis-instance/'
              + 'frr-ti-lfa. Add this container.'+"\n"
              + '4.Path:/configuration/route-isis/isis-instances/isis-instance/'
              + 'ipv6-frr-ti-lfa. Add this container.'+"\n"
              + '5.Path:/configuration/route-isis/isis-instances/isis-instance/'
              + 'ipv6-frr-ti-lfa. The state of this container is changed from c'
              + 'urrent to obsolete.'+"\n"
              + '6.Path:/configuration/route-isis/isis-instances/isis-instance/'
              + 'segment-routing-mpls/sr-mpls-mapping-server. Add this containe'
              + 'r.'+"\n"
              + '7.Path:/configuration/route-isis/isis-instances/isis-isis/isis'
              + '-instances/isis-instance/isis-intfs/isis-intf-attr/link-metric'
              + '/inc-metric. The default value is changed from increase-value '
              + 'to maximum-value.'+"\n"
              + '8.Path:/configuration/route-isis/isis-instances/isis-isis/isis'
              + '-instances/isis-instance/isis-intfs/isis-intf-attr/link-metric'
              + '/inc-metric/increase-value/inc-value. The default value is abo'
              + 'lished.'+"\n"
              + '9.Path:/state/route-isis/isis-adjacencies/isis-adjacency. Add '
              + 'some selects.'+"\n"
              + '10.Path:/state/route-isis/isis-circuits/isis-circuit. Add some'
              + ' selects.'+"\n"
              + '11.Path:/configuration/route-isis/isis-instances/isis-intfs/ip'
              + 'v4-bfd-negotiation/min-tx. The range is changed , and customiz'
              + 'ed by the  performance parameter.'+"\n"
              + '12.Path:/configuration/route-isis/isis-instances/isis-intfs/ip'
              + 'v4-bfd-negotiation/min-rx. The range is changed , and customiz'
              + 'ed by the  performance parameter.'+"\n"
              + '13.Path:/configuration/route-isis/isis-instances/isis-intfs/ip'
              + 'v6-bfd-negotiation/min-tx. The range is changed , and customiz'
              + 'ed by the  performance parameter.'+"\n"
              + '14.Path:/configuration/route-isis/isis-instances/isis-intfs/ip'
              + 'v6-bfd-negotiation/min-rx. The range is changed , and customiz'
              + 'ed by the  performance parameter.'
                ;
  }
  revision 2017-08-25 {
    description '1.Path:/configuration/route-isis/isis-instances/isis-instance/'
              + 'bier. Add this container.'+"\n"
              + '2.Add pc-feature. This feature only use for PC.'
                ;
  }
  revision 2017-07-18 {
    description '1.Path:/configuration/route-isis/isis-instances/rlfa-exclude-l'
              + 'dp-not-sync. Add this container.'+"\n"
              + '2.Add rlfa-exclude-ldp-not-sync.'
                ;
  }
  revision 2017-06-27 {
    description '1.Path:/configuration/route-isis/isis-instances/isis-intfs/met'
              + 'rics/metric-value. The minimum value of sub-node is changed fr'
              + 'om 1 into 0.'
                ;
  }
  revision 2017-06-06 {
    description '1.Path:/configuration/route-isis/isis-instances/isis-intfs/lin'
              + 'k-damping. Add this container.'+"\n"
              + '2.Path:/configuration/route-isis/isis-instances/isis-intfs/mt-'
              + 'ipv6-link-damping. Add this container.'+"\n"
              + '3.Add link-damping.'+"\n"
              + '3.Add mt-ipv6-link-damping.'
                ;
  }
  revision 2016-12-07 {
    description '1.Path:/configuration/route-isis/isis-instances/isis-instance/'
              + 'segment-routing-mpls.Add this container.'+"\n"
              + '2.Add sr-feature.'
                ;
  }
  revision 2016-09-19 {
    description '1.Path:/configuration/route-isis/isis-instances/isis-instance/'
              + 'microloop-prevention-rlfa.Add this container.'
                ;
  }
  revision 2016-08-04 {
    description '1.Path:/configuration/route-isis/isis-instances/isis-instance/'
              + 'def-info-learns.Add this container;'+"\n"
              + '2.Path:/configuration/route-isis/isis-instances/isis-instance/'
              + 'default-info/default-info-branches/def-rib-match.Add this cont'
              + 'ainer;'+"\n"
              + '3.Path:/configuration/route-isis/isis-instances/isis-instance/'
              + 'ipv6-def-info.Add this container;'+"\n"
              + '4.Path:/configuration/route-isis/isis-instances/isis-instance/'
              + 'ipv6-def-info-learns.Add this container;'+"\n"
              + '5.Path:/configuration/route-isis/isis-instances/isis-instance/'
              + 'ipv6-mpls-ldp-sync. Add this container;'+"\n"
              + '6.Path:/configuration/route-isis/isis-instances/isis-instance/'
              + 'authen-keychains. Add this container;'+"\n"
              + '7.Path:/configuration/route-isis/isis-instances/isis-intfs/isi'
              + 's-intf-attr/ipv6-mpls-ldps .Add this container.'+"\n"
              + '8.Path:/configuration/route-isis/isis-instances/isis-intfs/isi'
              + 's-intf-attr/authen-keychains .Add this container.'+"\n"
              + '9.Path:/configuration/route-isis/isis-instances/isis-intfs/isi'
              + 's-intf-attr/intf-hello-padding .Add this container.'+"\n"
              + '10.Path:/configuration/route-isis/isis-instances/isis-instance'
              + '/isis-attr.Add ipv6-auto-metric-state leaf.'+"\n"
              + '11.Path:/configuration/route-isis/isis-instances/isis-instance'
              + '/isis-attr.Add ipv6-auto-metric-ref-bw leaf.'+"\n"
              + '12.Path:/configuration/route-isis/isis-instances/isis-instance'
              + '/metrics.Add this container;'+"\n"
              + '13.Path:/configuration/route-isis/isis-instances/isis-instance'
              + '/ipv6-metrics.Add this container.'
                ;
  }
  revision 2016-03-16 {
    description 'Path:/configuration/route-isis/isis-instances/isis-instance/bg'
              + 'p-link-states. Add this container.'
                ;
  }
  revision 2015-09-22 {
    description '1.Path:/configuration/route-isis/isis-instances/isis-instance/'
              + 'router-id/router-id.Add this container;'+"\n"
              + '2.Path:/configuration/route-isis/isis-instances/isis-instance/'
              + 'remote-lfa-state.Add this container;'+"\n"
              + '3.Path:/configuration/route-isis/isis-instances/isis-instance/'
              + 'remote-lfa-max-metrics.Add this container;'+"\n"
              + '4.Path:/configuration/route-isis/isis-instances/isis-instance/'
              + 'frr-priority. Add this container;'+"\n"
              + '5.Path:/configuration/route-isis/isis-instances/isis-intfs/isi'
              + 's-intf-attr/fast-remote-lfa-block .Add this container.'
                ;
  }
  revision 2015-08-11 {
    description '1.Path: /configuration/route-isis/isis-instances/isis-instance'
              + '/ipv4-distribute-list. Add this container'
                ;
  }
  revision 2015-08-04 {
    description "Change config flag of state node and it's sub-node from true i"
              + "nto false."
                ;
  }
  revision 2015-07-21 {
    description '1.The path:/configuration/route-isis/isis-instances/isis-insta'
              + 'nce/isis-attr.Add auto-metric-state leaf.'+"\n"
              + '2.The path:/configuration/route-isis/isis-instances/isis-insta'
              + 'nce/isis-attr.Add auto-metric-ref-bandwidth leaf.'+"\n"
              + '3.The path:/configuration/route-isis/isis-instances/isis-intfs'
              + '/isis-intf-attr/ipv4-bfd-negotiation. Add this container.'+"\n"
              + '4.The path:/configuration/route-isis/isis-instances/isis-intfs'
              + '/isis-intf-attr/ipv6-bfd-negotiation. Add this container.'+"\n"
              + '5.The path:/configuration/route-isis/isis-instances/isis-insta'
              + 'nce/track-objects. Add this container.'
                ;
  }
  revision 2015-04-02 {
    description 'The path:/state/route-isis/isis/isis-adjacencies/isis-adjacenc'
              + 'y.'+"\n"
              + 'The isis-adjacency list add adj-vrf-name leaf.'
                ;
  }
  revision 2015-03-10 {
    description 'The path:/state/route-isis/isis/isis-adjacencies/isis-adjacenc'
              + 'y.'+"\n"
              + 'The isis-adjacency list add adj-system-type leaf and adj-exten'
              + 'ded-circ-id leaf.'
                ;
  }
  revision 2015-03-09 {
    description '1.Path: /configuration/route-isis/isis-instances/isis-instance'
              + '/ipv4-redis-prefix-limits. Add this container'+"\n"
              + '2.Path: /configuration/route-isis/isis-instances/isis-instance'
              + '/ipv6-redis-prefix-limits. Add this container'
                ;
  }
  revision 2015-01-09 {
    description '1.Path:/configuration/route-isis/isis-instances/isis-instance/'
              + 'isis-intfs/isis-intf-attr/link-metric.Add this container'
                ;
  }
  revision 2014-11-03 {
    description 'The path:/configuration/route-isis/isis-instances/isis-intfs/i'
              + 'sis-intf-attr/static-remote-lfas. Add this container.'
                ;
  }
  revision 2014-10-21 {
    description '1.Path:/configuration/route-isis/isis-instances/isis-instance/'
              + 'isis-attr/ipv6-distance. This leaf is out of use.'+"\n"
              + '2.Path:/configuration/route-isis/isis-instances/isis-instance/'
              + 'isis-attr/distance.This leaf is out of use.'+"\n"
              + '3.Path:/configuration/route-isis/isis-instances/isis-instance/'
              + 'ipv4-distances.'+"\n"
              + '  Add this container.'+"\n"
              + '4.Path:/configuration/route-isis/isis-instances/isis-instance/'
              + 'ipv6-distances.'+"\n"
              + '  Add this container.'
                ;
  }
  revision 2014-10-14 {
    description 'Path:/isis:configuration/isis:route-isis/isis:isis-instances/i'
              + 'sis:isis-instance/isis:ipv6-redistributes/isis:redis-other-pro'
              + 'tocols/isis:redis-other-protocol/isis:protocol'+"\n"
              + 'Add an enum type:dhcp-pd.'
                ;
  }
  revision 2014-07-04 {
    description 'The path:/configuration/route-isis/isis-instances/isis-instanc'
              + 'e/restart-t2-timers/restart-t2-timer/t2-timer'+"\n"
              + 'The default value of t2-timer changed from 60 into 330.'
                ;
  }
  revision 2014-06-19 {
    description '1.Modify some descriptions, which had mistakes or were imperfe'
              + 'ct.'+"\n"
              + '2.The leaf t3-timer-value was set mandatory.'+"\n"
              + '3.The range of tag-number changed from 0..4294967295 into 1..4'
              + '294967295.'+"\n"
              + '4.The type of leaf auto changed from boolean into empty.'+"\n"
              + '5.The type of leaf wait-for-bgp changed from boolean into empt'
              + 'y.'+"\n"
              + '6.Modify mesh-group model.'+"\n"
              + '7.Modify set-ol-bit model.'+"\n"
              + '8.Modify redistribute model.'
                ;
  }
  revision 2014-05-05 {
    description '1.Modify some spelling mistakes.'+"\n"
              + '2.Add description on some enum items which description was lac'
              + 'k.'+"\n"
              + '3.Change the type of adj-snpa-address from string into string-'
              + 'all.'+"\n"
              + '  Change the type of circuit-state from string into string-all'
              + '.'+"\n"
              + '  Change the type of adj-state from string into string-all.'+"\n"
              + '4.The type of level in redistributes change from uint8 into en'
              + 'umeration.'+"\n"
              + '5.The range of circuit-l1-dr modify from 0-17 into 1-17.'+"\n"
              + '6.Add default value on interval leaf of spf-interval.'+"\n"
              + '  Add default value on metric-style.'+"\n"
              + '7.Add two typedef:isis-level and isis-state.'
                ;
  }
  revision 2014-04-18 {
    description 'Change the object of system-id from container to list. '+"\n"
              + 'The leaf of state in route-leak-l2tol1 is set mandatory.'+"\n"
              + 'The leaf of state in ipv6-route-leak-l2tol1 is set mandatory.'
                ;
  }
  revision 2013-10-30 {
    description 'The initial version.'
                ;
  }
  feature sr-feature {
    description 'Only for the use of 15K ,T8K and PC.'
                ;
  }
  feature pc-feature {
    description 'Router and switch PC feature.'
                ;
  }
  feature aii-feature {
    description 'Router and switch aii feature.'
                ;
  }
  feature bier-feature {
    description 'Router and switch bier feature.'
                ;
  }
  typedef isis-level {
    type enumeration {
      enum level-1 {
        value 1 ;
        description 'Level-1 will be effected on.'
                    ;
      }
      enum level-2 {
        value 2 ;
        description 'Level-2 will be effected on.'
                    ;
      }
      enum level-1-2 {
        value 3 ;
        description 'Level-1-2 will be effected on.'
                    ;
      }
    }
    description 'Level(s) will be effected on.'
                ;
  }
  typedef isis-state {
    type enumeration {
      enum disable {
        value 0 ;
        description 'The state is off.'
                    ;
      }
      enum enable {
        value 1 ;
        description 'The state is on.'
                    ;
      }
    }
    description 'The state of some isis attributes.'
                ;
  }
  container configuration {
    description Configuration. ;
    container route-isis {
      description 'Route ISIS configuration.'
                  ;
      container isis-instances {
        description 'ISIS instance information.'
                    ;
        list isis-instance {
          description 'The information of ISIS instance.'
                      ;
          key process-id ;
          leaf process-id {
            description 'ISIS process ID'
                        ;
            type uint32 {
              range 0..65535 ;
            }
          }
          leaf vrf-name {
            description 'VPN routing/forwarding instance (VRF) name.'
                        ;
            type string {
              length 1..32 ;
            }
          }
          container system-ids {
            description 'System id.'
                        ;
            list system-id {
              description System-ID. ;
              max-elements 1 ;
              key isis-system-id ;
              leaf isis-system-id {
                description 'A system ID for an ISIS instance.'
                            ;
                type ncd:mac-address ;
              }
              leaf range {
                description 'The range of system-ID.'
                            ;
                type uint8 {
                  range 0..32 ;
                }
                default 0 ;
              }
            }
          }
          container authentications {
            description 'Authentication information.'
                        ;
            presence 'encrypted password'
                     ;
            list authentication {
              description 'Authentication information.'
                          ;
              key level ;
              leaf level {
                description 'Level(s) will be effected on.'
                            ;
                type uint8 {
                  range 0..2 ;
                }
              }
              choice authen-word {
                description Password ;
                case word {
                  description 'Word case.'
                              ;
                  leaf authen-pwd {
                    description 'The clear password.'
                                ;
                    type string {
                      length 1..100 ;
                    }
                    mandatory true ;
                  }
                }
                case clear {
                  description 'Authentication clear password case.'
                              ;
                  leaf clear-pwd {
                    description 'Specify the clear password.'
                                ;
                    type string {
                      length 1..100 ;
                    }
                    mandatory true ;
                  }
                }
                case encrypted-word {
                  description 'The label of encrypted password'
                              ;
                  leaf encrypted-pwd {
                    description 'Authentication encrypted password'
                                ;
                    type string {
                      length 24..192 ;
                    }
                    mandatory true ;
                  }
                }
              }
            }
          }
          container authentication-types {
            description 'Authentication type.'
                        ;
            presence 'authen type'
                     ;
            list authen-type {
              description 'Authentication type'
                          ;
              key level ;
              leaf level {
                description 'Level(s) would be effected on.'
                            ;
                type uint8 {
                  range 0..2 ;
                }
              }
              leaf authen-type {
                description 'Authentication type.'
                            ;
                type enumeration {
                  enum md5 {
                    value 1 ;
                  }
                  enum text {
                    value 2 ;
                  }
                }
                default text ;
              }
            }
          }
          container areas {
            description Areas. ;
            list area {
              description 'Area address information.'
                          ;
              max-elements 3 ;
              key area-addr ;
              leaf area-addr {
                description 'ISIS area address'
                            ;
                type ncd:area-id ;
              }
            }
          }
          container isis-attr {
            description 'ISIS attribution.'
                        ;
            leaf isis-protocol-state {
              description 'Flag of that system is enable.'
                          ;
              type isis-state ;
              default enable ;
            }
            leaf is-type {
              description 'Level(s) of the ISIS instance.'
                          ;
              type isis-level ;
              default level-1-2 ;
            }
            leaf i-spf {
              description 'Flag of the i-spf is enable.'
                          ;
              type boolean ;
            }
            leaf distance {
              description 'IPv4 management distance.This leaf is out of use. Th'
                        + 'e value of output is invalid.'
                          ;
              type uint8 {
                range 1..255 ;
              }
              default 115 ;
            }
            leaf maximum-paths {
              description 'Maximum of paths to one destination.'
                          ;
              type uint32 {
                range 1..128 ;
              }
              default 1 ;
            }
            leaf lsp-size-originate {
              description 'LSP MTU'
                          ;
              type uint16 {
                range 512..7680 ;
              }
              units byte ;
              default 1492 ;
            }
            leaf lsp-size-recieve {
              description 'The size of LSP can be recieved.'
                          ;
              type uint16 {
                range 512..7680 ;
              }
              units byte ;
              default 1492 ;
            }
            leaf snp-authentication-state {
              description 'Flag of the ISIS instance whether support SNP authen'
                        + 'tication.'
                          ;
              type enumeration {
                enum disable-snp-authentication {
                  value 0 ;
                  description 'Config disable-snp-authentication.'
                              ;
                }
                enum enable-snp-authentication {
                  value 1 ;
                  description 'Config enable-snp-authentication.'
                              ;
                }
              }
              default enable-snp-authentication ;
            }
            leaf ignore-lsp-errors {
              description 'Flag of the system whether would ignore LSP checksum'
                        + ' error.'
                          ;
              type isis-state ;
              default enable ;
            }
            leaf lsp-refresh-time {
              description 'LSP refresh interval.'
                          ;
              type uint16 {
                range 1..65535 ;
              }
              units second ;
              default 900 ;
            }
            leaf max-lsp-lifetime {
              description 'Max LSP life time.'
                          ;
              type uint16 {
                range 1..65535 ;
              }
              units second ;
              default 1200 ;
            }
            leaf restart-state {
              description 'Flag of the system whether enable GR.'
                          ;
              type isis-state ;
            }
            leaf snmp-context {
              description 'ISIS mib context name'
                          ;
              type string {
                length 1..30 ;
              }
            }
            leaf local-mt-state {
              description 'Flag of that IGP-MT is enable.'
                          ;
              type isis-state ;
            }
            leaf fast-reroute-type {
              description 'FRR type'
                          ;
              type enumeration {
                enum down-stream-path {
                  value 1 ;
                }
              }
            }
            leaf hostname-dynamic {
              description 'Dynamic hostname.'
                          ;
              type isis-state ;
              default enable ;
            }
            leaf fast-flood-num {
              description 'Number of the fast flooding LSPs.'
                          ;
              type uint8 {
                range 1..15 ;
              }
            }
            leaf ipv6-frr-type {
              description 'IPv6 fast-reroute type.'
                          ;
              type enumeration {
                enum down-stream-path {
                  value 1 ;
                  description 'The FRR type is down-stream-path.'
                              ;
                }
              }
            }
            leaf ipv6-distance {
              description 'ISIS IPv6 management distance.This leaf is out of us'
                        + 'e. The value of output is invalid.'
                          ;
              type uint8 {
                range 1..255 ;
              }
              default 115 ;
            }
            leaf ipv6-maximum-paths {
              description 'Maximum of paths to one destination of IPv6.'
                          ;
              type uint32 {
                range 1..128 ;
              }
              default 1 ;
            }
            leaf ipv6-set-ol-bit {
              description 'Set IPv6 OL bit.'
                          ;
              type boolean ;
            }
            leaf mpls-ldp-auto-config {
              description 'The state of mpls ldp auto-config.'
                          ;
              type isis-state ;
            }
            leaf auto-metric-state {
              description 'Whether adjust IS-IS interface metric according to b'
                        + 'andwidth.'
                          ;
              type isis-state ;
              default disable ;
              ncd:revise-date 2015-07-21 ;
            }
            leaf auto-metric-ref-bandwidth {
              description 'Use reference bandwidth to assign IS-IS metric'
                          ;
              type uint32 {
                range 1..2147483648 ;
              }
              default 100 ;
              ncd:revise-date 2015-07-21 ;
            }
            leaf ipv6-auto-metric-state {
              description 'Whether adjust IS-IS IPv6 interface metric according'
                        + ' to bandwidth.'
                          ;
              type isis-state ;
              default disable ;
              ncd:revise-date 2016-08-04 ;
            }
            leaf ipv6-auto-metric-ref-bw {
              description 'Use reference bandwidth to assign IS-IS IPv6 metric'
                          ;
              type uint32 {
                range 1..2147483648 ;
              }
              default 100 ;
              ncd:revise-date 2016-08-04 ;
            }
            leaf hostname-string {
              description 'ISIS hostname for instance'
                          ;
              type string {
                length 1..64 ;
              }
              ncd:revise-date 2020-03-11 ;
            }
            leaf description {
              description 'Description of process.'
                          ;
              type string {
                length 1..63 ;
              }
              ncd:revise-date 2020-04-09 ;
            }
            leaf segment-routing-mpls-adj-sid {
              if-feature sr-feature ;
              description 'Add the application mode of segment-routing-mpls-adj'
                        + '-sid.'
                          ;
              type enumeration {
                enum hybrid {
                  value 1 ;
                  description 'Hybrid mode.'
                              ;
                }
                enum static {
                  value 0 ;
                  description 'Static mode.'
                              ;
                }
              }
              default hybrid ;
              ncd:revise-date 2020-04-09 ;
            }
            leaf ipv6-segment-routing-mpls-adj-sid {
              if-feature sr-feature ;
              description 'Add the application mode of ipv6-segment-routing-mpl'
                        + 's-adj-sid.'
                          ;
              type enumeration {
                enum hybrid {
                  value 1 ;
                  description 'Hybrid mode.'
                              ;
                }
                enum static {
                  value 0 ;
                  description 'Static mode.'
                              ;
                }
              }
              default hybrid ;
              ncd:revise-date 2020-04-09 ;
            }
            leaf te-link-loss-anomalous-attach-sd {
              description 'Advertise te link loss anomalous attached with sd.'
                          ;
              type enumeration {
                enum disable {
                  value 0 ;
                  description 'Disable advertise te link loss anomalous attache'
                            + 'd with sd.'
                              ;
                }
                enum attach-sd {
                  value 1 ;
                  description 'Advertise te link loss anomalous attached with s'
                            + 'd.'
                              ;
                }
              }
              default disable ;
              ncd:revise-date 2020-04-15 ;
            }
            leaf adjacency-hold-time {
              description 'Adjacency hold time.'
                          ;
              type uint16 {
                range 0..65535 ;
              }
              units second ;
              default 0 ;
              ncd:revise-date 2020-10-13 ;
            }
            leaf lsp-hold-time {
              description 'Lsp hold time'
                          ;
              type uint16 {
                range 0..65535 ;
              }
              units second ;
              default 0 ;
              ncd:revise-date 2020-10-13 ;
            }
            leaf te-link-bandwidth {
              description 'Advertise te link bandwidth.'
                          ;
              type isis-state ;
              default disable ;
              ncd:revise-date 2020-12-10 ;
            }
            leaf te-link-loss {
              description 'Advertise te link bandwidth.'
                          ;
              type isis-state ;
              default disable ;
              ncd:revise-date 2021-01-15 ;
            }
            leaf prefix-attribute-advertise {
              description 'Set ipv4 prefix-attribute advertise mode'
                          ;
              type enumeration {
                enum auto {
                  value 0 ;
                  description 'Some prefix with prefix-attribute sub-TLV accord'
                            + 'ing to scenario'
                              ;
                }
                enum all {
                  value 1 ;
                  description 'All prefix with prefix-attribute sub-TLV'
                              ;
                }
                enum none {
                  value 2 ;
                  description 'None prefix with prefix-attribute sub-TLV'
                              ;
                }
              }
              default auto ;
              ncd:revise-date 2021-02-05 ;
            }
            leaf ipv6-prefix-attribute-advertise {
              description 'Set ipv6 prefix-attribute advertise mode'
                          ;
              type enumeration {
                enum auto {
                  value 0 ;
                  description 'Some prefix with prefix-attribute sub-TLV accord'
                            + 'ing to scenario'
                              ;
                }
                enum all {
                  value 1 ;
                  description 'All prefix with prefix-attribute sub-TLV'
                              ;
                }
                enum none {
                  value 2 ;
                  description 'None prefix with prefix-attribute sub-TLV'
                              ;
                }
              }
              default auto ;
              ncd:revise-date 2021-02-05 ;
            }
            leaf crypto-authen-keychain-hmac-md5 {
              description 'Configure generic cryptographic authentication based'
                        + ' on HMAC-MD5 algorithm of keychain.'
                          ;
              type isis-state ;
              default disable ;
              ncd:revise-date 2021-03-03 ;
            }
          }
          container hello-padding {
            description 'Hello padding.'
                        ;
            presence 'hello padding'
                     ;
            leaf hello-padding-type {
              description 'Hello PDU padding type.'
                          ;
              type enumeration {
                enum hello-padding {
                  value 0 ;
                  description 'Can pad multi-point and point to point.'
                              ;
                }
                enum multi-point {
                  value 1 ;
                  description 'Can pad multi-point.'
                              ;
                }
                enum point-to-point {
                  value 2 ;
                  description 'Can pad point-to-point.'
                              ;
                }
              }
              mandatory true ;
            }
          }
          container metric-style {
            description 'Metric style.'
                        ;
            presence 'metric style'
                     ;
            leaf metric-style {
              description 'Metric style. The default value is narrow.'
                          ;
              type enumeration {
                enum narrow {
                  value 1 ;
                  description 'The style of metric is narrow.'
                              ;
                }
                enum wide {
                  value 2 ;
                  description 'The style of metric is wide.'
                              ;
                }
              }
              mandatory true ;
            }
          }
          container restart-t3-timer {
            description 'GR T3 timer.'
                        ;
            choice t3-timer {
              description 'Attribution of T3 timer.'
                          ;
              case t3-type-adjacency {
                description 'T3 type is adjacency.'
                            ;
                leaf adjacency {
                  description 'Flag of that GR T3 is setup.'
                              ;
                  type enumeration {
                    enum adjacency {
                      value 1 ;
                      description 'The type of T3 is adjacency.'
                                  ;
                    }
                  }
                }
              }
              case t3-type-manual {
                description 'T3 type is manual.'
                            ;
                leaf manual {
                  description 'Flag of that GR t3 is setup.The default value of'
                            + ' t3-type is manual.'
                              ;
                  type enumeration {
                    enum manual {
                      value 2 ;
                      description 'The type of T3 is manual.'
                                  ;
                    }
                  }
                  mandatory true ;
                }
                leaf t3-timer-value {
                  description 'The value of GR T3 configured.'
                              ;
                  type uint16 {
                    range 1..65535 ;
                  }
                  units second ;
                  mandatory true ;
                }
              }
            }
          }
          container default-info {
            description 'Control distribution of default information.'
                        ;
            presence 'default information'
                     ;
            leaf default-info-originate {
              description 'ISIS redistribution default information flag.'
                          ;
              type boolean ;
              mandatory true ;
            }
            container default-info-branches {
              description 'Default info branches.'
                          ;
              presence 'always branch'
                       ;
              container always-branch {
                description 'Config default information always attribution.'
                            ;
                presence always ;
                leaf always {
                  description 'Always redistribute the default routes.'
                              ;
                  type boolean ;
                  mandatory true ;
                }
                leaf always-level {
                  description 'Level(s) on which the system will always redistr'
                            + 'ibute the default routes.'
                              ;
                  type isis-level ;
                  default level-2 ;
                }
                leaf always-metric {
                  description 'Metric of the default redistributed routes .'
                              ;
                  type uint32 {
                    range 0..4261412864 ;
                  }
                  default 0 ;
                }
                leaf always-metric-style {
                  description "Type of the default always redistributed routes'"
                            + " metric."
                              ;
                  type enumeration {
                    enum internal {
                      value 2 ;
                    }
                  }
                  default internal ;
                }
              }
              container conditional-branch {
                description 'Config default information conditional attribution.'
                            ;
                leaf default-info-level {
                  description 'Level(s) of the default routes.'
                              ;
                  type isis-level ;
                  default level-2 ;
                }
                leaf default-info-metric {
                  description 'Metric of the default routes.'
                              ;
                  type uint32 {
                    range 0..4261412864 ;
                  }
                  default 0 ;
                }
                leaf default-info-metric-style {
                  description "Type of the default routes' metric."
                              ;
                  type enumeration {
                    enum external {
                      value 1 ;
                    }
                    enum internal {
                      value 2 ;
                    }
                  }
                  default internal ;
                }
              }
              container def-rib-match {
                description 'Config default information default-rib-match attri'
                          + 'bution.'
                            ;
                presence def-rib-match ;
                leaf state {
                  description 'Advertise default route matched with RIB.'
                              ;
                  type boolean ;
                  mandatory true ;
                }
                leaf level {
                  description 'Level(s) on which the system will advertise defa'
                            + 'ult route matched with RIB.'
                              ;
                  type isis-level ;
                  default level-2 ;
                }
                leaf metric {
                  description 'Metric of the default routes matched with RIB.'
                              ;
                  type uint32 {
                    range 0..4261412864 ;
                  }
                  default 0 ;
                }
                leaf metric-style {
                  description "Type of the default routes' metric."
                              ;
                  type enumeration {
                    enum external {
                      value 1 ;
                    }
                    enum internal {
                      value 2 ;
                    }
                  }
                  default internal ;
                }
                ncd:revise-date 2016-08-04 ;
              }
            }
          }
          container spf-intervals {
            description 'Attributes of SPF interval.'
                        ;
            presence 'spf interval'
                     ;
            list spf-interval {
              description 'ISIS SPF execution interval.'
                          ;
              key level ;
              leaf level {
                description 'Level(s) will be effected on.'
                            ;
                type uint8 {
                  range 0..2 ;
                }
              }
              leaf interval {
                description 'SPF execution interval.The default value is for re'
                          + 'ference only, different devices are different.'
                            ;
                type uint16 {
                  range 1..120 ;
                }
                units second ;
                default 10 ;
              }
              leaf init-delay {
                description 'Initial delay before a SPF calculation in ms.The d'
                          + 'efault value is for reference only, different devi'
                          + 'ces are different.'
                            ;
                type uint32 {
                  range 0..120000 ;
                }
                units millisecond ;
                default 5500 ;
              }
              leaf wait-first-second {
                description 'Secondary delay before a SPF calculation in ms.The'
                          + ' default value is for reference only, different de'
                          + 'vices are different.'
                            ;
                type uint32 {
                  range 1..120000 ;
                }
                units millisecond ;
                default 5500 ;
              }
            }
          }
          container lsp-gen-intervals {
            description 'Attributes of LSP genaration interval.'
                        ;
            presence 'max delay'
                     ;
            list lsp-gen-interval {
              description 'LSP genaration interval.'
                          ;
              key level ;
              leaf level {
                description 'Level(s) will be effected on.'
                            ;
                type uint8 {
                  range 0..2 ;
                }
              }
              leaf init-delay {
                description 'Initial waiting time in milliseconds.The default v'
                          + 'alue is for reference only, different devices are '
                          + 'different.'
                            ;
                type uint32 {
                  range 0..120000 ;
                }
                units millisecond ;
                default 50 ;
              }
              leaf max-delay {
                description 'LSP Max generation interval in seconds.The default'
                          + ' value is for reference only, different devices ar'
                          + 'e different.'
                            ;
                type uint16 {
                  range 1..120 ;
                }
                units second ;
                default 5 ;
              }
              leaf wait-first-second {
                description 'Delay time between 1st and 2nd LSP generation in m'
                          + 's.The default value is for reference only, differe'
                          + 'nt devices are different.'
                            ;
                type uint32 {
                  range 1..120000 ;
                }
                units millisecond ;
                default 5000 ;
              }
            }
          }
          container summary-addrs {
            description 'Configure IP address summaries,'
                        ;
            list summary-address {
              description 'ISIS IPv4 summary'
                          ;
              key 'ip-address net-mask'
                  ;
              leaf ip-address {
                description 'Summary IP address.'
                            ;
                type ncd:ipv4-address ;
              }
              leaf net-mask {
                description 'Summary net mask.'
                            ;
                type ncd:ipv4-mask ;
              }
              leaf metric-value {
                description 'Specify the metric for summary routes.'
                            ;
                type uint32 {
                  range 0..4261412864 ;
                }
                default 0 ;
              }
              leaf level {
                description 'Level(s) will be effected on.'
                            ;
                type isis-level ;
                default level-1-2 ;
              }
            }
          }
          container ipv4-prefix-priorities {
            description 'Configure the IPv4 prefix priority.'
                        ;
            container acls {
              description 'Acl branch.'
                          ;
              list acl {
                description 'Specify acl-list to indicate priority.'
                            ;
                key 'level rule acl-name'
                    ;
                leaf level {
                  description 'Level(s) will be effected on by prefix priority.'
                              ;
                  type uint8 {
                    range 0..2 ;
                  }
                }
                leaf rule {
                  description 'ISIS prefix priority rule.'
                              ;
                  type enumeration {
                    enum critical {
                      value 1 ;
                    }
                    enum high {
                      value 2 ;
                    }
                    enum medium {
                      value 3 ;
                    }
                  }
                }
                leaf acl-name {
                  description 'ISIS prefix priority acl-list name.'
                              ;
                  type string {
                    length 1..31 ;
                  }
                }
              }
            }
            container tags {
              description 'Tag branch.'
                          ;
              list tag {
                description 'Specify a tag to indicate priority.'
                            ;
                key 'level rule tag-number'
                    ;
                leaf level {
                  description 'Level(s) will be effected on by prefix priority.'
                              ;
                  type uint8 {
                    range 0..2 ;
                  }
                }
                leaf rule {
                  description 'ISIS prefix priority rule.'
                              ;
                  type enumeration {
                    enum critical {
                      value 1 ;
                    }
                    enum high {
                      value 2 ;
                    }
                    enum medium {
                      value 3 ;
                    }
                  }
                }
                leaf tag-number {
                  description 'The number of isis prefix priority tag.'
                              ;
                  type uint32 {
                    range 1..4294967295 ;
                  }
                }
              }
            }
          }
          container route-leak-l1tol2 {
            description 'Route-leak level-1 into level-2.'
                        ;
            presence 'route leak state'
                     ;
            leaf routemap-name {
              description 'The name of route map.'
                          ;
              type string {
                length 1..200 ;
              }
            }
            leaf state {
              description "The state of route-leak level-1 into level-2.The def"
                        + "ault value is enable.It's value can not be modified."
                          ;
              type enumeration {
                enum enable {
                  value 1 ;
                  description 'The state of route-leak level-1 into level-2 is '
                            + 'enable.'
                              ;
                }
              }
              mandatory true ;
            }
            leaf without-prefix-sid {
              description 'Leak optional parameters without-prefix-sid.'
                          ;
              type isis-state ;
              default disable ;
              ncd:revise-date 2019-08-05 ;
            }
            leaf host-only {
              description 'Leak optional parameters host-only.'
                          ;
              type isis-state ;
              default disable ;
              ncd:revise-date 2019-08-05 ;
            }
          }
          container route-leak-l2tol1 {
            description 'Route-leak level-2 into level-1.'
                        ;
            presence route-leak ;
            leaf routemap-name {
              description 'The name of route map.'
                          ;
              type string {
                length 1..200 ;
              }
            }
            leaf state {
              description 'Set route leak level-2 into level-1.'
                          ;
              type isis-state ;
              mandatory true ;
            }
            leaf without-prefix-sid {
              description 'Leak optional parameters without-prefix-sid.'
                          ;
              type isis-state ;
              default disable ;
              ncd:revise-date 2019-08-05 ;
            }
            leaf host-only {
              description 'Leak optional parameters host-only.'
                          ;
              type isis-state ;
              default disable ;
              ncd:revise-date 2019-08-05 ;
            }
          }
          container redistributes {
            description 'Redistribute information from another routing protocol.'
                        ;
            container redis-isis-protocol {
              description 'Redistribute protocol is ISIS.'
                          ;
              list redis-isis {
                description 'Redistribute protocol is ISIS.'
                            ;
                key 'isis isis-process-id'
                    ;
                leaf isis {
                  description 'Redistribute protocol is ISIS.'
                              ;
                  type enumeration {
                    enum isis {
                      value 3 ;
                      description 'The type of protocol is ISIS.'
                                  ;
                    }
                  }
                }
                leaf isis-process-id {
                  description 'Redistribute process ID.'
                              ;
                  type uint32 {
                    range 0..65535 ;
                  }
                }
                leaf level {
                  description 'Level(s) will be effected on.'
                              ;
                  type isis-level ;
                  default level-2 ;
                }
                leaf metric-style {
                  description 'OSPF/ISIS exterior metric type for redistributio'
                            + 'n.'
                              ;
                  type enumeration {
                    enum external {
                      value 1 ;
                      description 'The metric-style is external.'
                                  ;
                    }
                    enum internal {
                      value 2 ;
                      description 'The metric-style is internal.'
                                  ;
                    }
                  }
                  default internal ;
                }
                leaf routemap-name {
                  description 'Route map reference.'
                              ;
                  type string {
                    length 1..200 ;
                  }
                }
                choice metric-value {
                  description 'The redistribute metric value.'
                              ;
                  default isis-branch ;
                  case originate-branch {
                    description 'The original metric case.'
                                ;
                    leaf with-originate-metric {
                      description 'Using original metric'
                                  ;
                      type empty ;
                    }
                  }
                  case isis-branch {
                    description 'ISIS config metric case'
                                ;
                    leaf metric {
                      description 'ISIS config metric'
                                  ;
                      type uint32 {
                        range 0..4261412864 ;
                      }
                      default 0 ;
                    }
                  }
                }
                leaf without-prefix-sid {
                  description 'Redistribute optional parameters without-prefix-'
                            + 'sid.'
                              ;
                  type isis-state ;
                  default disable ;
                  ncd:revise-date 2019-08-05 ;
                }
                leaf host-only {
                  description 'Redistribute optional parameters host-only.'
                              ;
                  type isis-state ;
                  default disable ;
                  ncd:revise-date 2019-08-05 ;
                }
              }
            }
            container redis-ospf-protocol {
              description 'The redistribute protocol is OSPF.'
                          ;
              list redis-ospf {
                description 'Redistribute protocol is OSPF.'
                            ;
                key 'ospf ospf-process-id'
                    ;
                leaf ospf {
                  description 'Redistribute protocol is OSPF.'
                              ;
                  type enumeration {
                    enum ospf {
                      value 4 ;
                      description 'Reditribute protocol is OSPF.'
                                  ;
                    }
                  }
                }
                leaf ospf-process-id {
                  description 'Process ID of OSPF.'
                              ;
                  type uint32 {
                    range 1..65535 ;
                  }
                }
                leaf level {
                  description 'Level will be effected on.'
                              ;
                  type isis-level ;
                  default level-2 ;
                }
                leaf routemap-name {
                  description 'Redistributed route map name.'
                              ;
                  type string {
                    length 1..200 ;
                  }
                }
                leaf metric-style {
                  description 'OSPF exterior metric type for redistribution.'
                              ;
                  type enumeration {
                    enum external {
                      value 1 ;
                      description 'The metric-style is external.'
                                  ;
                    }
                    enum internal {
                      value 2 ;
                      description 'The metric-style is internal.'
                                  ;
                    }
                  }
                  default internal ;
                }
                choice metric-value {
                  description 'The redistribute metric value.'
                              ;
                  default isis-branch ;
                  case isis-branch {
                    description 'ISIS config metric case.'
                                ;
                    leaf metric {
                      description 'ISIS config metric'
                                  ;
                      type uint32 {
                        range 0..4261412864 ;
                      }
                      default 0 ;
                    }
                  }
                  case originate-branch {
                    description 'The original metric case.'
                                ;
                    leaf with-originate-metric {
                      description 'Using original metric.'
                                  ;
                      type empty ;
                    }
                  }
                }
                leaf without-prefix-sid {
                  description 'Redistribute optional parameters without-prefix-'
                            + 'sid.'
                              ;
                  type isis-state ;
                  default disable ;
                  ncd:revise-date 2019-08-05 ;
                }
                leaf host-only {
                  description 'Redistribute optional parameters host-only.'
                              ;
                  type isis-state ;
                  default disable ;
                  ncd:revise-date 2019-08-05 ;
                }
              }
            }
            container redis-other-protocols {
              description 'Redistribute protocol is neither ISIS nor OSPF.'
                          ;
              list redis-other-protocol {
                description 'Redistribute protocol is neither ISIS nor OSPF.'
                            ;
                key protocol ;
                leaf protocol {
                  description 'Redistribution protocol.'
                              ;
                  type enumeration {
                    enum bgp {
                      value 1 ;
                      description 'The type of protocol is bgp.'
                                  ;
                    }
                    enum connected {
                      value 2 ;
                      description 'Connceted routes.'
                                  ;
                    }
                    enum rip {
                      value 5 ;
                      description 'The type of protocol is rip.'
                                  ;
                    }
                    enum static {
                      value 6 ;
                      description 'The type of protocol is static.'
                                  ;
                    }
                    enum nat {
                      value 8 ;
                      description 'NAT routes.'
                                  ;
                    }
                    enum natpt {
                      value 9 ;
                      description 'Port-addrees Translation routes.'
                                  ;
                    }
                    enum ps-busi-addr {
                      value 10 ;
                      description 'Ps-busi-addr routes.'
                                  ;
                    }
                    enum ps-user-addr {
                      value 11 ;
                      description 'Ps-user-addr routes.'
                                  ;
                    }
                    enum subscriber-aggregation {
                      value 12 ;
                      description "Bras subscriber's aggregation routes."
                                  ;
                    }
                    enum subscriber-host {
                      value 13 ;
                      description 'Subscriber host.'
                                  ;
                    }
                    enum user-special {
                      value 14 ;
                      description 'User-special routes.'
                                  ;
                    }
                    enum sl-nat64-ipv4 {
                      value 16 ;
                      description 'The type of protocol is sl-nat64-ipv6.'
                                  ;
                    }
                  }
                }
                leaf level {
                  description 'Level(s) will be effected on.'
                              ;
                  type isis-level ;
                  default level-2 ;
                }
                leaf metric-style {
                  description 'ISIS exterior metric type for redistribution.'
                              ;
                  type enumeration {
                    enum external {
                      value 1 ;
                      description 'The metric-style is external.'
                                  ;
                    }
                    enum internal {
                      value 2 ;
                      description 'The metric-style is internal.'
                                  ;
                    }
                  }
                  default internal ;
                }
                leaf routemap-name {
                  description 'Redistributed route map reference'
                              ;
                  type string {
                    length 1..200 ;
                  }
                }
                choice metric-value {
                  description 'The redistribute metric value.'
                              ;
                  default isis-branch ;
                  case isis-branch {
                    description 'ISIS config metric case.'
                                ;
                    leaf metric {
                      description 'ISIS config metric'
                                  ;
                      type uint32 {
                        range 0..4261412864 ;
                      }
                      default 0 ;
                    }
                  }
                  case originate-branch {
                    description 'The original metric case.'
                                ;
                    leaf with-originate-metric {
                      description 'Using original metric.'
                                  ;
                      type empty ;
                    }
                  }
                }
                leaf without-prefix-sid {
                  description 'Redistribute optional parameters without-prefix-'
                            + 'sid.'
                              ;
                  type isis-state ;
                  default disable ;
                  ncd:revise-date 2019-08-05 ;
                }
                leaf host-only {
                  description 'Redistribute optional parameters host-only.'
                              ;
                  type isis-state ;
                  default disable ;
                  ncd:revise-date 2019-08-05 ;
                }
              }
            }
          }
          container multi-topology {
            description Multi-topology. ;
            leaf state {
              description 'Multiply topology enable flag.'
                          ;
              type isis-state ;
            }
          }
          container ipv6-distribute-list {
            description 'IPv6 distribution instance.'
                        ;
            presence 'ipv6 distribute list'
                     ;
            leaf routemap-name {
              description 'Routemap name used in IPv6 distribution.'
                          ;
              type string {
                length 1..200 ;
              }
              mandatory true ;
            }
          }
          container ipv6-spf-intervals {
            description 'Attributes of IPv6 SPF interval.'
                        ;
            presence 'spf interval'
                     ;
            list ipv6-spf-interval {
              description 'IPv6 SPF interval.'
                          ;
              key level ;
              leaf level {
                description 'Level(s) will be effected on.'
                            ;
                type uint8 {
                  range 0..2 ;
                }
              }
              leaf interval {
                description 'ISIS SPF execution interval.The default value is f'
                          + 'or reference only, different devices are different'
                          + '.'
                            ;
                type uint16 {
                  range 1..120 ;
                }
                units second ;
                default 10 ;
              }
              leaf init-delay {
                description 'The initial waiting delay before first SPF in mill'
                          + 'iseconds.The default value is for reference only, '
                          + 'different devices are different.'
                            ;
                type uint32 {
                  range 0..120000 ;
                }
                units millisecond ;
                default 5500 ;
              }
              leaf second-delay {
                description 'Minimum wait between first and second SPF in ms.Th'
                          + 'e default value is for reference only, different d'
                          + 'evices are different.'
                            ;
                type uint32 {
                  range 1..120000 ;
                }
                units millisecond ;
                default 5500 ;
              }
            }
          }
          container ipv6-summary-prefixs {
            description 'IPv6 summary prefix.'
                        ;
            list ipv6-summary-prefix {
              description 'IPv6 summary prefix.'
                          ;
              key 'ipv6-prefix prefix-len'
                  ;
              leaf ipv6-prefix {
                description 'IPv6 summary address.'
                            ;
                type ncd:ipv6-address ;
              }
              leaf prefix-len {
                description 'Prefix length of summary.'
                            ;
                type uint8 ;
              }
              leaf metric {
                description 'Specify metric value for summary prefix.'
                            ;
                type uint32 {
                  range 0..4261412864 ;
                }
                default 0 ;
              }
              leaf level {
                description 'Level(s) will be effected on.'
                            ;
                type isis-level ;
                default level-1-2 ;
              }
            }
          }
          container ipv6-route-leak-l1tol2 {
            description 'IPv6 route-leak level-1 into level-2.'
                        ;
            presence ipv6-route-leak ;
            leaf routemap-name {
              description 'Route map name.'
                          ;
              type string {
                length 1..200 ;
              }
            }
            leaf state {
              description "The state of IPv6 route-leak level-1 into level-2.Th"
                        + "e default value is enable.It's value can not be modi"
                        + "fied."
                          ;
              type enumeration {
                enum enable {
                  value 1 ;
                  description 'The state of IPv6 route-leak level-1 into level-'
                            + '2 is enable.'
                              ;
                }
              }
              mandatory true ;
            }
            leaf without-prefix-sid {
              description 'IPv6 leak optional parameters without-prefix-sid.'
                          ;
              type isis-state ;
              default disable ;
              ncd:revise-date 2019-08-05 ;
            }
            leaf host-only {
              description 'IPv6 leak optional parameters host-only.'
                          ;
              type isis-state ;
              default disable ;
              ncd:revise-date 2019-08-05 ;
            }
          }
          container ipv6-route-leak-l2tol1 {
            description 'IPv6 route-leak level-2 into level-1.'
                        ;
            presence 'ipv6 route-leak'
                     ;
            leaf routemap-name {
              description 'Route map name.'
                          ;
              type string {
                length 1..200 ;
              }
            }
            leaf state {
              description 'Enable route-leak level-2 into level-1.'
                          ;
              type isis-state ;
              mandatory true ;
            }
            leaf without-prefix-sid {
              description 'IPv6 leak optional parameters without-prefix-sid.'
                          ;
              type isis-state ;
              default disable ;
              ncd:revise-date 2019-08-05 ;
            }
            leaf host-only {
              description 'IPv6 leak optional parameters host-only.'
                          ;
              type isis-state ;
              default disable ;
              ncd:revise-date 2019-08-05 ;
            }
          }
          container ipv6-frr-state {
            description 'Set ISIS IPv6 fast-reroute.'
                        ;
            presence 'ipv6 FRR'
                     ;
            leaf state {
              description 'The flag of IPv6 FRR.'
                          ;
              type isis-state ;
            }
            leaf multi-home {
              description 'Fast-reroute selection state for IPv6 multi-homed pr'
                        + 'efixes.'
                          ;
              type isis-state ;
              default disable ;
              ncd:revise-date 2021-02-23 ;
            }
          }
          container ipv6-redistributes {
            description 'IPv6 redistribute.'
                        ;
            container redis-isis-protocol {
              description 'Redistribute protocol is ISIS.'
                          ;
              list redis-isis {
                description 'Redistribute protocol is ISIS.'
                            ;
                key 'isis isis-process-id'
                    ;
                leaf isis {
                  description 'Redistribution protocol.'
                              ;
                  type enumeration {
                    enum isis {
                      value 3 ;
                      description 'The type of protocol is isis.'
                                  ;
                    }
                  }
                }
                leaf isis-process-id {
                  description 'Redistributed process ID.'
                              ;
                  type uint32 {
                    range 0..65535 ;
                  }
                }
                leaf level {
                  description 'Level(s) will be effected on.'
                              ;
                  type isis-level ;
                  default level-2 ;
                }
                leaf metric {
                  description 'Metric for redistributed routes'
                              ;
                  type uint32 {
                    range 0..4261412864 ;
                  }
                  default 0 ;
                }
                leaf routemap-name {
                  description 'Redistributed route map name.'
                              ;
                  type string {
                    length 1..200 ;
                  }
                }
                leaf without-prefix-sid {
                  description 'IPv6 redistribute optional parameters without-pr'
                            + 'efix-sid.'
                              ;
                  type isis-state ;
                  default disable ;
                  ncd:revise-date 2019-08-05 ;
                }
                leaf host-only {
                  description 'IPv6 redistribute optional parameters host-only.'
                              ;
                  type isis-state ;
                  default disable ;
                  ncd:revise-date 2019-08-05 ;
                }
              }
            }
            container redis-other-protocols {
              description 'Redistribute protocol is neither ISIS nor OSPF.'
                          ;
              list redis-other-protocol {
                description 'Redistribute protocol is not ISIS or OSPF.'
                            ;
                key protocol ;
                leaf protocol {
                  description 'Redistribution protocol.'
                              ;
                  type enumeration {
                    enum bgp {
                      value 1 ;
                      description 'The type of protocol is bgp.'
                                  ;
                    }
                    enum connected {
                      value 2 ;
                      description 'The type of protocol is connect.'
                                  ;
                    }
                    enum rip {
                      value 5 ;
                      description 'The type of protocol is rip.'
                                  ;
                    }
                    enum static {
                      value 6 ;
                      description 'The type of protocol is static.'
                                  ;
                    }
                    enum dhcp-pd {
                      value 7 ;
                      description 'The type of protocol is dhcp-pd.'
                                  ;
                    }
                    enum subscriber-host {
                      value 13 ;
                      description 'The type of protocol is subscriber-host.'
                                  ;
                    }
                    enum sl-nat64-ipv6 {
                      value 15 ;
                      description 'The type of protocol is ipv6 sl-nat64.'
                                  ;
                    }
                    enum sf-nat64 {
                      value 17 ;
                      description 'The type of protocol is sf-nat64.'
                                  ;
                    }
                    enum aftr {
                      value 18 ;
                      description 'The type of protocol is aftr.'
                                  ;
                    }
                    enum nptv6 {
                      value 23 ;
                      description 'The type of protocol is nptv6.'
                                  ;
                    }
                  }
                }
                leaf level {
                  description 'Level(s) will be effected on.'
                              ;
                  type isis-level ;
                  default level-2 ;
                }
                leaf metric {
                  description 'Metric for redistributed routes.'
                              ;
                  type uint32 {
                    range 0..4261412864 ;
                  }
                  default 0 ;
                }
                leaf routemap-name {
                  description 'Redistributed route map name.'
                              ;
                  type string {
                    length 1..200 ;
                  }
                }
                leaf without-prefix-sid {
                  description 'IPv6 redistribute optional parameters without-pr'
                            + 'efix-sid.'
                              ;
                  type isis-state ;
                  default disable ;
                  ncd:revise-date 2019-08-05 ;
                }
                leaf host-only {
                  description 'IPv6 redistribute optional parameters host-only.'
                              ;
                  type isis-state ;
                  default disable ;
                  ncd:revise-date 2019-08-05 ;
                }
              }
            }
            container redis-ospf-protocol {
              description 'Redistribute protocol is  OSPF.'
                          ;
              list redis-ospf {
                description 'Redistribute protocol is OSPF.'
                            ;
                key 'ospf ospf-process-id'
                    ;
                leaf ospf {
                  description 'Redistribute protocol is OSPF.'
                              ;
                  type enumeration {
                    enum ospf {
                      value 4 ;
                    }
                  }
                }
                leaf ospf-process-id {
                  description 'Process ID of OSPF.'
                              ;
                  type uint32 {
                    range 1..65535 ;
                  }
                }
                leaf level {
                  description 'Level will be effected on.'
                              ;
                  type isis-level ;
                  default level-2 ;
                }
                leaf metric {
                  description 'The metric of redistributed routes.'
                              ;
                  type uint32 {
                    range 0..4261412864 ;
                  }
                  default 0 ;
                }
                leaf routemap-name {
                  description 'The name of route-map.'
                              ;
                  type string {
                    length 1..200 ;
                  }
                }
                leaf without-prefix-sid {
                  description 'IPv6 redistribute optional parameters without-pr'
                            + 'efix-sid.'
                              ;
                  type isis-state ;
                  default disable ;
                  ncd:revise-date 2019-08-05 ;
                }
                leaf host-only {
                  description 'IPv6 redistribute optional parameters host-only.'
                              ;
                  type isis-state ;
                  default disable ;
                  ncd:revise-date 2019-08-05 ;
                }
              }
            }
          }
          container ipv6-prefix-priorities {
            description 'Configure the IPv6 prefix priority.'
                        ;
            container acls {
              description 'Specify acl-list to indicate priority.'
                          ;
              list acl {
                description 'Specify acl-list to indicate priority.'
                            ;
                key 'level rule acl-name'
                    ;
                leaf level {
                  description 'Level(s) will be effected on by prefix priority.'
                              ;
                  type uint8 {
                    range 0..2 ;
                  }
                }
                leaf rule {
                  description 'Prefix-priority rule.'
                              ;
                  type enumeration {
                    enum critical {
                      value 1 ;
                    }
                    enum high {
                      value 2 ;
                    }
                    enum medium {
                      value 3 ;
                    }
                  }
                }
                leaf acl-name {
                  description 'Acl name.'
                              ;
                  type string {
                    length 1..31 ;
                  }
                }
              }
            }
            container tags {
              description 'Specify a tag to indicate priority.'
                          ;
              list tag {
                description 'Specify a tag to indicate priority.'
                            ;
                key 'level rule tag-number'
                    ;
                leaf level {
                  description 'Level(s) will be effected on by prefix priority.'
                              ;
                  type uint8 {
                    range 0..2 ;
                  }
                }
                leaf rule {
                  description 'Prefix-priority rule.'
                              ;
                  type enumeration {
                    enum critical {
                      value 1 ;
                    }
                    enum high {
                      value 2 ;
                    }
                    enum medium {
                      value 3 ;
                    }
                  }
                }
                leaf tag-number {
                  description 'Config tag number.'
                              ;
                  type uint32 {
                    range 1..4294967295 ;
                  }
                }
              }
            }
          }
          container mpls-traffic-engs {
            description 'The object of ISIS MPLS.'
                        ;
            list mpls-traffic-eng {
              description 'ISIS traffic engineering.'
                          ;
              key level ;
              leaf level {
                description 'Level(s) will be effected on.'
                            ;
                type enumeration {
                  enum level-1 {
                    value 1 ;
                    description 'Mpls traffic-eng on level 1.'
                                ;
                  }
                  enum level-2 {
                    value 2 ;
                    description 'Mpls traffic-eng on level 2.'
                                ;
                  }
                }
              }
            }
          }
          container mpls-ldp-sync {
            description 'Configure LDP-ISIS synchronization.'
                        ;
            presence 'mpls ldp sync'
                     ;
            leaf level {
              description 'Level(s) will be effected on.'
                          ;
              type uint8 {
                range 0..2 ;
              }
              mandatory true ;
            }
          }
          container ipv4-frr-state {
            description 'IPv4 fast reroute state.'
                        ;
            presence 'frr state'
                     ;
            leaf state {
              description 'The state of IPv4 FRR.'
                          ;
              type isis-state ;
            }
            leaf multi-home {
              description 'Fast-reroute selection state for multi-homed prefixe'
                        + 's.'
                          ;
              type isis-state ;
              default disable ;
              ncd:revise-date 2021-02-23 ;
            }
          }
          container restart-t2-timers {
            description 'GR t2 timer.'
                        ;
            list restart-t2-timer {
              description 'ISIS GR t2 timer.'
                          ;
              key level ;
              leaf level {
                description 'Level(s) will be effected on.'
                            ;
                type uint8 {
                  range 0..2 ;
                }
              }
              leaf t2-timer {
                description 'The value of T2 timer.'
                            ;
                type uint16 {
                  range 5..65535 ;
                }
                units second ;
                default 330 ;
              }
            }
          }
          container set-ol-bit {
            description 'Set overload bit.'
                        ;
            presence 'set overload bit'
                     ;
            leaf ol-set-flag {
              description 'The flag of setting OL bit.'
                          ;
              type boolean ;
              mandatory true ;
            }
            container suppress-type {
              description 'If overload-bit set, suppress the following types.'
                          ;
              presence 'suppress type'
                       ;
              leaf ol-suppress-type {
                description 'If overload-bit set, suppress the following types.'
                            ;
                type enumeration {
                  enum external {
                    value 1 ;
                    description 'IP prefixes learned from other protocols.'
                                ;
                  }
                  enum interlevel {
                    value 2 ;
                    description 'IP prefixes learned from another ISIS level.'
                                ;
                  }
                  enum all {
                    value 3 ;
                    description 'Both interlevel and external.'
                                ;
                  }
                }
                mandatory true ;
              }
            }
            container ol-link-block-attr {
              description 'Block link advertisement after reload'
                          ;
              presence 'link block attr'
                       ;
              leaf link-block-attr {
                description 'Block link advertisement after reload'
                            ;
                type empty ;
                mandatory true ;
              }
              ncd:revise-date 2020-09-09 ;
            }
            choice on-start-up {
              description 'Config OL attribution after restart.'
                          ;
              case auto-branch {
                description 'Waiting for ISIS database synchronization.'
                            ;
                leaf auto {
                  description 'Waiting for ISIS database synchronization.'
                              ;
                  type empty ;
                  mandatory true ;
                }
                leaf auto-time {
                  description 'Time in seconds to clear OL bit after reboot.'
                              ;
                  type uint32 {
                    range 5..86400 ;
                  }
                  units second ;
                }
              }
              case wait-for-bgp-branch {
                description 'Let BGP decide when to unset the OL bit.'
                            ;
                leaf wait-for-bgp {
                  description 'Let BGP decide when to clear the OL bit.'
                              ;
                  type empty ;
                  mandatory true ;
                }
                leaf ol-bgp-time {
                  description 'Time in seconds to clear OL bit after reboot.'
                              ;
                  type uint32 {
                    range 5..86400 ;
                  }
                  units second ;
                }
              }
              case const-time-branch {
                description 'Time in seconds to unset OL bit after reboot.'
                            ;
                leaf ol-const-time {
                  description 'Time in seconds to unset OL bit after reboot.'
                              ;
                  type uint32 {
                    range 5..86400 ;
                  }
                  units second ;
                }
              }
              case on-start-up-invalid-branch {
                description 'Shutdown on-start-up function'
                            ;
                leaf on-start-up-invalid {
                  description 'Shutdown on-start-up function'
                              ;
                  type empty ;
                  mandatory true ;
                }
                ncd:revise-date 2020-03-30 ;
              }
            }
            container link-block {
              status obsolete {
                ncd:revise-date 2020-09-09 ;
              }
              description 'Block link advertisement after reload'
                          ;
              presence 'link block'
                       ;
              leaf ol-link-block {
                description 'Block link advertisement after reload'
                            ;
                type empty ;
                mandatory true ;
              }
              ncd:revise-date 2020-05-25 ;
            }
          }
          container isis-intfs {
            description 'Attributes of isis interface.'
                        ;
            list isis-intf-attr {
              description 'Information of ISIS interface.'
                          ;
              key intf-name ;
              leaf intf-name {
                description 'The name of interface.'
                            ;
                type ncd:ifname ;
              }
              leaf circuit-type {
                description "Circuit's level."
                            ;
                type enumeration {
                  enum level-1 {
                    value 1 ;
                    description level-1 ;
                  }
                  enum level-2-only {
                    value 2 ;
                    description level-2 ;
                  }
                  enum level-1-2 {
                    value 3 ;
                    description level-1-2 ;
                  }
                }
                default level-1-2 ;
              }
              leaf bfd-state {
                description 'Enable IPv4 bfd on this interface.'
                            ;
                type isis-state ;
              }
              leaf bfd-mode {
                description 'Set bfd mode.'
                            ;
                type enumeration {
                  enum standard {
                    value 0 ;
                  }
                  enum strict {
                    value 1 ;
                  }
                }
                default standard ;
                ncd:revise-date 2021-03-02 ;
              }
              leaf fast-reroute-block {
                description 'Set interface ip fast-reroute attribute.'
                            ;
                type boolean ;
              }
              leaf ignore-mtu {
                description 'Ignore interface MTU.'
                            ;
                type boolean ;
              }
              leaf max-burst {
                description 'The maximum number of sent LSP each time.'
                            ;
                type uint16 {
                  range 1..50 ;
                }
                default 1 ;
              }
              leaf monitor-receive-interval {
                description 'Monitor ISIS packet receive interval.'
                            ;
                type uint16 {
                  range 1..100 ;
                }
                units second ;
                default 10 ;
              }
              leaf monitor-send-interval {
                description 'Monitor ISIS packet send interval.'
                            ;
                type uint16 {
                  range 1..100 ;
                }
                units second ;
                default 10 ;
              }
              leaf network-p2p {
                description 'Specify ISIS point-to-point network.'
                            ;
                type boolean ;
              }
              leaf passive-mode {
                description 'Control the interface routing update.'
                            ;
                type enumeration {
                  enum disable {
                    value 0 ;
                    description 'Passive mode is off.'
                                ;
                  }
                  enum enable {
                    value 1 ;
                    description 'Passive mode is on.'
                                ;
                  }
                  enum with-original-metric {
                    value 2 ;
                    description 'Using original metric of the interface.'
                                ;
                  }
                }
              }
              leaf ignore-ip-adj-check {
                description 'Ignore adjacency check.'
                            ;
                type boolean ;
              }
              leaf ipv6-bfd-state {
                description 'Enable ipv6 bfd on this interface.'
                            ;
                type isis-state ;
              }
              leaf ipv6-fast-reroute-block {
                description 'Interface IPv6 fast-reroute block.'
                            ;
                type boolean ;
              }
              leaf ignore-ipv6-adj-check {
                description 'Ignore IPv6 adjacency check.'
                            ;
                type boolean ;
              }
              leaf ignore-ip-subnet-check {
                description 'Ignore IP address subnet check.'
                            ;
                type boolean ;
              }
              container psnp-intervals {
                description 'Psnp interval.'
                            ;
                presence 'psnp interval'
                         ;
                list psnp-interval {
                  description 'Psnp interval.'
                              ;
                  key level ;
                  leaf level {
                    description 'Level(s) will be effected on.'
                                ;
                    type uint8 {
                      range 0..2 ;
                    }
                  }
                  leaf psnp-interval {
                    description 'PSNP transmission interval.'
                                ;
                    type uint16 {
                      range 1..65535 ;
                    }
                    units second ;
                    default 3 ;
                  }
                }
              }
              container intf-mpls-ldps {
                description 'Configure MPLS LDP protocol parameters.'
                            ;
                list intf-mpls-ldp-sync {
                  description 'Configure LDP-ISIS synchronization on interface.'
                              ;
                  key level ;
                  leaf level {
                    description 'Level(s) will be effected on.'
                                ;
                    type uint8 {
                      range 0..2 ;
                    }
                  }
                  leaf disable {
                    description 'Disable the flag of ISIS interface mpls ldp sy'
                              + 'nchronization flag.'
                                ;
                    type boolean ;
                  }
                }
              }
              container retransmit-intervals {
                description 'Set per-lsp retransmission interval.'
                            ;
                presence 'retran interval'
                         ;
                list retransmit-interval {
                  description 'Set per-lsp retransmission interval.'
                              ;
                  key level ;
                  leaf level {
                    description 'Level(s) will be effected on.'
                                ;
                    type uint8 {
                      range 0..2 ;
                    }
                  }
                  leaf retran-interval {
                    description 'Lsp retransmition interval.'
                                ;
                    type uint16 {
                      range 1..65535 ;
                    }
                    default 5 ;
                  }
                }
              }
              container restart-t1-retrys {
                description 'Set restart T1 retry.'
                            ;
                presence 'gr t1 retry'
                         ;
                list restart-t1-retry {
                  description 'Set restart T1 retry.'
                              ;
                  key level ;
                  leaf level {
                    description 'Level(s) will be effected on.'
                                ;
                    type uint8 {
                      range 0..2 ;
                    }
                  }
                  leaf t1-retry {
                    description 'GR T1 maximum retransmission times.'
                                ;
                    type uint16 {
                      range 1..65535 ;
                    }
                    default 3 ;
                  }
                }
              }
              container restart-t1-timers {
                description 'Set restart T1 timer.'
                            ;
                presence 't1 timer'
                         ;
                list restart-t1-timer {
                  description 'Set restart T1 timer.'
                              ;
                  key level ;
                  leaf level {
                    description 'Level(s) will be effected on.'
                                ;
                    type uint8 {
                      range 0..2 ;
                    }
                  }
                  leaf t1-timer {
                    description 'GR T1 timer interval.'
                                ;
                    type uint16 {
                      range 1..65535 ;
                    }
                    units second ;
                    default 10 ;
                  }
                }
              }
              container priorities {
                description 'Set priority for designated router election.'
                            ;
                presence priority ;
                list priority {
                  description 'Set priority for designated router election.'
                              ;
                  key level ;
                  leaf level {
                    description 'Level(s) will be effected on.'
                                ;
                    type uint8 {
                      range 0..2 ;
                    }
                  }
                  leaf priority {
                    description 'Interface priority.'
                                ;
                    type uint8 {
                      range 0..127 ;
                    }
                    default 64 ;
                  }
                }
              }
              container metrics {
                description 'Configure the metric for interface.'
                            ;
                presence metric ;
                list metric {
                  description 'Configure the metric for interface.'
                              ;
                  key level ;
                  leaf level {
                    description 'Level(s) will be effected on.'
                                ;
                    type uint8 {
                      range 0..2 ;
                    }
                  }
                  leaf metric-value {
                    description 'Interface metric value.'
                                ;
                    type uint32 {
                      range 0..16777215 ;
                    }
                    mandatory true ;
                  }
                }
              }
              container lsp-intervals {
                description 'Information of LSP transmission interval.'
                            ;
                presence 'lsp interval'
                         ;
                list lsp-interval {
                  description 'Set LSP transmission interval.'
                              ;
                  key level ;
                  leaf level {
                    description 'Level(s) will be effected on.'
                                ;
                    type uint8 {
                      range 0..2 ;
                    }
                  }
                  leaf lsp-interval {
                    description 'LSP interval.'
                                ;
                    type uint32 {
                      range 33..4294967040 ;
                    }
                    units millisecond ;
                    default 33 ;
                  }
                }
              }
              container hello-multipliers {
                description 'Set multiplier for hello holding time.'
                            ;
                presence 'hello multi'
                         ;
                list hello-multiplier {
                  description 'Set multiplier for hello holding time.'
                              ;
                  key level ;
                  leaf level {
                    description 'Level(s) will be effected on.'
                                ;
                    type uint8 {
                      range 0..2 ;
                    }
                  }
                  leaf hello-multiplier {
                    description 'Hello multiplier.'
                                ;
                    type uint16 {
                      range 3..1000 ;
                    }
                    default 3 ;
                  }
                }
              }
              container hello-intervals {
                description Hello-interval ;
                presence 'hello interval'
                         ;
                list hello-interval {
                  description 'The interval of hello pdu transmit.'
                              ;
                  key level ;
                  leaf level {
                    description 'Level(s) will be effected on.'
                                ;
                    type uint8 {
                      range 0..2 ;
                    }
                  }
                  leaf hello-interval {
                    description 'Hello-interval in seconds.'
                                ;
                    type uint16 {
                      range 1..65535 ;
                    }
                    units second ;
                    default 10 ;
                  }
                }
              }
              container csnp-intervals {
                description 'Csnp interval.'
                            ;
                presence 'csnp interval'
                         ;
                list csnp-interval {
                  description 'CSNP interval.'
                              ;
                  key level ;
                  leaf level {
                    description 'Level(s) will be effected on.'
                                ;
                    type uint8 {
                      range 0..2 ;
                    }
                  }
                  leaf csnp-interval {
                    description 'CSNP interval.'
                                ;
                    type uint16 {
                      range 1..65535 ;
                    }
                    units second ;
                    default 10 ;
                  }
                }
              }
              container authentication-types {
                description 'Authentication type of interface.'
                            ;
                presence 'auth type'
                         ;
                list authentication-type {
                  description 'Authentication type.'
                              ;
                  key level ;
                  leaf level {
                    description 'Level(s) will be effected on.'
                                ;
                    type uint8 {
                      range 0..2 ;
                    }
                  }
                  leaf auth-type {
                    description 'The type of authentication.'
                                ;
                    type enumeration {
                      enum md5 {
                        value 1 ;
                      }
                      enum text {
                        value 2 ;
                      }
                    }
                    default text ;
                  }
                }
              }
              container intf-mtu {
                description 'Set ISIS MTU.'
                            ;
                presence mtu ;
                leaf mtu {
                  description 'Interface mtu value.'
                              ;
                  type uint32 {
                    range 512..4096 ;
                  }
                  mandatory true ;
                }
              }
              container ip-router-isis {
                description 'Enable ISIS protocol on interface.'
                            ;
                presence 'ip router isis'
                         ;
                leaf ipv4-isis-state {
                  description 'Enable IPv4 ISIS protocol.'
                              ;
                  type isis-state ;
                }
              }
              container ipv6-router-isis {
                description 'Enable ISIS IPv6 protocol on interface.'
                            ;
                presence 'ipv6 router isis'
                         ;
                leaf ipv6-isis-state {
                  description 'Enable isis IPv6 on interface.'
                              ;
                  type isis-state ;
                }
              }
              container mesh-group {
                description 'Set ISIS mesh group information.'
                            ;
                choice isis-mesh-group {
                  description 'ISIS mesh group branches.'
                              ;
                  case group-number-branch {
                    description 'The branch of group number.'
                                ;
                    leaf group-number {
                      description 'Mesh group number.'
                                  ;
                      type uint32 {
                        range 1..4294967295 {
                          description 'The range of group number.'
                                      ;
                        }
                      }
                    }
                  }
                  case blocked-branch {
                    description 'The branch of blocking LSPs.'
                                ;
                    leaf blocked {
                      description 'Block LSPs on this interface.'
                                  ;
                      type empty ;
                    }
                  }
                }
              }
              container authentications {
                description 'Set authentication on interface.'
                            ;
                presence 'encrypted password'
                         ;
                list authentication {
                  description 'Set authentication on interface.'
                              ;
                  key level ;
                  leaf level {
                    description 'Information of the level.'
                                ;
                    type uint8 {
                      range 0..2 ;
                    }
                  }
                  choice password {
                    description 'Config authentication.'
                                ;
                    case word {
                      description 'Authentication word case.'
                                  ;
                      leaf auth-pwd {
                        description Password. ;
                        type string {
                          length 1..100 ;
                        }
                        mandatory true ;
                      }
                    }
                    case clear-word {
                      description 'Authentication clear word case.'
                                  ;
                      leaf clear-pwd {
                        description 'Clear password.'
                                    ;
                        type string {
                          length 1..100 ;
                        }
                        mandatory true ;
                      }
                    }
                    case encrypted-word {
                      description 'Authentication encrypted password case.'
                                  ;
                      leaf encrypted-pwd {
                        description 'Encrypted password.'
                                    ;
                        type string {
                          length 24..192 ;
                        }
                        mandatory true ;
                      }
                    }
                  }
                }
              }
              container tags {
                description "The interface's tag information."
                            ;
                presence 'tag info'
                         ;
                list tag {
                  description 'Tag information'
                              ;
                  key level ;
                  leaf level {
                    description 'Level(s) will be effected on.'
                                ;
                    type uint8 {
                      range 0..2 ;
                    }
                  }
                  leaf tag-value {
                    description 'The tag value.'
                                ;
                    type uint32 {
                      range 1..4294967295 ;
                    }
                    mandatory true ;
                  }
                }
              }
              container mpls-ldp-auto-config {
                description 'The state of mpls ldp auto-config.'
                            ;
                leaf state {
                  description 'The state of mpls ldp auto-config.'
                              ;
                  type isis-state ;
                }
              }
              container static-remote-lfas {
                description 'Static remote lfa'
                            ;
                list static-remote-lfa-prefix {
                  description 'Static remote LFA with prefix'
                              ;
                  max-elements 31 ;
                  key prefix ;
                  leaf prefix {
                    description Prefix ;
                    type string {
                      length 1..169 ;
                    }
                  }
                  leaf next-hop {
                    description 'Next hop'
                                ;
                    type ncd:ipv4-address ;
                    mandatory true ;
                  }
                }
                container static-remote-lfa {
                  description 'Static remote LFA with no prefix'
                              ;
                  presence nexthop ;
                  leaf next-hop {
                    description 'Next hop'
                                ;
                    type ncd:ipv4-address ;
                    mandatory true ;
                  }
                }
              }
              container link-metric {
                status obsolete {
                  ncd:revise-date 2019-07-02 ;
                }
                description 'Configure the metric for interface in sd status'
                            ;
                choice inc-metric {
                  description 'Configure the metric increase for interface in s'
                            + 'd status'
                              ;
                  default maximum-value ;
                  case increase-value {
                    description 'Configure the metric increase for interface in'
                              + ' sd status'
                                ;
                    leaf inc-value {
                      description 'increase value'
                                  ;
                      type uint16 {
                        range 100..10000 ;
                      }
                    }
                  }
                  case maximum-value {
                    description 'set max metric when link in sd status'
                                ;
                    leaf maximum {
                      description 'Set max maximum'
                                  ;
                      type empty ;
                    }
                  }
                }
              }
              container ipv4-bfd-negotiation {
                description 'IPv4 BFD time negotiation parameter'
                            ;
                leaf min-tx {
                  description 'Minimum transmit interval in milliseconds.The de'
                            + 'fault value is provided by the performance param'
                            + 'eter.'
                              ;
                  type uint32 {
                    range 0..10000 ;
                  }
                  units millisecond ;
                }
                leaf min-rx {
                  description 'Minimum receive interval in milliseconds.The def'
                            + 'ault value is provided by the performance parame'
                            + 'ter.'
                              ;
                  type uint32 {
                    range 0..10000 ;
                  }
                  units millisecond ;
                }
                leaf multiplier {
                  description 'Detect multiplier.The default value is provided '
                            + 'by the performance parameter.'
                              ;
                  type uint8 {
                    range 3..50 ;
                  }
                }
                ncd:revise-date 2015-07-21 ;
              }
              container ipv6-bfd-negotiation {
                description 'IPv6 BFD time negotiation parameter'
                            ;
                leaf min-tx {
                  description 'Minimum transmit interval in milliseconds.The de'
                            + 'fault value is provided by the performance param'
                            + 'eter.'
                              ;
                  type uint32 {
                    range 0..10000 ;
                  }
                  units millisecond ;
                }
                leaf min-rx {
                  description 'Minimum receive interval in milliseconds.The def'
                            + 'ault value is provided by the performance parame'
                            + 'ter.'
                              ;
                  type uint32 {
                    range 0..10000 ;
                  }
                  units millisecond ;
                }
                leaf multiplier {
                  description 'Detect multiplier.The default value is provided '
                            + 'by the performance parameter.'
                              ;
                  type uint8 {
                    range 3..50 ;
                  }
                }
                ncd:revise-date 2015-07-21 ;
              }
              container fast-remote-lfa-block {
                description 'Block interface IP remote-lfa capability'
                            ;
                leaf level {
                  description 'Level(s) will be effected on.'
                              ;
                  type uint8 {
                    range 0..2 ;
                  }
                }
                ncd:revise-date 2015-09-22 ;
              }
              container ipv6-mpls-ldps {
                description 'Configure IPv6 MPLS LDP protocol parameters.'
                            ;
                list ipv6-mpls-ldp-sync {
                  description 'Configure IPv6 LDP-ISIS synchronization on the i'
                            + 'nterface.'
                              ;
                  key level ;
                  leaf level {
                    description 'Level(s) will be effected on.'
                                ;
                    type uint8 {
                      range 0..2 ;
                    }
                  }
                  leaf disable {
                    description 'Disable ISIS mpls ldp synchronization on the i'
                              + 'nterface.'
                                ;
                    type boolean ;
                  }
                }
                ncd:revise-date 2016-08-04 ;
              }
              container authen-keychains {
                description 'Configure keychain authentication information.'
                            ;
                list authen-keychain {
                  description 'Configure keychain authentication on the interfa'
                            + 'ce.'
                              ;
                  key level ;
                  leaf level {
                    description 'Level(s) will be effected on.'
                                ;
                    type uint8 {
                      range 0..2 ;
                    }
                  }
                  leaf keychain-name {
                    description 'Keychain name associated to neighbor for authe'
                              + 'ntication on the interface.'
                                ;
                    type string {
                      length 1..31 {
                        description 'Name of a keychain (1-31 characters).'
                                    ;
                      }
                    }
                  }
                }
                ncd:revise-date 2016-08-04 ;
              }
              container link-damping {
                status obsolete {
                  ncd:revise-date 2019-07-02 ;
                }
                description 'Configure link damping for interface.'
                            ;
                leaf damping-time {
                  description 'Set damping time for link damping.'
                              ;
                  type uint32 {
                    range 1..3600 {
                      description 'The damping time value in seconds.'
                                  ;
                    }
                  }
                  units second ;
                  default 600 ;
                }
                choice inc-metric {
                  description 'Set metric for link damping.'
                              ;
                  default maximum-value ;
                  case increase-value {
                    description 'Set increase metric when link is damping.'
                                ;
                    leaf inc-value {
                      description 'The increase metric value.'
                                  ;
                      type uint32 {
                        range 100..10000 {
                          description 'The increase metric value.'
                                      ;
                        }
                      }
                      mandatory true ;
                    }
                  }
                  case maximum-value {
                    description 'Set maximum metric when link is damping.'
                                ;
                    leaf maximum {
                      description 'Set max maximum.'
                                  ;
                      type empty ;
                    }
                  }
                }
                ncd:revise-date 2017-06-06 ;
              }
              container mt-ipv6-link-damping {
                status obsolete {
                  ncd:revise-date 2019-07-02 ;
                }
                description 'Configure link damping for interface.'
                            ;
                leaf damping-time {
                  description 'Set damping time for link damping.'
                              ;
                  type uint32 {
                    range 1..3600 {
                      description 'The damping time value in seconds.'
                                  ;
                    }
                  }
                  units second ;
                  default 600 ;
                }
                choice inc-metric {
                  description 'Set metric for link damping.'
                              ;
                  default maximum-value ;
                  case increase-value {
                    description 'Set increase metric when link is damping.'
                                ;
                    leaf inc-value {
                      description 'The increase metric value.'
                                  ;
                      type uint32 {
                        range 100..10000 {
                          description 'The increase metric value.'
                                      ;
                        }
                      }
                      mandatory true ;
                    }
                  }
                  case maximum-value {
                    description 'Set maximum metric when link is damping.'
                                ;
                    leaf maximum {
                      description 'Set max maximum.'
                                  ;
                      type empty ;
                    }
                  }
                }
                ncd:revise-date 2017-06-06 ;
              }
              container link-damped-adj-establish {
                description 'Configure link damped for adj establish.'
                            ;
                leaf adj-establish-status {
                  description 'Set link damped disable or enable for adj establ'
                            + 'ish.'
                              ;
                  type isis-state ;
                  default disable ;
                }
                ncd:revise-date 2019-04-11 ;
              }
              container ipv6-link-damped-adj-establish {
                description 'Configure link damped for adj establish.'
                            ;
                leaf adj-establish-status {
                  description 'Set link damped disable or enable for adj establ'
                            + 'ish.'
                              ;
                  type isis-state ;
                  default disable ;
                }
                ncd:revise-date 2019-04-11 ;
              }
              container link-damped-revert-interval {
                description 'Configure link damped revert interval for interfac'
                          + 'e.'
                            ;
                leaf max-delay-time {
                  description 'Maximum delay before a link damped in seconds.'
                              ;
                  type uint32 {
                    range 1..3600 {
                      description 'Maximum delay before a link damped in second'
                                + 's.'
                                  ;
                    }
                  }
                  units second ;
                  default 600 ;
                }
                leaf init-delay-time {
                  description 'Initial delay before a link damped in ms.'
                              ;
                  type uint32 {
                    range 1..600000 {
                      description 'Range for delay time:1-600000(ms)'
                                  ;
                    }
                  }
                  units millisecond ;
                  default 3000 ;
                }
                leaf second-delay-time {
                  description 'Secondary delay before a link damped in ms.'
                              ;
                  type uint32 {
                    range 1..600000 {
                      description 'Range for delay time:1-600000(ms)'
                                  ;
                    }
                  }
                  units millisecond ;
                  default 3000 ;
                }
                ncd:revise-date 2019-04-11 ;
              }
              container ipv6-link-damped-revert-interval {
                description 'Configure link damped revert interval for interfac'
                          + 'e.'
                            ;
                leaf max-delay-time {
                  description 'Maximum delay before a link damped in seconds.'
                              ;
                  type uint32 {
                    range 1..3600 {
                      description 'Maximum delay before a link damped in second'
                                + 's.'
                                  ;
                    }
                  }
                  units second ;
                  default 600 ;
                }
                leaf init-delay-time {
                  description 'Initial delay before a link damped in ms.'
                              ;
                  type uint32 {
                    range 1..600000 {
                      description 'Range for delay time:1-600000(ms)'
                                  ;
                    }
                  }
                  units millisecond ;
                  default 3000 ;
                }
                leaf second-delay-time {
                  description 'Secondary delay before a link damped in ms.'
                              ;
                  type uint32 {
                    range 1..600000 {
                      description 'Range for delay time:1-600000(ms)'
                                  ;
                    }
                  }
                  units millisecond ;
                  default 3000 ;
                }
                ncd:revise-date 2019-04-11 ;
              }
              container link-damped-metric {
                description 'Configure the metric for link damped'
                            ;
                choice inc-metric {
                  description 'Configure the increase metric for link damped'
                              ;
                  default maximum-value ;
                  case increase-value {
                    description 'Configure the increase metric for link damped'
                                ;
                    leaf inc-value {
                      description 'increase value'
                                  ;
                      type uint32 {
                        range 100..10000 ;
                      }
                    }
                  }
                  case maximum-value {
                    description 'Set max metric when link damped'
                                ;
                    leaf maximum {
                      description 'Set max maximum'
                                  ;
                      type empty ;
                    }
                  }
                }
                ncd:revise-date 2019-07-02 ;
              }
              container ipv6-link-damped-metric {
                description 'Configure the metric for link damped'
                            ;
                choice inc-metric {
                  description 'Configure the increase metric for link damped'
                              ;
                  default maximum-value ;
                  case increase-value {
                    description 'Configure the increase metric for link damped'
                                ;
                    leaf inc-value {
                      description 'increase value'
                                  ;
                      type uint32 {
                        range 100..10000 ;
                      }
                    }
                  }
                  case maximum-value {
                    description 'Set max metric when link damped'
                                ;
                    leaf maximum {
                      description 'Set max maximum'
                                  ;
                      type empty ;
                    }
                  }
                }
                ncd:revise-date 2019-07-02 ;
              }
              container link-damped-link-sd {
                description 'Link SD suppression function switch.'
                            ;
                leaf status {
                  description 'enable:open link SD suppression function switch;'
                            + 'disable:shutdown link SD suppression function sw'
                            + 'itch.'
                              ;
                  type isis-state ;
                  default enable ;
                }
                ncd:revise-date 2019-08-08 ;
              }
              container ipv6-link-damped-link-sd {
                description 'Link SD suppression function switch.'
                            ;
                leaf status {
                  description 'enable:open link SD suppression function switch;'
                            + 'disable:shutdown link SD suppression function sw'
                            + 'itch.'
                              ;
                  type isis-state ;
                  default enable ;
                }
                ncd:revise-date 2019-08-08 ;
              }
              container link-damped-lag-detect-down {
                description 'Smartgroup link member interface detects the BFD d'
                          + 'own link suppression function switch.'
                            ;
                leaf status {
                  description 'enable:open switch;disable:shutdown switch.'
                              ;
                  type isis-state ;
                  default disable ;
                }
                ncd:revise-date 2019-08-08 ;
              }
              container ipv6-link-damped-lag-detect-down {
                description 'Smartgroup link member interface detects the BFD d'
                          + 'own link suppression function switch.'
                            ;
                leaf status {
                  description 'enable:open switch;disable:shutdown switch.'
                              ;
                  type isis-state ;
                  default disable ;
                }
                ncd:revise-date 2019-08-08 ;
              }
              container ipv6-metrics {
                description 'Configure the IPv6 metric for interface.'
                            ;
                list ipv6-metric {
                  description 'Configure the IPv6 metric for interface.'
                              ;
                  key level ;
                  leaf level {
                    description 'Level(s) will be effected on.'
                                ;
                    type uint8 {
                      range 0..2 ;
                    }
                  }
                  leaf metric-value {
                    description 'Interface IPv6 metric value.'
                                ;
                    type uint32 {
                      range 0..16777215 ;
                    }
                    mandatory true ;
                  }
                }
                ncd:revise-date 2019-08-13 ;
              }
              container link-damped-bfd-down {
                description 'Link BFD down suppression function switch.'
                            ;
                leaf status {
                  description 'enable:open link BFD down suppression function s'
                            + 'witch;disable:shutdown link BFD down suppression'
                            + ' function switch.'
                              ;
                  type isis-state ;
                  default enable ;
                }
                ncd:revise-date 2019-09-18 ;
              }
              container ipv6-link-damped-bfd-down {
                description 'Link IPv6 BFD down suppression function switch.'
                            ;
                leaf status {
                  description 'enable:open link IPv6 BFD down suppression funct'
                            + 'ion switch;disable:shutdown link IPv6 BFD down s'
                            + 'uppression function switch.'
                              ;
                  type isis-state ;
                  default enable ;
                }
                ncd:revise-date 2019-09-18 ;
              }
              container flapping-damping {
                description 'The damping set of isis adjacency up/down flapping.'
                            ;
                leaf state {
                  description 'State of adjacency flapping damping.'
                              ;
                  type isis-state ;
                  default enable ;
                }
                leaf delay-time {
                  description 'Delay time for adjacency flapping damping.'
                              ;
                  type uint32 ;
                  default 60 ;
                }
                container detect-parameter {
                  description 'Set detection parameters.'
                              ;
                  leaf interval {
                    description 'Detect interval.'
                                ;
                    type uint32 ;
                    default 60 ;
                  }
                  leaf threshold {
                    description 'The number of adjacency down times within the '
                              + 'detection time reaches the threshold.'
                                ;
                    type uint8 ;
                    default 3 ;
                  }
                }
                ncd:revise-date 2019-12-13 ;
              }
              container reverse-metric {
                description 'In ISIS Interface mode, set attributes of reverse-'
                          + 'metric.'
                            ;
                leaf state {
                  description 'enable:open Reverse-Metric function switch; disa'
                            + 'ble: shutdown Reverse-Metric function switch'
                              ;
                  type isis-state ;
                  default disable ;
                }
                leaf increase-value {
                  description 'Interface reverse-metric increase value'
                              ;
                  type uint32 {
                    range 1..16777214 ;
                  }
                  default 16777214 ;
                }
                ncd:revise-date 2020-01-07 ;
              }
              container fast-reroute-srlgs {
                status obsolete {
                  ncd:revise-date 2020-12-11 ;
                }
                list fast-reroute-srlg {
                  key value ;
                  leaf value {
                    description 'Configure the value of srlg.'
                                ;
                    type int32 ;
                  }
                }
                ncd:revise-date 2020-03-31 ;
              }
              container ipv4-bfd-template {
                presence 'template name'
                         ;
                leaf template-name {
                  description 'Configure BFD interface template parameter'
                              ;
                  type string {
                    length 1..31 ;
                  }
                  mandatory true ;
                }
                ncd:revise-date 2020-07-15 ;
              }
              container ipv6-bfd-template {
                presence 'template name'
                         ;
                leaf template-name {
                  description 'Configure BFD interface template parameter'
                              ;
                  type string {
                    length 1..31 ;
                  }
                  mandatory true ;
                }
                ncd:revise-date 2020-07-15 ;
              }
              container fast-reroute-tilfa-block {
                description 'Block interface IP ti-lfa capability'
                            ;
                leaf level {
                  description 'Level(s) will be effected on'
                              ;
                  type uint8 {
                    range 0..2 ;
                  }
                }
                ncd:revise-date 2020-11-13 ;
              }
              container ipv6-fast-reroute-tilfa-block {
                description 'Block interface IPv6 ti-lfa capability'
                            ;
                leaf level {
                  description 'Level(s) will be effected on'
                              ;
                  type uint8 {
                    range 0..2 ;
                  }
                }
                ncd:revise-date 2020-11-13 ;
              }
              container frr-srlgs {
                list frr-srlg {
                  key value ;
                  leaf value {
                    description 'Configure the value of srlg.'
                                ;
                    type uint32 {
                      range 0..4294967295 ;
                    }
                  }
                }
                ncd:revise-date 2020-12-11 ;
              }
            }
          }
          container ipv4-distances {
            description 'Administrative distance of IPv4 ISIS route.'
                        ;
            presence distance ;
            list ipv4-distance {
              description 'Administrative distance of route.'
                          ;
              max-elements 9 ;
              key prefix-list-name ;
              leaf prefix-list-name {
                description 'Name of a prefix list (1-169 characters).'
                            ;
                type string {
                  length 1..169 {
                    description 'Name of a prefix list (1-169 characters).'
                                ;
                  }
                }
              }
              leaf distance {
                description 'Distance value.Range:1-255'
                            ;
                type uint8 {
                  range 1..255 {
                    description 'Distance value.Range:1-255'
                                ;
                  }
                }
                mandatory true ;
              }
            }
            container distance-without-prefix-list {
              description 'IPv4 distance without prefix-list name.'
                          ;
              presence distance ;
              leaf distance {
                description 'Distance value.Range:1-255. Default:115'
                            ;
                type uint8 {
                  range 1..255 ;
                }
                default 115 ;
              }
            }
            list distance-with-rmp {
              description 'Administrative distance of route with route map.'
                          ;
              max-elements 9 ;
              key route-map-name ;
              leaf route-map-name {
                description 'Name of a route map (1-200 characters).'
                            ;
                type string {
                  length 1..200 {
                    description 'Name of a route map (1-200 characters).'
                                ;
                  }
                }
              }
              leaf distance {
                description 'Distance value.Range:1-255'
                            ;
                type uint8 {
                  range 1..255 {
                    description 'Distance value.Range:1-255'
                                ;
                  }
                }
                mandatory true ;
              }
              ncd:revise-date 2021-03-30 ;
            }
          }
          container ipv6-distances {
            description 'Administrative distance of IPv6 ISIS route.'
                        ;
            presence 'distance leaf'
                     ;
            list ipv6-distance {
              description 'Administrative distance of IPv6 route.'
                          ;
              max-elements 9 ;
              key prefix-list-name ;
              leaf prefix-list-name {
                description 'Name of a prefix list (1-169 characters).'
                            ;
                type string {
                  length 1..169 {
                    description 'Name of a prefix list (1-169 characters).'
                                ;
                  }
                }
              }
              leaf distance {
                description 'Value of distance. Range:1-255.'
                            ;
                type uint8 {
                  range 1..255 {
                    description 'Distance value.Range:1-255'
                                ;
                  }
                }
                mandatory true ;
              }
            }
            container distance-without-prefix-list {
              description 'IPv6 distance without prefix-list name.'
                          ;
              presence distance ;
              leaf distance {
                description 'Value of distance. Range:1-255.Default:115'
                            ;
                type uint8 {
                  range 1..255 ;
                }
                default 115 ;
              }
            }
            list distance-with-rmp {
              description 'Administrative distance of IPv6 route with route map.'
                          ;
              max-elements 9 ;
              key route-map-name ;
              leaf route-map-name {
                description 'Name of a route map (1-200 characters).'
                            ;
                type string {
                  length 1..200 {
                    description 'Name of a route map (1-200 characters).'
                                ;
                  }
                }
              }
              leaf distance {
                description 'Distance value.Range:1-255'
                            ;
                type uint8 {
                  range 1..255 {
                    description 'Distance value.Range:1-255'
                                ;
                  }
                }
                mandatory true ;
              }
              ncd:revise-date 2021-03-30 ;
            }
          }
          container ipv4-redis-prefix-limits {
            description 'IPv4 redistribute prefix limit'
                        ;
            list ipv4-redis-prefix-limit {
              description 'IPv4 redistribute prefix limit'
                          ;
              key level ;
              leaf level {
                description 'Level(s) will be effected on.'
                            ;
                type uint8 {
                  range 0..2 ;
                }
              }
              leaf prefix-limit {
                description 'Maximum number of IPv4 prefixes redistributed'
                            ;
                type uint32 {
                  range 1..1000000 ;
                }
                mandatory true ;
              }
            }
          }
          container ipv6-redis-prefix-limits {
            description 'IPv6 redistribute prefix limit'
                        ;
            list ipv6-redis-prefix-limit {
              description 'IPv6 redistribute prefix limit'
                          ;
              key level ;
              leaf level {
                description 'Level(s) will be effected on.'
                            ;
                type uint8 {
                  range 0..2 ;
                }
              }
              leaf prefix-limit {
                description 'Maximum number of IPv6 prefixes redistributed'
                            ;
                type uint32 {
                  range 1..1000000 ;
                }
                mandatory true ;
              }
            }
          }
          container track-objects {
            description 'Event tracking.'
                        ;
            list track-object {
              description 'Event tracking.'
                          ;
              key track-name ;
              leaf track-name {
                description 'The samgr name of the associated track detection'
                            ;
                type string {
                  length 1..31 {
                    description 'The length of track-name is from 1 to 31 chara'
                              + 'cters.'
                                ;
                  }
                }
              }
            }
            ncd:revise-date 2015-07-21 ;
          }
          container ipv4-distribute-list {
            description 'IPv4 distribution instance.'
                        ;
            presence 'ipv4 distribute list'
                     ;
            leaf routemap-name {
              description 'Routemap name used in IPv4 distribution.'
                          ;
              type string {
                length 1..200 ;
              }
              mandatory true ;
            }
            ncd:revise-date 2015-08-11 ;
          }
          container isis-router-id {
            description 'Set auxiliary router-id for ISIS process'
                        ;
            leaf router-id {
              description 'ISIS auxiliary router-id in IP address format'
                          ;
              type ncd:ipv4-address ;
            }
            ncd:revise-date 2015-09-22 ;
          }
          container remote-lfa-state {
            description 'The state of remote LFA.'
                        ;
            leaf level {
              description 'Level(s) will be effected on.'
                          ;
              type uint8 {
                range 0..2 ;
              }
            }
            ncd:revise-date 2015-09-22 ;
          }
          container remote-lfa-max-metrics {
            description 'Set maximum metric required to the release node'
                        ;
            list remote-lfa-max-metric {
              description 'Set maximum metric required to the release node'
                          ;
              key level ;
              leaf level {
                description 'Level(s) will be effected on.'
                            ;
                type uint8 {
                  range 0..2 ;
                }
              }
              leaf metric-value {
                description 'Maximum metric value.'
                            ;
                type uint32 {
                  range 1..4261412864 ;
                }
              }
            }
            ncd:revise-date 2015-09-22 ;
          }
          container frr-priority {
            description 'Set priority for FRR type'
                        ;
            leaf lfa-priority {
              description 'LFA priority.Range:1-255. Default:115.'
                          ;
              type uint8 {
                range 1..255 ;
              }
              default 115 ;
            }
            leaf rlfa-priority {
              description 'Set remote-lfa priority. Range:1-255. Default:115'
                          ;
              type uint8 {
                range 1..255 ;
              }
              default 115 ;
            }
            leaf static-rlfa-priority {
              description 'Set static remote-lfa priority. Range:1-255. Default'
                        + ':115.'
                          ;
              type uint8 {
                range 1..255 ;
              }
              default 115 ;
            }
            leaf ti-lfa-priority {
              description 'Set ti-lfa priority. Range:1-255. Default:115.'
                          ;
              type uint8 {
                range 1..255 ;
              }
              default 115 ;
              ncd:revise-date 2019-09-02 ;
            }
            ncd:revise-date 2015-09-22 ;
          }
          container bgp-link-states {
            description 'The object of ISIS BGP-LS.'
                        ;
            list bgp-ls {
              description 'ISIS BGP-LS'
                          ;
              key level ;
              leaf level {
                description 'Level(s) will be effected on.'
                            ;
                type enumeration {
                  enum level-1 {
                    value 1 ;
                    description 'BGP-LS on level-1'
                                ;
                  }
                  enum level-2 {
                    value 2 ;
                    description 'BGP-LS on level-2'
                                ;
                  }
                }
              }
              leaf instance-id {
                description 'The link-state data instance identifier'
                            ;
                type int32 {
                  range 0..65535 ;
                }
                ncd:revise-date 2018-10-19 ;
              }
            }
            ncd:revise-date 2016-03-16 ;
          }
          container def-info-learns {
            description 'Learn of ISIS IPv4 default route.'
                        ;
            list def-info-learn {
              description 'Learn of ISIS IPv4 default route.'
                          ;
              key state ;
              leaf state {
                description 'Flag of the system whether would ignore the IPv4 d'
                          + 'efault route.'
                            ;
                type enumeration {
                  enum ignore {
                    value 1 ;
                    description 'Ignore learn of ISIS default route'
                                ;
                  }
                }
              }
              leaf level {
                description 'Level(s) will be effected on.'
                            ;
                type isis-level ;
                mandatory true ;
              }
            }
            ncd:revise-date 2016-08-04 ;
          }
          container ipv6-def-info {
            description 'Control distribution of IPv6 default information.'
                        ;
            presence 'ipv6 default information'
                     ;
            leaf def-info-originate {
              description 'ISIS redistribution default information flag.'
                          ;
              type boolean ;
              mandatory true ;
            }
            container default-info {
              description 'Default info branches.'
                          ;
              presence 'always branch'
                       ;
              container always {
                description 'Config IPv6 default information always attribution.'
                            ;
                presence always ;
                leaf state {
                  description 'Always redistribute the default routes.'
                              ;
                  type boolean ;
                  mandatory true ;
                }
                leaf level {
                  description 'Level(s) on which the system will always redistr'
                            + 'ibute the IPv6 default routes.'
                              ;
                  type isis-level ;
                  default level-2 ;
                }
                leaf metric {
                  description 'Metric of the IPv6 always redistributed default '
                            + 'routes.'
                              ;
                  type uint32 {
                    range 0..4261412864 ;
                  }
                  default 0 ;
                }
              }
              container def-rib-match {
                description 'Config IPv6 default information default-rib-match '
                          + 'attribution.'
                            ;
                presence def-rib-match ;
                leaf state {
                  description 'Advertise default route matched with RIB.'
                              ;
                  type boolean ;
                  mandatory true ;
                }
                leaf level {
                  description 'Level(s) on which the system will advertise IPv6'
                            + ' default route matched with RIB.'
                              ;
                  type isis-level ;
                  default level-2 ;
                }
                leaf metric {
                  description 'Metric of the IPv6 default routes matched with R'
                            + 'IB.'
                              ;
                  type uint32 {
                    range 0..4261412864 ;
                  }
                  default 0 ;
                }
              }
            }
            ncd:revise-date 2016-08-04 ;
          }
          container ipv6-def-info-learns {
            description 'Learn of ISIS IPv6 default route.'
                        ;
            list def-info-learn {
              description 'Learn of ISIS IPv6 default route.'
                          ;
              key state ;
              leaf state {
                description 'Flag of the system whether would ignore the IPv6 d'
                          + 'efault route.'
                            ;
                type enumeration {
                  enum ignore {
                    value 1 ;
                    description 'Ignore learn of ISIS default route'
                                ;
                  }
                }
              }
              leaf level {
                description 'Level(s) will be effected on.'
                            ;
                type isis-level ;
                mandatory true ;
              }
            }
            ncd:revise-date 2016-08-04 ;
          }
          container ipv6-mpls-ldp-sync {
            description 'Configure IPv6 LDP-ISIS synchronization.'
                        ;
            leaf level {
              description 'Level(s) will be effected on.'
                          ;
              type uint8 {
                range 0..2 ;
              }
            }
            ncd:revise-date 2016-08-04 ;
          }
          container authen-keychains {
            description 'Authentication keychain information.'
                        ;
            list authen-keychain {
              description 'Configure keychain authentication.'
                          ;
              key level ;
              leaf level {
                description 'Level(s) will be effected on.'
                            ;
                type uint8 {
                  range 0..2 ;
                }
              }
              leaf keychain-name {
                description 'Keychain name associated to neighbore for authenti'
                          + 'cation.'
                            ;
                type string {
                  length 1..31 {
                    description 'Name of a keychain (1-31 characters).'
                                ;
                  }
                }
              }
            }
            ncd:revise-date 2016-08-04 ;
          }
          container metrics {
            description 'Set IS-IS instance metric'
                        ;
            list metric {
              description 'Set IS-IS instance metric'
                          ;
              key level ;
              leaf level {
                description 'Level(s) will be effected on.'
                            ;
                type uint8 {
                  range 0..2 ;
                }
              }
              leaf metric-value {
                description 'Metric value.'
                            ;
                type uint32 {
                  range 1..16777215 ;
                }
                default 10 ;
              }
            }
            ncd:revise-date 2016-08-04 ;
          }
          container ipv6-metrics {
            description 'Set IS-IS instance IPv6 metric'
                        ;
            list metric {
              description 'Set IS-IS instance IPv6 metric'
                          ;
              key level ;
              leaf level {
                description 'Level(s) will be effected on.'
                            ;
                type uint8 {
                  range 0..2 ;
                }
              }
              leaf metric-value {
                description 'Metric value.'
                            ;
                type uint32 {
                  range 1..16777215 ;
                }
                default 10 ;
              }
            }
            ncd:revise-date 2016-08-04 ;
          }
          container microloop-prevention-rlfa {
            description 'Attributes of microloop prevention for remote-LFA.'
                        ;
            leaf state {
              description 'State of microloop prevention for remote-LFA.'
                          ;
              type isis-state ;
              default enable ;
            }
            leaf delay-time {
              description 'Delay time in ms.'
                          ;
              type uint32 {
                range 1..300000 {
                  description 'Range for delay time:1-300000(ms)'
                              ;
                }
              }
              default 3000 ;
            }
            ncd:revise-date 2016-09-19 ;
          }
          container segment-routing-mpls {
            if-feature sr-feature ;
            description 'Configure segment routing for MPLS dataplane.'
                        ;
            leaf state {
              description 'State of segment routing for MPLS dataplane.'
                          ;
              type isis-state ;
              default disable ;
            }
            container sr-mpls-mapping-server {
              if-feature sr-feature ;
              description 'Configure segment routing mpls mapping-server.'
                          ;
              leaf state {
                description 'Configure segment routing mpls mapping-server.'
                            ;
                type isis-state ;
                default disable ;
              }
              ncd:revise-date 2018-09-07 ;
            }
            container entropy-label {
              if-feature sr-feature ;
              description 'Configure segment routing mpls entropy label capabil'
                        + 'ity.'
                          ;
              leaf state {
                description 'Configure segment routing mpls entropy label capab'
                          + 'ility.'
                            ;
                type isis-state ;
                default disable ;
              }
              ncd:revise-date 2019-09-27 ;
            }
            ncd:revise-date 2016-12-07 ;
          }
          container rlfa-exclude-ldp-not-sync {
            description "Configure ISIS remote-lfa with excluding primary link "
                      + "whichLDP doesn't sync"
                        ;
            leaf state {
              description "Status of ISIS remote-lfa with excluding primary lin"
                        + "k which LDP doesn't sync"
                          ;
              type isis-state ;
              default disable ;
            }
            ncd:revise-date 2017-07-18 ;
          }
          container bier {
            if-feature pc-feature ;
            status obsolete {
              ncd:revise-date 2020-09-24 ;
            }
            description 'Set IS-IS BIER info'
                        ;
            list sub-domain {
              if-feature pc-feature ;
              description 'Set IS-IS BIER sub-domain info'
                          ;
              max-elements 255 ;
              key sub-domain-id ;
              leaf sub-domain-id {
                if-feature pc-feature ;
                description 'BIER sub-domain identifier'
                            ;
                type uint16 {
                  range 0..255 {
                    description 'BIER sub-domain-id range'
                                ;
                  }
                }
              }
              leaf level {
                if-feature pc-feature ;
                description 'Level(s) will be effected on.'
                            ;
                type uint8 {
                  range 1..2 {
                    description 'Level will be effected on.'
                                ;
                  }
                }
                mandatory true ;
              }
            }
            ncd:revise-date 2017-08-25 ;
          }
          container segment-routing-ipv6 {
            description 'Configure SRV6.'
                        ;
            leaf state {
              description 'State of segment routing for IPV6 dataplane.'
                          ;
              type isis-state ;
              default disable ;
            }
            container end-sid {
              status obsolete {
                ncd:revise-date 2020-06-24 ;
              }
              list index {
                description 'Configure End SID Index'
                            ;
                key value ;
                leaf value {
                  description 'Value of End SID index.'
                              ;
                  type uint32 {
                    range 0..255 {
                      description 'Range for the value of index:0-255'
                                  ;
                    }
                  }
                }
                container style {
                  description 'Specify the SRv6 END SID style'
                              ;
                  choice style {
                    description 'Specify the SRv6 END SID style'
                                ;
                    default auto-style ;
                    case auto-style {
                      description 'Specify the SRv6 END SID is auto'
                                  ;
                      leaf auto {
                        description 'Specify the SRv6 END SID is auto'
                                    ;
                        type empty ;
                      }
                    }
                    case static-style {
                      description 'Specify the SRv6 END SID is static'
                                  ;
                      leaf sid {
                        description 'Specify the SRv6 END SID is static'
                                    ;
                        type empty ;
                        mandatory true ;
                      }
                      leaf ipv6-addr {
                        description 'Static End SID'
                                    ;
                        type ncd:ipv6-address ;
                        mandatory true ;
                      }
                    }
                  }
                }
                container flavors {
                  description 'Set the END SID behavior'
                              ;
                  choice flavors {
                    description 'Set the END SID behavior'
                                ;
                    case no-flavor {
                      description 'Set the END SID without flavor'
                                  ;
                      leaf no-flavor {
                        description 'Set the End SID without flavor.'
                                    ;
                        type empty ;
                      }
                    }
                    case flavor {
                      description 'Set the END SID with flavor'
                                  ;
                      leaf psp {
                        description 'Set the End SID with PSP.'
                                    ;
                        type empty ;
                      }
                      leaf usp {
                        description 'Set the End SID with USP.'
                                    ;
                        type empty ;
                      }
                    }
                  }
                }
                ncd:revise-date 2020-05-16 ;
              }
              choice end-sid {
                status obsolete {
                  ncd:revise-date 2020-05-16 ;
                }
                description 'end sid'
                            ;
                default auto-style ;
                case auto-style {
                  description auto ;
                  leaf auto {
                    description auto ;
                    type empty ;
                  }
                }
                case static-style {
                  description 's id'
                              ;
                  leaf sid {
                    type empty ;
                    mandatory true ;
                  }
                  leaf ipv6-addr {
                    type ncd:ipv6-address ;
                    mandatory true ;
                  }
                }
              }
              leaf non-psp {
                status obsolete {
                  ncd:revise-date 2020-05-16 ;
                }
                type uint8 {
                  range 0..1 ;
                }
                default 0 ;
              }
            }
            container ipv6-sr-mpls-mapping-server {
              status obsolete {
                ncd:revise-date 2019-03-18 ;
              }
              description 'Configure ipv6 segment routing mpls mapping-server.'
                          ;
              leaf state {
                description 'Configure ipv6 segment routing mpls mapping-server.'
                            ;
                type isis-state ;
                default disable ;
              }
            }
            ncd:revise-date 2018-10-19 ;
          }
          container frr-ti-lfa {
            description 'Configure fast-reroute ti-lfa sr-mpls.'
                        ;
            list frr-ti-lfa {
              description 'Configure fast-reroute ti-lfa sr-mpls.'
                          ;
              key level ;
              leaf level {
                description level ;
                type uint8 {
                  range 0..2 {
                    description level ;
                    reference level ;
                  }
                }
              }
              leaf sr-type {
                description 'IPV4 sr-type'
                            ;
                type enumeration {
                  enum sr-mpls {
                    value 1 ;
                    description sr-mpls ;
                  }
                }
              }
              leaf strategy {
                description 'IPv4 SR MPLS TILFA protection type.'
                            ;
                type enumeration {
                  enum default-strategy {
                    value 0 ;
                    description 'Configure TILFA default protection type.'
                                ;
                  }
                  enum node-protection {
                    value 1 ;
                    description 'Configure TILFA node protection type.'
                                ;
                  }
                }
                default default-strategy ;
                ncd:revise-date 2019-07-23 ;
              }
            }
            ncd:revise-date 2018-09-07 ;
          }
          container ipv6-frr-ti-lfa {
            description 'Configure IPV6 fast-reroute ti-lfa sr-mpls.'
                        ;
            list ipv6-frr-ti-lfa {
              description 'Configure IPV6 fast-reroute ti-lfa sr-mpls or srv6.'
                          ;
              key level ;
              leaf level {
                description level ;
                type uint8 {
                  range 0..2 {
                    description level ;
                    reference level ;
                  }
                }
              }
              leaf sr-type {
                description 'IPV6 sr-type'
                            ;
                type enumeration {
                  enum srv6 {
                    value 2 ;
                    description srv6 ;
                  }
                }
              }
              leaf strategy {
                description 'SRv6 TILFA protection type.'
                            ;
                type enumeration {
                  enum default-strategy {
                    value 0 ;
                    description 'Configure TILFA default protection type.'
                                ;
                  }
                  enum node-protection {
                    value 1 ;
                    description 'Configure TILFA node protection type.'
                                ;
                  }
                }
                default default-strategy ;
                ncd:revise-date 2019-07-23 ;
              }
            }
            ncd:revise-date 2018-10-19 ;
          }
          container ipv6-frr-ti-lfa-sr-mpls {
            description 'Configure IPV6 fast-reroute ti-lfa sr-mpls.'
                        ;
            list ipv6-frr-ti-lfa-sr-mpls {
              description 'Configure IPV6 fast-reroute ti-lfa sr-mpls or srv6.'
                          ;
              key level ;
              leaf level {
                description level ;
                type uint8 {
                  range 0..2 {
                    description level ;
                    reference level ;
                  }
                }
              }
              leaf strategy {
                description 'IPv6 SR MPLS TILFA protection type.'
                            ;
                type enumeration {
                  enum default-strategy {
                    value 0 ;
                    description 'Configure TILFA default protection type.'
                                ;
                  }
                  enum node-protection {
                    value 1 ;
                    description 'Configure TILFA node protection type.'
                                ;
                  }
                }
                default default-strategy ;
              }
            }
            ncd:revise-date 2019-07-23 ;
          }
          container microloop-prevention-link-up {
            description 'In the configuration of single topology or IPv4 mode o'
                      + 'f multi-topology , attributes of microloop prevention '
                      + 'for link-up.'
                        ;
            leaf state {
              description 'In the configuration of single topology or IPv4 mode'
                        + ' of multi-topology , state of microloop prevention f'
                        + 'or link-up.'
                          ;
              type isis-state ;
              default enable ;
            }
            leaf delay-time {
              description 'Delay time in ms.'
                          ;
              type uint32 {
                range 50..30000 {
                  description 'Range for delay time:50-300000(ms)'
                              ;
                }
              }
              default 1000 ;
            }
            ncd:revise-date 2018-09-11 ;
          }
          container ipv6-microloop-prevention-link-up {
            description 'In the configuration of multi-topology , attributes of'
                      + ' microloop prevention for link-up.'
                        ;
            leaf state {
              description 'In the configuration of multi-topology ,state of mic'
                        + 'roloop prevention for link-up.'
                          ;
              type isis-state ;
              default enable ;
            }
            leaf delay-time {
              description 'Delay time in ms.'
                          ;
              type uint32 {
                range 50..30000 {
                  description 'Range for delay time:50-300000(ms)'
                              ;
                }
              }
              default 1000 ;
            }
            ncd:revise-date 2018-09-11 ;
          }
          container microloop-prevention-segment-routing {
            description 'In the configuration of ISIS IPv4 mode ,  attributes o'
                      + 'f microloop prevention for segment-routing.'
                        ;
            leaf mpls-state {
              description 'In the configuration of ISIS IPv4 mode , state of mi'
                        + 'croloop prevention for segment-routing mpls.'
                          ;
              type isis-state ;
              default disable ;
            }
            leaf delay-time {
              description 'Delay time in ms.'
                          ;
              type uint32 {
                range 1..300000 {
                  description 'Range for delay time:1-300000(ms)'
                              ;
                }
              }
              default 3000 ;
            }
            ncd:revise-date 2019-01-08 ;
          }
          container ipv6-microloop-prevention-segment-routing {
            description 'In the configuration of ISIS IPv6 mode ,  attributes o'
                      + 'f microloop prevention for segment-routing.'
                        ;
            leaf mpls-state {
              description 'In the configuration of ISIS IPv6 mode , state of mi'
                        + 'croloop prevention for segment-routing mpls.'
                          ;
              type isis-state ;
              default disable ;
            }
            leaf srv6-state {
              description 'In the configuration of ISIS IPv6 mode , state of mi'
                        + 'croloop prevention for segment-routing srv6.'
                          ;
              type isis-state ;
              default disable ;
            }
            leaf delay-time {
              description 'IPv6 Delay time in ms.'
                          ;
              type uint32 {
                range 1..300000 {
                  description 'Range for delay time:1-300000(ms)'
                              ;
                }
              }
              default 3000 ;
            }
            ncd:revise-date 2019-07-26 ;
          }
          container ipv6-segment-routing-mpls {
            if-feature sr-feature ;
            description 'Configure ipv6 segment routing for MPLS dataplane.'
                        ;
            leaf state {
              description 'State of ipv6 segment routing for MPLS dataplane.'
                          ;
              type isis-state ;
              default disable ;
            }
            container ipv6-sr-mpls-mapping-server {
              if-feature sr-feature ;
              description 'Configure ipv6 segment routing mpls mapping-server.'
                          ;
              leaf state {
                description 'Configure ipv6 segment routing mpls mapping-server.'
                            ;
                type isis-state ;
                default disable ;
              }
            }
            container ipv6-entropy-label {
              if-feature sr-feature ;
              description 'Configure ipv6 segment routing mpls entropy label ca'
                        + 'pability.'
                          ;
              leaf state {
                description 'Configure ipv6 segment routing mpls entropy label '
                          + 'capability.'
                            ;
                type isis-state ;
                default disable ;
              }
              ncd:revise-date 2019-09-27 ;
            }
            ncd:revise-date 2019-01-28 ;
          }
          container te-link-delay {
            description 'ISIS link TE delay information notification function.'
                        ;
            leaf state {
              description 'ISIS link TE delay information notification function'
                        + ' switch.'
                          ;
              type isis-state ;
              default disable ;
            }
            ncd:revise-date 2019-10-30 ;
          }
          container aiis {
            if-feature aii-feature ;
            description 'Configure aii function.'
                        ;
            list aii {
              description 'Configure aii function.'
                          ;
              key value ;
              leaf value {
                description 'Configure the value of aii.'
                            ;
                type uint32 {
                  range 1..4294967295 {
                    description 'Range for the value of aii:1-4294967295'
                                ;
                  }
                }
              }
              leaf level {
                description 'Command support level.'
                            ;
                type uint8 {
                  range 0..2 {
                    description level ;
                    reference level ;
                  }
                }
              }
            }
            ncd:revise-date 2020-02-11 ;
          }
          container flex-algorithms {
            if-feature sr-feature ;
            description 'Configure flex-algorithm function.'
                        ;
            list flex-algorithm {
              description 'Configure flex-algorithm function.'
                          ;
              key value ;
              leaf value {
                description 'Configure the value of flex-algorithm.'
                            ;
                type uint16 {
                  range 128..255 {
                    description 'Range for the value of flex-algorithm:128-255'
                                ;
                  }
                }
              }
              leaf level {
                description 'Command support level.'
                            ;
                type uint8 {
                  range 0..2 {
                    description level ;
                    reference level ;
                  }
                }
              }
            }
            ncd:revise-date 2020-02-11 ;
          }
          container microloop-prevention-policy {
            description 'Configure microloop prevention policy.'
                        ;
            presence 'microloop prevention policy'
                     ;
            choice policy-type {
              description 'Configure microloop prevention policy.'
                          ;
              mandatory true ;
              case host-only {
                description 'Configure  microloop prevention policy base on hos'
                          + 't.'
                            ;
                leaf host-only {
                  description 'Configure microloop prevention policy base on ho'
                            + 'st.'
                              ;
                  type enumeration {
                    enum host-only {
                      value 1 ;
                      description 'Host-only policy.'
                                  ;
                    }
                  }
                  mandatory true ;
                }
              }
            }
            ncd:revise-date 2020-04-23 ;
          }
          container frr-policy {
            description 'Configure fast-reroute policy.'
                        ;
            presence 'frr policy'
                     ;
            choice policy-type {
              description 'Configure fast-reroute policy.'
                          ;
              mandatory true ;
              case host-only {
                description 'Configure fast-reroute policy base on host.'
                            ;
                leaf host-only {
                  description 'Configure fast-reroute policy base on host.'
                              ;
                  type enumeration {
                    enum host-only {
                      value 1 ;
                      description 'Host-only policy.'
                                  ;
                    }
                  }
                  mandatory true ;
                }
              }
            }
            ncd:revise-date 2020-04-23 ;
          }
          container ipv6-microloop-prevention-policy {
            description 'Configure IPv6 microloop prevention policy.'
                        ;
            presence 'ipv6 microloop prevention policy'
                     ;
            choice policy-type {
              description 'Configure IPv6 microloop prevention policy.'
                          ;
              mandatory true ;
              case host-only {
                description 'Configure  microloop prevention policy base on hos'
                          + 't.'
                            ;
                leaf host-only {
                  description 'Configure microloop prevention policy base on ho'
                            + 'st.'
                              ;
                  type enumeration {
                    enum host-only {
                      value 1 ;
                      description 'Host-only policy.'
                                  ;
                    }
                  }
                  mandatory true ;
                }
              }
            }
            ncd:revise-date 2020-04-23 ;
          }
          container ipv6-frr-policy {
            description 'Configure IPv6 fast-reroute policy.'
                        ;
            presence 'ipv6 frr policy'
                     ;
            choice ipv6-policy-type {
              description 'Configure IPv6 fast-reroute policy.'
                          ;
              mandatory true ;
              case host-only {
                description 'Configure fast-reroute policy base on host.'
                            ;
                leaf host-only {
                  description 'Configure IPv6 fast-reroute policy base on host.'
                              ;
                  type enumeration {
                    enum host-only {
                      value 1 ;
                      description 'Host-only policy.'
                                  ;
                    }
                  }
                  mandatory true ;
                }
              }
            }
            ncd:revise-date 2020-04-23 ;
          }
          container ipv6-traffic-eng {
            description 'ISIS IPv6 traffic engineering.'
                        ;
            list ipv6-traffic-eng {
              description 'ISIS IPv6 traffic engineering.'
                          ;
              key level ;
              leaf level {
                description 'Level(s) will be effected on.'
                            ;
                type enumeration {
                  enum level-1 {
                    value 1 ;
                    description 'IPv6 traffic-eng on level-1.'
                                ;
                  }
                  enum level-2 {
                    value 2 ;
                    description 'IPv6 traffic-eng on level-2.'
                                ;
                  }
                }
              }
            }
            ncd:revise-date 2020-08-26 ;
          }
          container ipv4-bier {
            if-feature bier-feature ;
            description 'Set IS-IS IPv4 BIER info'
                        ;
            list sub-domain {
              if-feature bier-feature ;
              description 'Set IS-IS IPv4 BIER sub-domain info'
                          ;
              max-elements 255 ;
              key 'sub-domain-id level'
                  ;
              leaf sub-domain-id {
                if-feature bier-feature ;
                description 'BIER sub-domain identifier'
                            ;
                type uint8 {
                  range 0..255 ;
                }
              }
              leaf level {
                if-feature bier-feature ;
                description 'Level(s) will be effected on.'
                            ;
                type uint8 {
                  range 0..2 ;
                }
              }
            }
            ncd:revise-date 2020-09-24 ;
          }
          container ipv6-bier {
            if-feature bier-feature ;
            description 'Set IS-IS IPv6 BIER info'
                        ;
            list sub-domain {
              if-feature bier-feature ;
              description 'Set IS-IS IPv6 BIER sub-domain info'
                          ;
              max-elements 255 ;
              key 'sub-domain-id level'
                  ;
              leaf sub-domain-id {
                if-feature bier-feature ;
                description 'BIER sub-domain identifier'
                            ;
                type uint8 {
                  range 0..255 ;
                }
              }
              leaf level {
                if-feature bier-feature ;
                description 'Level(s) will be effected on.'
                            ;
                type uint8 {
                  range 0..2 ;
                }
              }
            }
            ncd:revise-date 2020-09-24 ;
          }
          container ipv6-flex-algorithms {
            if-feature sr-feature ;
            description 'Configure ipv6 flex-algorithm function.'
                        ;
            list ipv6-flex-algorithm {
              description 'Configure ipv6 flex-algorithm function.'
                          ;
              key value ;
              leaf value {
                description 'Configure the value of ipv6 flex-algorithm.'
                            ;
                type uint16 {
                  range 128..255 {
                    description 'Range for the value of flex-algorithm:128-255'
                                ;
                  }
                }
              }
              leaf level {
                description 'Command support level.'
                            ;
                type uint8 {
                  range 0..2 {
                    description level ;
                  }
                }
              }
            }
            ncd:revise-date 2020-10-16 ;
          }
          container isis-ipv6-router-id {
            description 'Set auxiliary IPv6 router-id for ISIS process'
                        ;
            leaf ipv6-router-id {
              description 'ISIS auxiliary IPv6 router-id in IPv6 address format'
                          ;
              type ncd:ipv6-address ;
            }
            ncd:revise-date 2020-11-09 ;
          }
          container srv6-locators {
            if-feature sr-feature ;
            description 'SRv6 locator mode configuration.'
                        ;
            list srv6-locator {
              description 'SRv6 locator mode configuration.'
                          ;
              key locator-name ;
              leaf locator-name {
                description 'The name of locator.'
                            ;
                type string {
                  length 1..31 ;
                }
              }
              container end-sid {
                description 'End SID configuration.'
                            ;
                container auto {
                  description 'Configure the SRv6 End SID automatically.'
                              ;
                  presence 'auto status'
                           ;
                  leaf psp {
                    description 'The psp attribute of auto End SID.'
                                ;
                    type isis-state ;
                    mandatory true ;
                  }
                  leaf usp {
                    description 'The usp attribute of auto End SID.'
                                ;
                    type isis-state ;
                    mandatory true ;
                  }
                }
                container compressed-sids {
                  description 'Compressed End SID static configuration.'
                              ;
                  presence 'compressed sid'
                           ;
                  list compressed-sid {
                    description 'Compressed End SID static configuration.'
                                ;
                    key func-code ;
                    leaf func-code {
                      description 'The function code of End SID.'
                                  ;
                      type ncd:ipv6-address ;
                    }
                    leaf encapsulation-type {
                      description 'The encapsulation type attribute of End SID.'
                                  ;
                      type enumeration {
                        enum uet-128 {
                          value 0 ;
                        }
                        enum uet-32 {
                          value 1 ;
                        }
                      }
                      default uet-128 ;
                    }
                    leaf psp {
                      description 'The psp attribute of End SID.'
                                  ;
                      type isis-state ;
                      mandatory true ;
                    }
                    leaf usp {
                      description 'The usp attribute of End SID.'
                                  ;
                      type isis-state ;
                      mandatory true ;
                    }
                  }
                }
                container sids {
                  description 'End SID static configuration.'
                              ;
                  presence 'func code'
                           ;
                  list sid {
                    description 'End SID static configuration.'
                                ;
                    key func-code ;
                    leaf func-code {
                      description 'The function code of End SID.'
                                  ;
                      type ncd:ipv6-address ;
                    }
                    leaf psp {
                      description 'The psp attribute of End SID.'
                                  ;
                      type isis-state ;
                      mandatory true ;
                    }
                    leaf usp {
                      description 'The usp attribute of End SID.'
                                  ;
                      type isis-state ;
                      mandatory true ;
                    }
                  }
                }
              }
              container end-x-sid {
                description 'End.X SID configuration.'
                            ;
                container auto {
                  description 'Configure the SRv6 End.X SID automatically.'
                              ;
                  presence 'auto status'
                           ;
                  leaf psp {
                    description 'The psp attribute of auto End.X SID.'
                                ;
                    type isis-state ;
                    mandatory true ;
                  }
                  leaf usp {
                    description 'The usp attribute of auto End.X SID.'
                                ;
                    type isis-state ;
                    mandatory true ;
                  }
                }
                container compressed-sids {
                  description 'Compressed End.X SID static configuration.'
                              ;
                  presence 'func code'
                           ;
                  list compressed-sid {
                    description 'Compress End.X SID static configuration.'
                                ;
                    key func-code ;
                    leaf func-code {
                      description 'The function code of End.X SID.'
                                  ;
                      type ncd:ipv6-address ;
                    }
                    choice neighbor {
                      description 'The information of neighbor associated with '
                                + 'End.X SID.'
                                  ;
                      mandatory true ;
                      case interface {
                        description 'The branch of interface associated with En'
                                  + 'd.X SID.'
                                    ;
                        container interface {
                          description 'The information of interface associated '
                                    + 'with End.X SID.'
                                      ;
                          leaf interface-name {
                            description 'The name of interface associated with End.X SID.'
                                        ;
                            type ncd:ifname ;
                            mandatory true ;
                          }
                        }
                      }
                      case router-id {
                        description 'The branch of router-id associated with En'
                                  + 'd.X SID.'
                                    ;
                        container router-id {
                          description 'The information of router-id associated '
                                    + 'with End.X SID.'
                                      ;
                          leaf interface-name {
                            description 'The name of interface associated with End.X SID.'
                                        ;
                            type ncd:ifname ;
                            mandatory true ;
                          }
                          leaf router-id {
                            description 'The IPv6 router-id of neighbor associated with End.X SID.'
                                        ;
                            type ncd:ipv6-address ;
                            mandatory true ;
                          }
                        }
                      }
                      case system-id {
                        description 'The branch of system-id associated with En'
                                  + 'd.X SID.'
                                    ;
                        container system-id {
                          description 'The information of system-id associated '
                                    + 'with End.X SID.'
                                      ;
                          leaf interface-name {
                            description 'The name of interface associated with End.X SID.'
                                        ;
                            type ncd:ifname ;
                            mandatory true ;
                          }
                          leaf system-id {
                            description 'The system-id of neighbor associated with End.X SID.'
                                        ;
                            type ncd:mac-address ;
                            mandatory true ;
                          }
                        }
                      }
                    }
                    leaf encapsulation-type {
                      description 'The encapsulation type attribute of End.X SI'
                                + 'D.'
                                  ;
                      type enumeration {
                        enum uet-128 {
                          value 0 ;
                        }
                        enum uet-32 {
                          value 1 ;
                        }
                      }
                      default uet-128 ;
                    }
                    leaf psp {
                      description 'The psp attribute of End.X SID.'
                                  ;
                      type isis-state ;
                      mandatory true ;
                    }
                    leaf usp {
                      description 'The usp attribute of End.X SID.'
                                  ;
                      type isis-state ;
                      mandatory true ;
                    }
                  }
                }
                container sids {
                  description 'End.X SID static configuration.'
                              ;
                  presence 'func code'
                           ;
                  list sid {
                    description 'End.X SID static configuration.'
                                ;
                    key func-code ;
                    leaf func-code {
                      description 'The function code of End.X SID.'
                                  ;
                      type ncd:ipv6-address ;
                    }
                    choice neighbor {
                      description 'The information of neighbor associated with '
                                + 'End.X SID.'
                                  ;
                      mandatory true ;
                      case interface {
                        description 'The branch of interface associated with En'
                                  + 'd.X SID.'
                                    ;
                        container interface {
                          description 'The information of interface associated '
                                    + 'with End.X SID.'
                                      ;
                          leaf interface-name {
                            description 'The name of interface associated with End.X SID.'
                                        ;
                            type ncd:ifname ;
                            mandatory true ;
                          }
                        }
                      }
                      case router-id {
                        description 'The branch of router-id associated with En'
                                  + 'd.X SID.'
                                    ;
                        container router-id {
                          description 'The information of router-id associated '
                                    + 'with End.X SID.'
                                      ;
                          leaf interface-name {
                            description 'The name of interface associated with End.X SID.'
                                        ;
                            type ncd:ifname ;
                            mandatory true ;
                          }
                          leaf router-id {
                            description 'The IPv6 router-id of neighbor associated with End.X SID.'
                                        ;
                            type ncd:ipv6-address ;
                            mandatory true ;
                          }
                        }
                      }
                      case system-id {
                        description 'The branch of system-id associated with En'
                                  + 'd.X SID.'
                                    ;
                        container system-id {
                          description 'The information of system-id associated '
                                    + 'with End.X SID.'
                                      ;
                          leaf interface-name {
                            description 'The name of interface associated with End.X SID.'
                                        ;
                            type ncd:ifname ;
                            mandatory true ;
                          }
                          leaf system-id {
                            description 'The system-id of neighbor associated with End.X SID.'
                                        ;
                            type ncd:mac-address ;
                            mandatory true ;
                          }
                        }
                      }
                    }
                    leaf psp {
                      description 'The psp attribute of End.X SID.'
                                  ;
                      type isis-state ;
                      mandatory true ;
                    }
                    leaf usp {
                      description 'The usp attribute of End.X SID.'
                                  ;
                      type isis-state ;
                      mandatory true ;
                    }
                  }
                }
              }
            }
            ncd:revise-date 2021-03-30 ;
          }
          container ipv4-summary-policys {
            description 'ISIS IPv4 route summary policy configuration.'
                        ;
            list ipv4-summary-policy {
              description 'ISIS IPv4 route summary policy configuration.'
                          ;
              key policy-type ;
              leaf policy-type {
                description 'ISIS IPv4 route summary policy type configuration.'
                            ;
                type enumeration {
                  enum exclude-local-prefix {
                    value 1 ;
                    description 'Exclude ipv4 prefix of local interface.'
                                ;
                  }
                }
              }
              leaf level {
                description 'Level(s) will be effected on.'
                            ;
                type isis-level ;
                mandatory true ;
              }
            }
            ncd:revise-date 2021-04-21 ;
          }
          container ipv6-summary-policys {
            description 'ISIS IPv6 route summary policy configuration.'
                        ;
            list ipv6-summary-policy {
              description 'ISIS IPv6 route summary policy configuration.'
                          ;
              key policy-type ;
              leaf policy-type {
                description 'ISIS IPv6 route summary policy type configuration.'
                            ;
                type enumeration {
                  enum exclude-local-prefix {
                    value 1 ;
                    description 'Exclude ipv4 prefix of local interface.'
                                ;
                  }
                }
              }
              leaf level {
                description 'Level(s) will be effected on.'
                            ;
                type isis-level ;
                mandatory true ;
              }
            }
            ncd:revise-date 2021-04-21 ;
          }
        }
      }
    }
    container global-config {
      description 'Route ISIS global config.'
                  ;
      leaf p2p-comply-level-2 {
        description 'Comply P2P hello level-2 config.'
                    ;
        type isis-state ;
        default disable ;
      }
      leaf ipv4-external-prefix-calculate-low-preference {
        description 'Set IS-IS IPv4 external-prefix as low-preference when calc'
                  + 'ulate'
                    ;
        type isis-state ;
        default disable ;
        ncd:revise-date 2021-02-05 ;
      }
      leaf ipv6-external-prefix-calculate-low-preference {
        description 'Set IS-IS IPv6 external-prefix as low-preference when calc'
                  + 'ulate'
                    ;
        type isis-state ;
        default disable ;
        ncd:revise-date 2021-02-05 ;
      }
      ncd:revise-date 2020-07-09 ;
    }
  }
  container state {
    config false ;
    container route-isis {
      description 'Route isis.'
                  ;
      container isis-adjacencies {
        description 'The information of ISIS adjacency.'
                    ;
        list isis-adjacency {
          description 'The information of ISIS adjacency.'
                      ;
          key 'adj-process-id adj-intf-name adj-level adj-system-id adj-snpa-ad'
            + 'dr'
              ;
          leaf adj-process-id {
            description 'Process ID which adjacency belongs to.'
                        ;
            type uint32 {
              range 0..65535 ;
            }
          }
          leaf adj-intf-name {
            description 'The interface name of ISIS adjacency.'
                        ;
            type string {
              length 0..32 ;
            }
          }
          leaf adj-level {
            description "Adjacency's level."
                        ;
            type uint8 {
              range 1..2 ;
            }
          }
          leaf adj-system-id {
            description 'Adjacent system-ID'
                        ;
            type ncd:mac-address ;
          }
          leaf adj-snpa-addr {
            description 'Adjacent SNPA address.'
                        ;
            type ncd:string-all {
              length 1..14 {
                description 'The SNPA of isis adjacency.'
                            ;
              }
            }
          }
          leaf adj-state {
            description 'Adjacent state.'
                        ;
            type ncd:string-all {
              length 1..4 {
                description 'The state of isis adjacency.'
                            ;
              }
            }
          }
          leaf adj-hold-time {
            description 'Holding time of ISIS adjacency.'
                        ;
            type uint16 {
              range 0..65535 {
                description 'Hold-time of isis adjacency.'
                            ;
              }
            }
          }
          leaf adj-priority {
            description 'Priority of ISIS adjacency.'
                        ;
            type uint8 {
              range 0..127 {
                description 'The priority of isis adjacency.'
                            ;
              }
            }
          }
          leaf adj-mt-flag {
            description 'The multi-toplogy flag of isis adjacency'
                        ;
            type uint8 {
              range 0..1 {
                description 'The multi-toplogy flag of isis adjacency.'
                            ;
              }
            }
          }
          leaf adj-system-type {
            description "Adjacency's system type."
                        ;
            type isis-level ;
          }
          leaf adj-extended-circ-id {
            description "Adjacency's extended circuit id."
                        ;
            type uint32 ;
          }
          leaf adj-vrf-name {
            description "Adjacency's VRF name."
                        ;
            type string {
              length 1..32 ;
            }
            ncd:revise-date 2015-04-02 ;
          }
          leaf adj-id {
            description 'The ID of adjacency.'
                        ;
            type string {
              length 28 ;
            }
            ncd:revise-date 2018-09-11 ;
          }
          leaf adj-3way-state {
            description 'This is the 3way-state of ISIS adjacency, when the typ'
                      + 'e of network is point-to-point(it is zero ,when networ'
                      + 'k is not point-to-point).'
                        ;
            type uint8 {
              range 0..2 {
                description 'The range of 3way-state is from 0 to 2.'
                            ;
              }
            }
            ncd:revise-date 2018-09-11 ;
          }
          leaf adj-last-uptime {
            description 'This is the time interval since the last adjacency was'
                      + ' established.'
                        ;
            type uint32 {
              range 0..4294967295 {
                description 'This is the time interval since the last adjacency'
                          + ' was established.'
                            ;
              }
            }
            ncd:revise-date 2018-09-11 ;
          }
          ncd:select adj-process-id ;
          ncd:select adj-intf-name ;
          ncd:select adj-level ;
          ncd:select 'adj-process-id adj-intf-name'
                     ;
          ncd:select 'adj-process-id adj-intf-name adj-level'
                     ;
          ncd:select 'adj-process-id adj-level'
                     ;
          ncd:select 'adj-intf-name adj-level'
                     ;
          ncd:select 'adj-process-id adj-intf-name adj-level adj-system-id'
                     ;
          ncd:select 'adj-process-id adj-intf-name adj-level adj-snpa-addr'
                     ;
          ncd:select 'adj-process-id adj-intf-name adj-level adj-system-id adj-'
                   + 'snpa-addr'
                     ;
        }
      }
      container isis-circuits {
        description 'The information of ISIS circuits.'
                    ;
        list isis-circuit {
          description 'The information of ISIS circuits.'
                      ;
          key 'circuit-process-id circuit-name'
              ;
          leaf circuit-process-id {
            description 'Process ID which the circuit belongs to.'
                        ;
            type uint32 {
              range 0..65535 ;
            }
          }
          leaf circuit-name {
            description 'The name of the circuit.'
                        ;
            type ncd:string-all {
              length 1..32 {
                description 'ISIS interface name.'
                            ;
              }
            }
          }
          leaf circuit-type {
            description 'The type of the circuit.'
                        ;
            type enumeration {
              enum L1 {
                value 1 ;
              }
              enum L2 {
                value 2 ;
              }
              enum L1L2 {
                value 3 ;
              }
            }
          }
          leaf circuit-state {
            description 'The state of the circuit.'
                        ;
            type ncd:string-all {
              length 1..7 {
                description 'The state of ISIS interface.'
                            ;
              }
            }
          }
          leaf circuit-id {
            description 'The ID of the circuit'
                        ;
            type uint8 {
              range 0..255 {
                description 'Circuit id of the isis circuit.'
                            ;
              }
            }
          }
          leaf circuit-l1-dr {
            description 'The level-1 DR information of circuit.'
                        ;
            type ncd:string-all {
              length 1..17 {
                description 'The flag of level-1 designated router of the isis '
                          + 'circuit.'
                            ;
              }
            }
          }
          leaf circuit-l2-dr {
            description 'The level-2 DR information of circuit.'
                        ;
            type ncd:string-all {
              length 1..17 {
                description 'The flag of level-2 designated router of the isis '
                          + 'circuit.'
                            ;
              }
            }
          }
          leaf circuit-l1-priority {
            description 'Priority of the ISIS level-1 circuit.'
                        ;
            type uint8 {
              range 0..127 {
                description "Range of circuit's priority."
                            ;
              }
            }
          }
          leaf circuit-l2-priority {
            description 'Priority of the ISIS level-2 circuit.'
                        ;
            type uint8 {
              range 0..127 {
                description "Range of circuit's priority."
                            ;
              }
            }
          }
          ncd:select circuit-process-id ;
          ncd:select circuit-name ;
          ncd:select 'circuit-process-id circuit-name'
                     ;
        }
      }
      container isis-peer-routerids {
        description 'The informance of the remote router id'
                    ;
        list isis-peer-routerid {
          description 'The informance of the remote router id'
                      ;
          key 'process-id level peer-system-id'
              ;
          leaf process-id {
            description 'The process ID of the local ISIS instance'
                        ;
            type uint32 {
              range 0..65535 ;
            }
          }
          leaf instance-type {
            description 'The type of the local ISIS instance'
                        ;
            type uint8 {
              range 0..1 ;
            }
          }
          leaf vrf-name {
            description 'The vrf name of the local ISIS instance'
                        ;
            type string {
              length 0..32 ;
            }
          }
          leaf system-id {
            description 'The system id of the local ISIS instance'
                        ;
            type ncd:mac-address ;
          }
          leaf level {
            description 'The level of the remote router-id'
                        ;
            type uint8 {
              range 1..2 ;
            }
          }
          leaf peer-system-id {
            description 'The system id of the remote ISIS instance'
                        ;
            type ncd:mac-address ;
          }
          leaf peer-name {
            description 'The name of the remote ISIS'
                        ;
            type string {
              length 0..254 ;
            }
          }
          leaf peer-routerid {
            description 'The router id of the remote ISIS instance'
                        ;
            type ncd:ipv4-address ;
          }
          ncd:select process-id ;
          ncd:select level ;
          ncd:select peer-system-id ;
          ncd:select 'process-id level'
                     ;
          ncd:select 'process-id peer-system-id'
                     ;
          ncd:select 'level peer-system-id'
                     ;
          ncd:select 'process-id level peer-system-id'
                     ;
        }
        ncd:revise-date 2018-09-11 ;
      }
    }
  }
}
