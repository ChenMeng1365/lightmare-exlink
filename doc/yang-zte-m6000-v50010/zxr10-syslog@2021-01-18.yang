module zxr10-syslog {
  namespace 'http://www.zte.com.cn/zxr10/netconf/schema/rosng/syslog'
            ;
  prefix syslog ;
  yang-version 1 ;
  import zxr10-netconf-defs {
    prefix ncd ;
  }
  organization 'ZTE Corporation'
               ;
  contact 'ZTE Corporation '+"\n"
        + '         Nanjing Institute of ZTE Corporation'+"\n"
        + '         No.68 Zijinghua Rd. Yuhuatai District, Nanjing, China'+"\n"
        + '         Tel: +86-25-52870000'
          ;
  description 'This module describes the netconf model about syslog.'
              ;
  revision 2021-01-18 {
    description '1. Add traplog type to syslog-server host.'
                ;
  }
  revision 2020-07-28 {
    description "(1)Add list '/configuration/syslog-server/tcp-hosts-vrf/ipv4-v"
              + "rf/ipv4'.
\n(2)Add list '/configuration/syslog-server/tcp-host"
              + "s-vrf/ipv6-linklocal-vrf/ipv6-linklocal'.
\n(3)Add list '/conf"
              + "iguration/syslog-server/tcp-hosts-vrf/ipv6-non-linklocal-vrf/i"
              + "pv6-non-linklocal'.
\n(4)Add list '/configuration/syslog-serve"
              + "r/tcp-hosts/ipv4-type/ipv4'.
\n(5)Add list '/configuration/sys"
              + "log-server/tcp-hosts/ipv6-linklocal-type/ipv6-linklocal'.
\n(6"
              + ")Add list '/configuration/syslog-server/tcp-hosts/ipv6-non-lin"
              + "klocal-type/ipv6-non-linklocal'."
                ;
  }
  revision 2020-05-21 {
    description '1.Add syslog format.'
                ;
  }
  revision 2018-12-26 {
    description '1. Add weblog type to syslog-server host.'
                ;
  }
  revision 2018-06-28 {
    description '1.Obsolete the leaf /syslog-server/sources/ipv4/ipv4-address,/'
              + 'syslog-server/sources/ipv6/ipv6-address and /syslog-server/sou'
              + 'rces/interface/interface-name.'+"\n"
              + '2.Delete the filter of the container /syslog-server/sources/ip'
              + 'v4,/syslog-server/sources/ipv6 and /syslog-server/sources/inte'
              + 'rface.'+"\n"
              + '3.Add the listleaf /syslog-server/sources/ipv4/ipv4-addr,/sysl'
              + 'og-server/sources/ipv6/ipv6-addr and /syslog-server/sources/in'
              + 'terface/if-name.'
                ;
  }
  revision 2018-01-04 {
    description '1.Add leaf src-ipv4 and src-ipv6 for syslog host.'
                ;
  }
  revision 2017-07-28 {
    description '1. Add snmplog type to syslog-server host.'
                ;
  }
  revision 2017-06-05 {
    description '1.Modify the interface filter of syslog-server source.'
                ;
  }
  revision 2017-03-03 {
    description '1. Add haglog type to syslog-server host.'
                ;
  }
  revision 2016-02-23 {
    description '1. Add netconflog type to syslog-server host.'
                ;
  }
  revision 2016-02-01 {
    description "(1)Add leaf node 'nat-translationlog' 'nat-portrangelog' to '/"
              + "configuration/syslog-server/hosts-vrf/ipv4-vrf/ipv4'.
\n(2)Add"
              + " leaf node 'nat-translationlog' 'nat-portrangelog' to '/config"
              + "uration/syslog-server/hosts-vrf/ipv6-linklocal-vrf/ipv6-linklo"
              + "cal'.
\n(3)Add leaf node 'nat-translationlog' 'nat-portrangelo"
              + "g' to '/configuration/syslog-server/hosts-vrf/ipv6-non-linkloc"
              + "al-vrf/ipv6-non-linklocal'.
\n(4)Add leaf node 'nat-translatio"
              + "nlog' 'nat-portrangelog' to '/configuration/syslog-server/host"
              + "s/ipv4-type/ipv4'.
\n(5)Add leaf node 'nat-translationlog' 'na"
              + "t-portrangelog' to '/configuration/syslog-server/hosts/ipv6-li"
              + "nklocal-type/ipv6-linklocal'.
\n(6)Add leaf node 'nat-translat"
              + "ionlog' 'nat-portrangelog' to '/configuration/syslog-server/ho"
              + "sts/ipv6-non-linklocal-type/ipv6-non-linklocal'."
                ;
  }
  revision 2015-05-18 {
    description "Modify 'interface-name' minimal length form 0 to 1. Add 'inter"
              + "face-name' to 'filter-nodes'."
                ;
  }
  revision 2015-04-20 {
    description "Add feature node 'syslog-souce-interface' and apply the featur"
              + "eto leaf of interface-name."
                ;
  }
  revision 2015-04-15 {
    description 'Add project info to urllog-syslog feature.'
                ;
  }
  revision 2015-02-11 {
    description "(1)Add default value to '/configuration/syslog-server/hosts-vr"
              + "f/ipv4-vrf/ipv4/urllog'.
\n(2)Add default value to '/configura"
              + "tion/syslog-server/hosts-vrf/ipv6-linklocal-vrf/ipv6-linklocal"
              + "/urllog'.
\n(3)Add default value to '/configuration/syslog-ser"
              + "ver/hosts-vrf/ipv6-non-linklocal-vrf/ipv6-non-linklocal/urllog"
              + "'.
\n(4)Add default value to '/configuration/syslog-server/hos"
              + "ts/ipv4-type/ipv4/urllog'.
\n(5)Add default value to '/configu"
              + "ration/syslog-server/hosts/ipv6-linklocal-type/ipv6-linklocal/"
              + "urllog'.
\n(6)Add default value to '/configuration/syslog-serv"
              + "er/hosts/ipv6-non-linklocal-type/ipv6-non-linklocal/urllog'."
                ;
  }
  revision 2014-07-08 {
    description "(1)Add the leaf 'urllog''/configuration/syslog-server/hosts-vr"
              + "f/ipv4-vrf/ipv4/urllog'.
\n(2)Add the leaf 'urllog''/configura"
              + "tion/syslog-server/hosts-vrf/ipv6-linklocal-vrf/ipv6-linklocal"
              + "/urllog'.
\n(3)Add the leaf 'urllog''/configuration/syslog-ser"
              + "ver/hosts-vrf/ipv6-non-linklocal-vrf/ipv6-non-linklocal/urllog"
              + "'.
\n(4)Add the leaf 'urllog''/configuration/syslog-server/hos"
              + "ts/ipv4-type/ipv4/urllog'.
\n(5)Add the leaf 'urllog''/configu"
              + "ration/syslog-server/hosts/ipv6-linklocal-type/ipv6-linklocal/"
              + "urllog'.
\n(6)Add the leaf 'urllog''/configuration/syslog-serv"
              + "er/hosts/ipv6-non-linklocal-type/ipv6-non-linklocal/urllog'."
                ;
  }
  revision 2014-05-13 {
    description "Modify the pattern of the leaf 'link-local-ipv6' of address."
                ;
  }
  revision 2014-04-22 {
    description 'Initial revision.'
                ;
  }
  feature urllog-syslog {
    description 'send URL log to syslog.'
                ;
  }
  feature syslog-source-interface {
    description 'syslog source interface feature.'
                ;
  }
  feature syslog-format {
    description '1.Syslog format.'
                ;
  }
  feature syslog-tcp {
    description 'SYSLOG TCP.'
                ;
  }
  typedef alarm-level {
    type enumeration {
      enum emergencies {
        value 1 ;
        description 'Level of emergency.'
                    ;
      }
      enum alerts {
        value 2 ;
        description 'Level of alert.'
                    ;
      }
      enum critical {
        value 3 ;
        description 'Level of  critical.'
                    ;
      }
      enum errors {
        value 4 ;
        description 'Level of error.'
                    ;
      }
      enum warnings {
        value 5 ;
        description 'Level of warning.'
                    ;
      }
      enum notifications {
        value 6 ;
        description 'Level of notification.'
                    ;
      }
      enum informational {
        value 7 ;
        description 'Level of information.'
                    ;
      }
      enum debugging {
        value 8 ;
        description 'Level of debug.'
                    ;
      }
    }
    default notifications ;
    description 'Alarm level.'
                ;
  }
  typedef syslog-facility {
    type enumeration {
      enum kern {
        value 0 ;
        description Kernel. ;
      }
      enum user {
        value 1 ;
        description 'User process.'
                    ;
      }
      enum mail {
        value 2 ;
        description 'Mail system.'
                    ;
      }
      enum daemon {
        value 3 ;
        description 'System daemons.'
                    ;
      }
      enum auth1 {
        value 4 ;
        description 'Authorization system.'
                    ;
      }
      enum syslog {
        value 5 ;
        description 'Syslog itself.'
                    ;
      }
      enum lpr {
        value 6 ;
        description 'Line printer system.'
                    ;
      }
      enum news {
        value 7 ;
        description 'USENET news.'
                    ;
      }
      enum uucp {
        value 8 ;
        description 'Unix-to-Unix copy system.'
                    ;
      }
      enum clock1 {
        value 9 ;
        description 'Clock process.'
                    ;
      }
      enum auth2 {
        value 10 ;
        description 'Authorization system.'
                    ;
      }
      enum ftp {
        value 11 ;
        description 'FTP process.'
                    ;
      }
      enum ntp {
        value 12 ;
        description 'NTP process.'
                    ;
      }
      enum log-audit {
        value 13 ;
        description 'Log audit.'
                    ;
      }
      enum log-alert {
        value 14 ;
        description 'Log alert.'
                    ;
      }
      enum clock2 {
        value 15 ;
        description 'Clock daemons.'
                    ;
      }
      enum local0 {
        value 16 ;
        description 'Local use.'
                    ;
      }
      enum local1 {
        value 17 ;
        description 'Local use.'
                    ;
      }
      enum local2 {
        value 18 ;
        description 'Local use.'
                    ;
      }
      enum local3 {
        value 19 ;
        description 'Local use.'
                    ;
      }
      enum local4 {
        value 20 ;
        description 'Local use.'
                    ;
      }
      enum local5 {
        value 21 ;
        description 'Local use.'
                    ;
      }
      enum local6 {
        value 22 ;
        description 'Local use.'
                    ;
      }
      enum local7 {
        value 23 ;
        description 'Local use.'
                    ;
      }
    }
    default local0 ;
    description 'Syslog facility.'
                ;
  }
  typedef syslog-log-switch {
    type enumeration {
      enum off {
        value 0 ;
        description 'Do not send log to syslog server.'
                    ;
      }
      enum on {
        value 1 ;
        description 'Send log to syslog server.'
                    ;
      }
    }
    description 'Swtich to send log to syslog server.'
                ;
  }
  typedef syslog-format {
    type enumeration {
      enum rfc3164 {
        value 1 ;
        description RFC3164. ;
      }
      enum rfc3164-with-tag {
        value 2 ;
        description 'RFC3164 with TAG.'
                    ;
      }
      enum rfc5424 {
        value 3 ;
        description RFC5424. ;
      }
    }
    default rfc3164 ;
    description 'Syslog format.'
                ;
  }
  container configuration {
    description 'Configuration info.'
                ;
    container syslog-server {
      description 'Specify syslog-server.'
                  ;
      container sources {
        description 'Specify source address in syslog transactions.'
                    ;
        container ipv4 {
          description 'Specify IPv4 source address.'
                      ;
          presence ipv4 ;
          leaf ipv4-address {
            status obsolete {
              ncd:revise-date 2018-06-28 ;
            }
            description 'IPv4 address.'
                        ;
            type ncd:ipv4-address ;
          }
          leaf-list ipv4-addr {
            description 'IPv4 address.'
                        ;
            type ncd:ipv4-address ;
            max-elements 1 ;
            ncd:revise-date 2018-06-28 ;
          }
        }
        container ipv6 {
          description 'Specify IPv6 source address.'
                      ;
          presence ipv6 ;
          leaf ipv6-address {
            status obsolete {
              ncd:revise-date 2018-06-28 ;
            }
            description 'IPv6 address.'
                        ;
            type ncd:ipv6-address ;
          }
          leaf-list ipv6-addr {
            description 'IPv6 address.'
                        ;
            type ncd:ipv6-address ;
            max-elements 1 ;
            ncd:revise-date 2018-06-28 ;
          }
        }
        container interface {
          description 'Specify the name of the interface.'
                      ;
          presence interface ;
          leaf interface-name {
            // if-feature syslog-source-interface ;
            status obsolete {
              ncd:revise-date 2018-06-28 ;
            }
            description 'Interface name.'
                        ;
            type ncd:ifname {
              length 0..31 ;
            }
          }
          leaf-list if-name {
            // if-feature syslog-source-interface ;
            description 'Interface name.'
                        ;
            type ncd:ifname ;
            max-elements 1 ;
            ncd:revise-date 2018-06-28 ;
          }
        }
      }
      container hosts-vrf {
        description 'Specify syslog-server host with vrf.'
                    ;
        container ipv4-vrf {
          description 'Specify syslog-server host of ipv4 with vrf.'
                      ;
          list ipv4 {
            description 'Specify syslog-server host of ipv4.'
                        ;
            key 'vrf-name ipv4-address'
                ;
            leaf vrf-name {
              description 'VPN routing/forwarding instance (VRF) name.'
                          ;
              type string {
                length 1..32 ;
              }
            }
            leaf ipv4-address {
              description 'IPv4 address.'
                          ;
              type ncd:ipv4-address ;
            }
            leaf src-ipv4 {
              description 'Source IPv4 address.'
                          ;
              type ncd:ipv4-address-none-zero ;
              ncd:revise-date 2018-01-04 ;
            }
            leaf fport {
              description 'The remote port.'
                          ;
              type uint16 {
                range 1..65535 ;
              }
              default 514 ;
            }
            leaf lport {
              description 'The local port.'
                          ;
              type uint16 {
                range '514 | 1024..65535'
                      ;
              }
              default 514 ;
            }
            leaf alarmlog {
              description 'Send alarm log to syslog server.'
                          ;
              type syslog-log-switch ;
              default off ;
            }
            leaf debugmsg {
              description 'Send debug message to syslog server.'
                          ;
              type syslog-log-switch ;
              default off ;
            }
            leaf cmdlog {
              description 'Send command log to syslog server.'
                          ;
              type syslog-log-switch ;
              default off ;
            }
            leaf servicelog {
              description 'Send service log to syslog server.'
                          ;
              type syslog-log-switch ;
              default off ;
            }
            leaf netconflog {
              description 'Send NETCONF log to syslog server.'
                          ;
              type syslog-log-switch ;
              default off ;
              ncd:revise-date 2016-02-23 ;
            }
            leaf braslog {
              description 'Send bras log to syslog server.'
                          ;
              type syslog-log-switch ;
              default off ;
            }
            leaf natlog {
              description 'Send NAT log to syslog server.'
                          ;
              type syslog-log-switch ;
              default off ;
            }
            leaf urllog {
              // if-feature urllog-syslog ;
              description 'Send URL log to syslog server.'
                          ;
              type syslog-log-switch ;
              default off ;
            }
            leaf nat-translationlog {
              // if-feature urllog-syslog ;
              description 'Send NAT translation log to syslog server.'
                          ;
              type syslog-log-switch ;
              default off ;
              ncd:revise-date 2016-02-01 ;
            }
            leaf nat-portrangelog {
              // if-feature urllog-syslog ;
              description 'Send NAT portrange log to syslog server.'
                          ;
              type syslog-log-switch ;
              default off ;
              ncd:revise-date 2016-02-01 ;
            }
            leaf haglog {
              // if-feature urllog-syslog ;
              description 'Send Hybrid Access Gateway log to syslog server.'
                          ;
              type syslog-log-switch ;
              default off ;
              ncd:revise-date 2017-03-03 ;
            }
            leaf snmplog {
              description 'Send SNMP log to syslog server.'
                          ;
              type syslog-log-switch ;
              default off ;
              ncd:revise-date 2017-07-28 ;
            }
            leaf weblog {
              description 'Send WEB log to syslog server.'
                          ;
              type syslog-log-switch ;
              default off ;
              ncd:revise-date 2018-12-26 ;
            }
            leaf traplog {
              description 'Send TRAP log to syslog server.'
                          ;
              type syslog-log-switch ;
              default off ;
              ncd:revise-date 2021-01-18 ;
            }
          }
        }
        container ipv6-linklocal-vrf {
          description 'Specify syslog-server host of IPv6(linklocal) with vrf.'
                      ;
          list ipv6-linklocal {
            description 'Specify syslog-server host of IPv6 with linklocal.'
                        ;
            key 'vrf-name ipv6-address interface-name'
                ;
            leaf vrf-name {
              description 'VPN routing/forwarding instance (VRF) name.'
                          ;
              type string {
                length 1..32 ;
              }
            }
            leaf ipv6-address {
              description 'IPv6 address.'
                          ;
              type ncd:ipv6-address {
                pattern '^[Ff][Ee][8-9a-bA-B][0-9a-fA-F]'
                        ;
              }
            }
            leaf interface-name {
              description 'Interface name.'
                          ;
              type ncd:ifname {
                length 1..31 ;
              }
            }
            container src-ip {
              description 'Source IPv6 address.'
                          ;
              leaf src-ipv6 {
                description 'Source IPv6 address.'
                            ;
                type ncd:ipv6-address ;
              }
              ncd:revise-date 2018-01-04 ;
            }
            leaf fport {
              description 'The remote port.'
                          ;
              type uint16 {
                range 1..65535 ;
              }
              default 514 ;
            }
            leaf lport {
              description 'The local port.'
                          ;
              type uint16 {
                range '514 | 1024..65535'
                      ;
              }
              default 514 ;
            }
            leaf alarmlog {
              description 'Send alarm log to syslog server.'
                          ;
              type syslog-log-switch ;
              default off ;
            }
            leaf debugmsg {
              description 'Send debug message to syslog server.'
                          ;
              type syslog-log-switch ;
              default off ;
            }
            leaf cmdlog {
              description 'Send command log to syslog server.'
                          ;
              type syslog-log-switch ;
              default off ;
            }
            leaf servicelog {
              description 'Send service log to syslog server.'
                          ;
              type syslog-log-switch ;
              default off ;
            }
            leaf netconflog {
              description 'Send NETCONF log to syslog server.'
                          ;
              type syslog-log-switch ;
              default off ;
              ncd:revise-date 2016-02-23 ;
            }
            leaf braslog {
              description 'Send bras log to syslog server.'
                          ;
              type syslog-log-switch ;
              default off ;
            }
            leaf natlog {
              description 'Send NAT log to syslog server.'
                          ;
              type syslog-log-switch ;
              default off ;
            }
            leaf urllog {
              // if-feature urllog-syslog ;
              description 'Send URL log to syslog server.'
                          ;
              type syslog-log-switch ;
              default off ;
            }
            leaf nat-translationlog {
              // if-feature urllog-syslog ;
              description 'Send NAT translation log to syslog server.'
                          ;
              type syslog-log-switch ;
              default off ;
              ncd:revise-date 2016-02-01 ;
            }
            leaf nat-portrangelog {
              // if-feature urllog-syslog ;
              description 'Send NAT portrange log to syslog server.'
                          ;
              type syslog-log-switch ;
              default off ;
              ncd:revise-date 2016-02-01 ;
            }
            leaf haglog {
              // if-feature urllog-syslog ;
              description 'Send Hybrid Access Gateway log to syslog server.'
                          ;
              type syslog-log-switch ;
              default off ;
              ncd:revise-date 2017-03-03 ;
            }
            leaf snmplog {
              description 'Send SNMP log to syslog server.'
                          ;
              type syslog-log-switch ;
              default off ;
              ncd:revise-date 2017-07-28 ;
            }
            leaf weblog {
              description 'Send WEB log to syslog server.'
                          ;
              type syslog-log-switch ;
              default off ;
              ncd:revise-date 2018-12-26 ;
            }
            leaf traplog {
              description 'Send TRAP log to syslog server.'
                          ;
              type syslog-log-switch ;
              default off ;
              ncd:revise-date 2021-01-18 ;
            }
          }
        }
        container ipv6-non-linklocal-vrf {
          description 'Specify syslog-server host of IPv6 with vrf.'
                      ;
          list ipv6-non-linklocal {
            description 'Specify syslog-server host of IPv6 without linklocal.'
                        ;
            key 'vrf-name ipv6-address'
                ;
            leaf vrf-name {
              description 'VPN routing/forwarding instance (VRF) name.'
                          ;
              type string {
                length 1..32 ;
              }
            }
            leaf ipv6-address {
              description 'IPv6 address.'
                          ;
              type ncd:ipv6-address ;
            }
            container src-ip {
              description 'Source IPv6 address.'
                          ;
              leaf src-ipv6 {
                description 'Source IPv6 address.'
                            ;
                type ncd:ipv6-address ;
              }
              ncd:revise-date 2018-01-04 ;
            }
            leaf fport {
              description 'The remote port.'
                          ;
              type uint16 {
                range 1..65535 ;
              }
              default 514 ;
            }
            leaf lport {
              description 'The local port.'
                          ;
              type uint16 {
                range '514 | 1024..65535'
                      ;
              }
              default 514 ;
            }
            leaf alarmlog {
              description 'Send alarm log to syslog server.'
                          ;
              type syslog-log-switch ;
              default off ;
            }
            leaf debugmsg {
              description 'Send debug message to syslog server.'
                          ;
              type syslog-log-switch ;
              default off ;
            }
            leaf cmdlog {
              description 'Send command log to syslog server.'
                          ;
              type syslog-log-switch ;
              default off ;
            }
            leaf servicelog {
              description 'Send service log to syslog server.'
                          ;
              type syslog-log-switch ;
              default off ;
            }
            leaf netconflog {
              description 'Send NETCONF log to syslog server.'
                          ;
              type syslog-log-switch ;
              default off ;
              ncd:revise-date 2016-02-23 ;
            }
            leaf braslog {
              description 'Send bras log to syslog server.'
                          ;
              type syslog-log-switch ;
              default off ;
            }
            leaf natlog {
              description 'Send NAT log to syslog server.'
                          ;
              type syslog-log-switch ;
              default off ;
            }
            leaf urllog {
              // if-feature urllog-syslog ;
              description 'Send URL log to syslog server.'
                          ;
              type syslog-log-switch ;
              default off ;
            }
            leaf nat-translationlog {
              // if-feature urllog-syslog ;
              description 'Send NAT translation log to syslog server.'
                          ;
              type syslog-log-switch ;
              default off ;
              ncd:revise-date 2016-02-01 ;
            }
            leaf nat-portrangelog {
              // if-feature urllog-syslog ;
              description 'Send NAT portrange log to syslog server.'
                          ;
              type syslog-log-switch ;
              default off ;
              ncd:revise-date 2016-02-01 ;
            }
            leaf haglog {
              // if-feature urllog-syslog ;
              description 'Send Hybrid Access Gateway log to syslog server.'
                          ;
              type syslog-log-switch ;
              default off ;
              ncd:revise-date 2017-03-03 ;
            }
            leaf snmplog {
              description 'Send SNMP log to syslog server.'
                          ;
              type syslog-log-switch ;
              default off ;
              ncd:revise-date 2017-07-28 ;
            }
            leaf weblog {
              description 'Send WEB log to syslog server.'
                          ;
              type syslog-log-switch ;
              default off ;
              ncd:revise-date 2018-12-26 ;
            }
            leaf traplog {
              description 'Send TRAP log to syslog server.'
                          ;
              type syslog-log-switch ;
              default off ;
              ncd:revise-date 2021-01-18 ;
            }
          }
        }
      }
      container hosts {
        description 'Specify syslog-server host.'
                    ;
        container ipv4-type {
          description 'Specify syslog-server host of ipv4.'
                      ;
          list ipv4 {
            description 'Specify syslog-server host of ipv4.'
                        ;
            key ipv4-address ;
            leaf ipv4-address {
              description 'IPv4 address.'
                          ;
              type ncd:ipv4-address ;
            }
            leaf src-ipv4 {
              description 'Source IPv4 address.'
                          ;
              type ncd:ipv4-address-none-zero ;
              ncd:revise-date 2018-01-04 ;
            }
            leaf fport {
              description 'The remote port.'
                          ;
              type uint16 {
                range 1..65535 ;
              }
              default 514 ;
            }
            leaf lport {
              description 'The local port.'
                          ;
              type uint16 {
                range '514 | 1024..65535'
                      ;
              }
              default 514 ;
            }
            leaf alarmlog {
              description 'Send alarm log to syslog server.'
                          ;
              type syslog-log-switch ;
              default off ;
            }
            leaf debugmsg {
              description 'Send debug message to syslog server.'
                          ;
              type syslog-log-switch ;
              default off ;
            }
            leaf cmdlog {
              description 'Send command log to syslog server.'
                          ;
              type syslog-log-switch ;
              default off ;
            }
            leaf servicelog {
              description 'Send service log to syslog server.'
                          ;
              type syslog-log-switch ;
              default off ;
            }
            leaf netconflog {
              description 'Send NETCONF log to syslog server.'
                          ;
              type syslog-log-switch ;
              default off ;
              ncd:revise-date 2016-02-23 ;
            }
            leaf braslog {
              description 'Send bras log to syslog server.'
                          ;
              type syslog-log-switch ;
              default off ;
            }
            leaf natlog {
              description 'Send NAT log to syslog server.'
                          ;
              type syslog-log-switch ;
              default off ;
            }
            leaf urllog {
              // if-feature urllog-syslog ;
              description 'Send URL log to syslog server.'
                          ;
              type syslog-log-switch ;
              default off ;
            }
            leaf nat-translationlog {
              // if-feature urllog-syslog ;
              description 'Send NAT translation log to syslog server.'
                          ;
              type syslog-log-switch ;
              default off ;
              ncd:revise-date 2016-02-01 ;
            }
            leaf nat-portrangelog {
              // if-feature urllog-syslog ;
              description 'Send NAT portrange log to syslog server.'
                          ;
              type syslog-log-switch ;
              default off ;
              ncd:revise-date 2016-02-01 ;
            }
            leaf haglog {
              // if-feature urllog-syslog ;
              description 'Send Hybrid Access Gateway log to syslog server.'
                          ;
              type syslog-log-switch ;
              default off ;
              ncd:revise-date 2017-03-03 ;
            }
            leaf snmplog {
              description 'Send SNMP log to syslog server.'
                          ;
              type syslog-log-switch ;
              default off ;
              ncd:revise-date 2017-07-28 ;
            }
            leaf weblog {
              description 'Send WEB log to syslog server.'
                          ;
              type syslog-log-switch ;
              default off ;
              ncd:revise-date 2018-12-26 ;
            }
            leaf traplog {
              description 'Send TRAP log to syslog server.'
                          ;
              type syslog-log-switch ;
              default off ;
              ncd:revise-date 2021-01-18 ;
            }
          }
        }
        container ipv6-linklocal-type {
          description 'Specify syslog-server host of IPv6(linklocal) without vr'
                    + 'f.'
                      ;
          list ipv6-linklocal {
            description 'Specify syslog-server host of IPv6 with linklocal.'
                        ;
            key 'ipv6-address interface-name'
                ;
            leaf ipv6-address {
              description 'IPv6 address.'
                          ;
              type ncd:ipv6-address {
                pattern '^[Ff][Ee][8-9a-bA-B][0-9a-fA-F]'
                        ;
              }
            }
            leaf interface-name {
              description 'Interface name.'
                          ;
              type ncd:ifname {
                length 1..31 ;
              }
            }
            container src-ip {
              description 'Source IPv6 address.'
                          ;
              leaf src-ipv6 {
                description 'Source IPv6 address.'
                            ;
                type ncd:ipv6-address ;
              }
              ncd:revise-date 2018-01-04 ;
            }
            leaf fport {
              description 'The remote port.'
                          ;
              type uint16 {
                range 1..65535 ;
              }
              default 514 ;
            }
            leaf lport {
              description 'The local port.'
                          ;
              type uint16 {
                range '514 | 1024..65535'
                      ;
              }
              default 514 ;
            }
            leaf alarmlog {
              description 'Send alarm log to syslog server.'
                          ;
              type syslog-log-switch ;
              default off ;
            }
            leaf debugmsg {
              description 'Send debug message to syslog server.'
                          ;
              type syslog-log-switch ;
              default off ;
            }
            leaf cmdlog {
              description 'Send command log to syslog server.'
                          ;
              type syslog-log-switch ;
              default off ;
            }
            leaf servicelog {
              description 'Send service log to syslog server.'
                          ;
              type syslog-log-switch ;
              default off ;
            }
            leaf netconflog {
              description 'Send NETCONF log to syslog server.'
                          ;
              type syslog-log-switch ;
              default off ;
              ncd:revise-date 2016-02-23 ;
            }
            leaf braslog {
              description 'Send bras log to syslog server.'
                          ;
              type syslog-log-switch ;
              default off ;
            }
            leaf natlog {
              description 'Send NAT log to syslog server.'
                          ;
              type syslog-log-switch ;
              default off ;
            }
            leaf urllog {
              // if-feature urllog-syslog ;
              description 'Send URL log to syslog server.'
                          ;
              type syslog-log-switch ;
              default off ;
            }
            leaf nat-translationlog {
              // if-feature urllog-syslog ;
              description 'Send NAT translation log to syslog server.'
                          ;
              type syslog-log-switch ;
              default off ;
              ncd:revise-date 2016-02-01 ;
            }
            leaf nat-portrangelog {
              // if-feature urllog-syslog ;
              description 'Send NAT portrange log to syslog server.'
                          ;
              type syslog-log-switch ;
              default off ;
              ncd:revise-date 2016-02-01 ;
            }
            leaf haglog {
              // if-feature urllog-syslog ;
              description 'Send Hybrid Access Gateway log to syslog server.'
                          ;
              type syslog-log-switch ;
              default off ;
              ncd:revise-date 2017-03-03 ;
            }
            leaf snmplog {
              description 'Send SNMP log to syslog server.'
                          ;
              type syslog-log-switch ;
              default off ;
              ncd:revise-date 2017-07-28 ;
            }
            leaf weblog {
              description 'Send WEB log to syslog server.'
                          ;
              type syslog-log-switch ;
              default off ;
              ncd:revise-date 2018-12-26 ;
            }
            leaf traplog {
              description 'Send TRAP log to syslog server.'
                          ;
              type syslog-log-switch ;
              default off ;
              ncd:revise-date 2021-01-18 ;
            }
          }
        }
        container ipv6-non-linklocal-type {
          description 'Specify syslog-server host of IPv6 without vrf.'
                      ;
          list ipv6-non-linklocal {
            description 'Specify syslog-server host of IPv6 without linklocal.'
                        ;
            key ipv6-address ;
            leaf ipv6-address {
              description 'IPv6 address.'
                          ;
              type ncd:ipv6-address ;
            }
            container src-ip {
              description 'Source IPv6 address.'
                          ;
              leaf src-ipv6 {
                description 'Source IPv6 address.'
                            ;
                type ncd:ipv6-address ;
              }
              ncd:revise-date 2018-01-04 ;
            }
            leaf fport {
              description 'The remote port.'
                          ;
              type uint16 {
                range 1..65535 ;
              }
              default 514 ;
            }
            leaf lport {
              description 'The local port.'
                          ;
              type uint16 {
                range '514 | 1024..65535'
                      ;
              }
              default 514 ;
            }
            leaf alarmlog {
              description 'Send alarm log to syslog server.'
                          ;
              type syslog-log-switch ;
              default off ;
            }
            leaf debugmsg {
              description 'Send debug message to syslog server.'
                          ;
              type syslog-log-switch ;
              default off ;
            }
            leaf cmdlog {
              description 'Send command log to syslog server.'
                          ;
              type syslog-log-switch ;
              default off ;
            }
            leaf servicelog {
              description 'Send service log to syslog server.'
                          ;
              type syslog-log-switch ;
              default off ;
            }
            leaf netconflog {
              description 'Send NETCONF log to syslog server.'
                          ;
              type syslog-log-switch ;
              default off ;
              ncd:revise-date 2016-02-23 ;
            }
            leaf braslog {
              description 'Send bras log to syslog server.'
                          ;
              type syslog-log-switch ;
              default off ;
            }
            leaf natlog {
              description 'Send NAT log to syslog server.'
                          ;
              type syslog-log-switch ;
              default off ;
            }
            leaf urllog {
              // if-feature urllog-syslog ;
              description 'Send URL log to syslog server.'
                          ;
              type syslog-log-switch ;
              default off ;
            }
            leaf nat-translationlog {
              // if-feature urllog-syslog ;
              description 'Send NAT translation log to syslog server.'
                          ;
              type syslog-log-switch ;
              default off ;
              ncd:revise-date 2016-02-01 ;
            }
            leaf nat-portrangelog {
              // if-feature urllog-syslog ;
              description 'Send NAT portrange log to syslog server.'
                          ;
              type syslog-log-switch ;
              default off ;
              ncd:revise-date 2016-02-01 ;
            }
            leaf haglog {
              // if-feature urllog-syslog ;
              description 'Send Hybrid Access Gateway log to syslog server.'
                          ;
              type syslog-log-switch ;
              default off ;
              ncd:revise-date 2017-03-03 ;
            }
            leaf snmplog {
              description 'Send SNMP log to syslog server.'
                          ;
              type syslog-log-switch ;
              default off ;
              ncd:revise-date 2017-07-28 ;
            }
            leaf weblog {
              description 'Send WEB log to syslog server.'
                          ;
              type syslog-log-switch ;
              default off ;
              ncd:revise-date 2018-12-26 ;
            }
            leaf traplog {
              description 'Send TRAP log to syslog server.'
                          ;
              type syslog-log-switch ;
              default off ;
              ncd:revise-date 2021-01-18 ;
            }
          }
        }
      }
      container tcp-hosts-vrf {
        // if-feature syslog-tcp ;
        description 'Specify syslog-server host with vrf.'
                    ;
        container ipv4-vrf {
          description 'Specify syslog-server host of ipv4 with vrf.'
                      ;
          list ipv4 {
            description 'Specify syslog-server host of ipv4.'
                        ;
            key 'vrf-name ipv4-address'
                ;
            leaf vrf-name {
              description 'VPN routing/forwarding instance (VRF) name.'
                          ;
              type string {
                length 1..32 ;
              }
            }
            leaf ipv4-address {
              description 'IPv4 address.'
                          ;
              type ncd:ipv4-address-none-zero ;
            }
            container ssl {
              description 'SSL name and PKI profile name.'
                          ;
              presence 'ssl-contex mandatory'
                       ;
              leaf ssl-context {
                description 'SSL name.'
                            ;
                type string {
                  length 1..31 ;
                }
                mandatory true ;
              }
              leaf pki-profile {
                description 'PKI profile name.'
                            ;
                type string {
                  length 1..63 ;
                }
              }
            }
            leaf src-ipv4 {
              description 'Source IPv4 address.'
                          ;
              type ncd:ipv4-address-none-zero ;
            }
            leaf fport {
              description 'The remote port.'
                          ;
              type uint16 {
                range 1..65535 ;
              }
              default 514 ;
            }
            leaf alarmlog {
              description 'Send alarm log to syslog server.'
                          ;
              type syslog-log-switch ;
              default off ;
            }
            leaf cmdlog {
              description 'Send command log to syslog server.'
                          ;
              type syslog-log-switch ;
              default off ;
            }
            leaf debugmsg {
              description 'Send debug message to syslog server.'
                          ;
              type syslog-log-switch ;
              default off ;
            }
            leaf servicelog {
              description 'Send service log to syslog server.'
                          ;
              type syslog-log-switch ;
              default off ;
            }
            leaf braslog {
              description 'Send bras log to syslog server.'
                          ;
              type syslog-log-switch ;
              default off ;
            }
            leaf netconflog {
              description 'Send NETCONF log to syslog server.'
                          ;
              type syslog-log-switch ;
              default off ;
            }
            leaf snmplog {
              description 'Send SNMP log to syslog server.'
                          ;
              type syslog-log-switch ;
              default off ;
            }
            leaf weblog {
              description 'Send WEB log to syslog server.'
                          ;
              type syslog-log-switch ;
              default off ;
            }
            leaf traplog {
              description 'Send TRAP log to syslog server.'
                          ;
              type syslog-log-switch ;
              default off ;
              ncd:revise-date 2021-01-18 ;
            }
          }
        }
        container ipv6-linklocal-vrf {
          description 'Specify syslog-server host of IPv6(linklocal) with vrf.'
                      ;
          list ipv6-linklocal {
            description 'Specify syslog-server host of IPv6 with linklocal.'
                        ;
            key 'vrf-name ipv6-address interface-name'
                ;
            leaf vrf-name {
              description 'VPN routing/forwarding instance (VRF) name.'
                          ;
              type string {
                length 1..32 ;
              }
            }
            leaf ipv6-address {
              description 'IPv6 address.'
                          ;
              type ncd:ipv6-address-none-zero {
                pattern '^[Ff][Ee][8-9a-bA-B][0-9a-fA-F]'
                        ;
              }
            }
            leaf interface-name {
              description 'Interface name.'
                          ;
              type ncd:ifname {
                length 1..31 ;
              }
            }
            container ssl {
              description 'SSL name and PKI profile name.'
                          ;
              presence 'ssl-contex mandatory'
                       ;
              leaf ssl-context {
                description 'SSL name.'
                            ;
                type string {
                  length 1..31 ;
                }
                mandatory true ;
              }
              leaf pki-profile {
                description 'PKI profile name.'
                            ;
                type string {
                  length 1..63 ;
                }
              }
            }
            container src-ip {
              description 'Source IPv6 address.'
                          ;
              leaf src-ipv6 {
                description 'Source IPv6 address.'
                            ;
                type ncd:ipv6-address-none-zero ;
              }
            }
            leaf fport {
              description 'The remote port.'
                          ;
              type uint16 {
                range 1..65535 ;
              }
              default 514 ;
            }
            leaf alarmlog {
              description 'Send alarm log to syslog server.'
                          ;
              type syslog-log-switch ;
              default off ;
            }
            leaf cmdlog {
              description 'Send command log to syslog server.'
                          ;
              type syslog-log-switch ;
              default off ;
            }
            leaf debugmsg {
              description 'Send debug message to syslog server.'
                          ;
              type syslog-log-switch ;
              default off ;
            }
            leaf servicelog {
              description 'Send service log to syslog server.'
                          ;
              type syslog-log-switch ;
              default off ;
            }
            leaf braslog {
              description 'Send bras log to syslog server.'
                          ;
              type syslog-log-switch ;
              default off ;
            }
            leaf netconflog {
              description 'Send NETCONF log to syslog server.'
                          ;
              type syslog-log-switch ;
              default off ;
            }
            leaf snmplog {
              description 'Send SNMP log to syslog server.'
                          ;
              type syslog-log-switch ;
              default off ;
            }
            leaf weblog {
              description 'Send WEB log to syslog server.'
                          ;
              type syslog-log-switch ;
              default off ;
            }
            leaf traplog {
              description 'Send TRAP log to syslog server.'
                          ;
              type syslog-log-switch ;
              default off ;
              ncd:revise-date 2021-01-18 ;
            }
          }
        }
        container ipv6-non-linklocal-vrf {
          description 'Specify syslog-server host of IPv6 with vrf.'
                      ;
          list ipv6-non-linklocal {
            description 'Specify syslog-server host of IPv6 without linklocal.'
                        ;
            key 'vrf-name ipv6-address'
                ;
            leaf vrf-name {
              description 'VPN routing/forwarding instance (VRF) name.'
                          ;
              type string {
                length 1..32 ;
              }
            }
            leaf ipv6-address {
              description 'IPv6 address.'
                          ;
              type ncd:ipv6-address-none-zero ;
            }
            container ssl {
              description 'SSL name and PKI profile name.'
                          ;
              presence 'ssl-contex mandatory'
                       ;
              leaf ssl-context {
                description 'SSL name.'
                            ;
                type string {
                  length 1..31 ;
                }
                mandatory true ;
              }
              leaf pki-profile {
                description 'PKI profile name.'
                            ;
                type string {
                  length 1..63 ;
                }
              }
            }
            container src-ip {
              description 'Source IPv6 address.'
                          ;
              leaf src-ipv6 {
                description 'Source IPv6 address.'
                            ;
                type ncd:ipv6-address-none-zero ;
              }
            }
            leaf fport {
              description 'The remote port.'
                          ;
              type uint16 {
                range 1..65535 ;
              }
              default 514 ;
            }
            leaf alarmlog {
              description 'Send alarm log to syslog server.'
                          ;
              type syslog-log-switch ;
              default off ;
            }
            leaf cmdlog {
              description 'Send command log to syslog server.'
                          ;
              type syslog-log-switch ;
              default off ;
            }
            leaf debugmsg {
              description 'Send debug message to syslog server.'
                          ;
              type syslog-log-switch ;
              default off ;
            }
            leaf servicelog {
              description 'Send service log to syslog server.'
                          ;
              type syslog-log-switch ;
              default off ;
            }
            leaf braslog {
              description 'Send bras log to syslog server.'
                          ;
              type syslog-log-switch ;
              default off ;
            }
            leaf netconflog {
              description 'Send NETCONF log to syslog server.'
                          ;
              type syslog-log-switch ;
              default off ;
            }
            leaf snmplog {
              description 'Send SNMP log to syslog server.'
                          ;
              type syslog-log-switch ;
              default off ;
            }
            leaf weblog {
              description 'Send WEB log to syslog server.'
                          ;
              type syslog-log-switch ;
              default off ;
            }
            leaf traplog {
              description 'Send TRAP log to syslog server.'
                          ;
              type syslog-log-switch ;
              default off ;
              ncd:revise-date 2021-01-18 ;
            }
          }
        }
        ncd:revise-date 2020-07-28 ;
      }
      container tcp-hosts {
        // if-feature syslog-tcp ;
        description 'Specify syslog-server host without vrf.'
                    ;
        container ipv4 {
          description 'Specify syslog-server host of ipv4 without vrf.'
                      ;
          list ipv4 {
            description 'Specify syslog-server host of ipv4.'
                        ;
            key ipv4-address ;
            leaf ipv4-address {
              description 'IPv4 address.'
                          ;
              type ncd:ipv4-address-none-zero ;
            }
            container ssl {
              description 'SSL name and PKI profile name.'
                          ;
              presence 'ssl-contex mandatory'
                       ;
              leaf ssl-context {
                description 'SSL name.'
                            ;
                type string {
                  length 1..31 ;
                }
                mandatory true ;
              }
              leaf pki-profile {
                description 'PKI profile name.'
                            ;
                type string {
                  length 1..63 ;
                }
              }
            }
            leaf src-ipv4 {
              description 'Source IPv4 address.'
                          ;
              type ncd:ipv4-address-none-zero ;
            }
            leaf fport {
              description 'The remote port.'
                          ;
              type uint16 {
                range 1..65535 ;
              }
              default 514 ;
            }
            leaf alarmlog {
              description 'Send alarm log to syslog server.'
                          ;
              type syslog-log-switch ;
              default off ;
            }
            leaf cmdlog {
              description 'Send command log to syslog server.'
                          ;
              type syslog-log-switch ;
              default off ;
            }
            leaf debugmsg {
              description 'Send debug message to syslog server.'
                          ;
              type syslog-log-switch ;
              default off ;
            }
            leaf servicelog {
              description 'Send service log to syslog server.'
                          ;
              type syslog-log-switch ;
              default off ;
            }
            leaf braslog {
              description 'Send bras log to syslog server.'
                          ;
              type syslog-log-switch ;
              default off ;
            }
            leaf netconflog {
              description 'Send NETCONF log to syslog server.'
                          ;
              type syslog-log-switch ;
              default off ;
            }
            leaf snmplog {
              description 'Send SNMP log to syslog server.'
                          ;
              type syslog-log-switch ;
              default off ;
            }
            leaf weblog {
              description 'Send WEB log to syslog server.'
                          ;
              type syslog-log-switch ;
              default off ;
            }
            leaf traplog {
              description 'Send TRAP log to syslog server.'
                          ;
              type syslog-log-switch ;
              default off ;
              ncd:revise-date 2021-01-18 ;
            }
          }
        }
        container ipv6-linklocal {
          description 'Specify syslog-server host of IPv6(linklocal) without vr'
                    + 'f.'
                      ;
          list ipv6-linklocal {
            description 'Specify syslog-server host of IPv6 with linklocal.'
                        ;
            key 'ipv6-address interface-name'
                ;
            leaf ipv6-address {
              description 'IPv6 address.'
                          ;
              type ncd:ipv6-address-none-zero {
                pattern '^[Ff][Ee][8-9a-bA-B][0-9a-fA-F]'
                        ;
              }
            }
            leaf interface-name {
              description 'Interface name.'
                          ;
              type ncd:ifname {
                length 1..31 ;
              }
            }
            container ssl {
              description 'SSL name and PKI profile name.'
                          ;
              presence 'ssl-contex mandatory'
                       ;
              leaf ssl-context {
                description 'SSL name.'
                            ;
                type string {
                  length 1..31 ;
                }
                mandatory true ;
              }
              leaf pki-profile {
                description 'PKI profile name.'
                            ;
                type string {
                  length 1..63 ;
                }
              }
            }
            container src-ip {
              description 'Source IPv6 address.'
                          ;
              leaf src-ipv6 {
                description 'Source IPv6 address.'
                            ;
                type ncd:ipv6-address-none-zero ;
              }
            }
            leaf fport {
              description 'The remote port.'
                          ;
              type uint16 {
                range 1..65535 ;
              }
              default 514 ;
            }
            leaf alarmlog {
              description 'Send alarm log to syslog server.'
                          ;
              type syslog-log-switch ;
              default off ;
            }
            leaf cmdlog {
              description 'Send command log to syslog server.'
                          ;
              type syslog-log-switch ;
              default off ;
            }
            leaf debugmsg {
              description 'Send debug message to syslog server.'
                          ;
              type syslog-log-switch ;
              default off ;
            }
            leaf servicelog {
              description 'Send service log to syslog server.'
                          ;
              type syslog-log-switch ;
              default off ;
            }
            leaf braslog {
              description 'Send bras log to syslog server.'
                          ;
              type syslog-log-switch ;
              default off ;
            }
            leaf netconflog {
              description 'Send NETCONF log to syslog server.'
                          ;
              type syslog-log-switch ;
              default off ;
            }
            leaf snmplog {
              description 'Send SNMP log to syslog server.'
                          ;
              type syslog-log-switch ;
              default off ;
            }
            leaf weblog {
              description 'Send WEB log to syslog server.'
                          ;
              type syslog-log-switch ;
              default off ;
            }
            leaf traplog {
              description 'Send TRAP log to syslog server.'
                          ;
              type syslog-log-switch ;
              default off ;
              ncd:revise-date 2021-01-18 ;
            }
          }
        }
        container ipv6-non-linklocal {
          description 'Specify syslog-server host of IPv6 without vrf.'
                      ;
          list ipv6-non-linklocal {
            description 'Specify syslog-server host of IPv6 without linklocal.'
                        ;
            key ipv6-address ;
            leaf ipv6-address {
              description 'IPv6 address.'
                          ;
              type ncd:ipv6-address-none-zero ;
            }
            container ssl {
              description 'SSL name and PKI profile name.'
                          ;
              presence 'ssl-contex mandatory'
                       ;
              leaf ssl-context {
                description 'SSL name.'
                            ;
                type string {
                  length 1..31 ;
                }
                mandatory true ;
              }
              leaf pki-profile {
                description 'PKI profile name.'
                            ;
                type string {
                  length 1..63 ;
                }
              }
            }
            container src-ip {
              description 'Source IPv6 address.'
                          ;
              leaf src-ipv6 {
                description 'Source IPv6 address.'
                            ;
                type ncd:ipv6-address-none-zero ;
              }
            }
            leaf fport {
              description 'The remote port.'
                          ;
              type uint16 {
                range 1..65535 ;
              }
              default 514 ;
            }
            leaf alarmlog {
              description 'Send alarm log to syslog server.'
                          ;
              type syslog-log-switch ;
              default off ;
            }
            leaf cmdlog {
              description 'Send command log to syslog server.'
                          ;
              type syslog-log-switch ;
              default off ;
            }
            leaf debugmsg {
              description 'Send debug message to syslog server.'
                          ;
              type syslog-log-switch ;
              default off ;
            }
            leaf servicelog {
              description 'Send service log to syslog server.'
                          ;
              type syslog-log-switch ;
              default off ;
            }
            leaf braslog {
              description 'Send bras log to syslog server.'
                          ;
              type syslog-log-switch ;
              default off ;
            }
            leaf netconflog {
              description 'Send NETCONF log to syslog server.'
                          ;
              type syslog-log-switch ;
              default off ;
            }
            leaf snmplog {
              description 'Send SNMP log to syslog server.'
                          ;
              type syslog-log-switch ;
              default off ;
            }
            leaf weblog {
              description 'Send WEB log to syslog server.'
                          ;
              type syslog-log-switch ;
              default off ;
            }
            leaf traplog {
              description 'Send TRAP log to syslog server.'
                          ;
              type syslog-log-switch ;
              default off ;
              ncd:revise-date 2021-01-18 ;
            }
          }
        }
        ncd:revise-date 2020-07-28 ;
      }
      leaf facility {
        description 'Facility parameter for syslog messages.'
                    ;
        type syslog-facility ;
        default local0 ;
      }
      leaf level {
        description 'Set syslog logging level.'
                    ;
        type alarm-level ;
        default notifications ;
      }
    }
    container syslog {
      description 'Specify SYSLOG.'
                  ;
      container format {
        description 'Specify the format of SYSLOG.'
                    ;
        leaf format {
          // if-feature syslog-format ;
          description 'Syslog format.'
                      ;
          type syslog-format ;
          default rfc3164 ;
        }
      }
      ncd:revise-date 2020-05-21 ;
    }
  }
}
