module zxr10-isakmp-dev-t8000 {
  namespace 'http://www.zte.com.cn/zxr10/netconf/schema/rosng/isakmp-dev-t8000'
            ;
  prefix isakmp-dev-t8000 ;
  import zxr10-isakmp {
    prefix isakmp ;
  }
  organization 'ZTE Corporation'
               ;
  contact 'ZTE Corporation  '+"\n"
        + '   Nanjing Institute of ZTE Corporation '+"\n"
        + '   No.68 Zijinghua Rd. Yuhuatai District, Nanjing, China '+"\n"
        + '   Tel: +86-25-52870000'
          ;
  revision 2017-10-16 ;
  deviation '/isakmp:configuration/isakmp:isakmp/isakmp:isakmp-policys/isakmp:i'
          + 'sakmp-policy/isakmp:authentication'
            {
    deviate replace {
      type enumeration {
        enum pre-share {
          value 0 ;
          description 'Pre-Shared key'
                      ;
        }
        enum rsa-sig {
          value 1 ;
          description 'RSA signature'
                      ;
        }
      }
    }
  }
  deviation '/isakmp:configuration/isakmp:isakmp/isakmp:isakmp-policys/isakmp:i'
          + 'sakmp-policy/isakmp:encryption'
            {
    deviate replace {
      type enumeration {
        enum aes-128 {
          value 0 ;
          description 'AES - Advanced Encryption Standard(128 bit keys)'
                      ;
        }
        enum aes-192 {
          value 1 ;
          description 'AES - Advanced Encryption Standard(192 bit keys)'
                      ;
        }
        enum aes-256 {
          value 2 ;
          description 'AES - Advanced Encryption Standard(256 bit keys)'
                      ;
        }
        enum des {
          value 3 ;
          description 'DES - Data Encryption Standard (56 bit keys)'
                      ;
        }
        enum 3des {
          value 4 ;
          description 'Three key triple DES'
                      ;
        }
      }
    }
  }
  deviation '/isakmp:configuration/isakmp:isakmp/isakmp:isakmp-policys/isakmp:i'
          + 'sakmp-policy/isakmp:hash'
            {
    deviate replace {
      type enumeration {
        enum md5 {
          value 0 ;
          description 'Message Digest 5'
                      ;
        }
        enum sha1 {
          value 1 ;
          description 'Secure Hash Standard'
                      ;
        }
        enum sha256 {
          value 3 ;
          description 'Secure Hash Standard 256'
                      ;
        }
        enum sha384 {
          value 4 ;
          description 'Secure Hash Standard 384'
                      ;
        }
        enum sha512 {
          value 5 ;
          description 'Secure Hash Standard 512'
                      ;
        }
      }
    }
  }
}
