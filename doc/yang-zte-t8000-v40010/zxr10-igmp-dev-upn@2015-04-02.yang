module zxr10-igmp-dev-upn {
  namespace 'http://www.zte.com.cn/zxr10/netconf/schema/rosng/router-igmp' ;
  prefix router-igmp ;
  import zxr10-igmp {
    prefix igmp ;
  }
  organization 'ZTE Corporation' ;
  contact "ZTE Corporation  
\n"
        + "   Nanjing Institute of ZTE Corporation 
\n"
        + "   No.68 Zijinghua Rd. Yuhuatai District, Nanjing, China 
\n"
        + '   Tel: +86-25-52870000'
          ;
  description 'IGMP in router.' ;
  revision 2015-04-02 {
    description 'Delete the revision date of the import.' ;
  }
  revision 2014-03-11 {
    description 'Initial version.' ;
  }
  deviation "/igmp:configuration/igmp:router-igmp/igmp:igmps/igmp:group-intf-nu"
          + "ms"
            {
    description 'Max host limit commands' ;
    deviate not-supported ;
  }
  deviation "/igmp:configuration/igmp:router-igmp/igmp:igmp-vrf/igmp:igmp/igmp:"
          + "group-intf-nums"
            {
    description 'Max host limit commands' ;
    deviate not-supported ;
  }
}
